module saos106-nc-1.0 {
  yang-version 1.1;
  namespace "http://tail-f.com/ns/ned-id/saos106-nc-1.0";
  prefix saos106-nc-1.0;

  import saos106-nc {
    prefix family;
  }

  identity saos106-nc-1.0 {
    base family:saos106-nc;
  }
}
