module ciena-bfd-types {
  // Generated by yanger -t ncs
  tailf:mount-id "saos106-nc-1.0:saos106-nc-1.0";
  tailf:ncs-device-type "netconf";

  namespace "http://ciena.com/ns/yang/ciena-bfd-types";
  prefix bfd-types;

  import iana-bfd-types {
    prefix iana-bfd-types;
  }
  import ietf-inet-types {
    prefix inet;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
                 Hanover, Maryland 21076
                 U.S.A.
     Phone:   +1 800-921-1144
     Fax:     +1 410-694-5750";
  description
    "This YANG module defines Ciena's BFD Types.

     Copyright (c) 2019  Ciena Corporation.  All rights
     reserved.

     All information contained herein is, and remains the
     property of Ciena Corporation. Dissemination of this
     information or reproduction of this material is strictly
     forbidden unless prior written permission is obtained
     from Ciena Corporation.";

  revision 2021-02-01 {
    description
      "Added a leaf statistics-collection (on/off).";
  }
  revision 2020-08-19 {
    description
      "Added bfd-session-type.
       Added identity bfd-client.
       Added grouping bfd-client-info.
       Added grouping session-statistics-summary.
       Added feature for accelerated BFD.
       Added an enum of value 3300 (3.3ms).";
  }
  revision 2010-02-14 {
    description
      "Initial revision.";
  }

  typedef ncs_template_discriminator {
    type string;
    description
      "BFD discriminator as described in RFC 5880.";
  }

  typedef ncs_template_state {
    type string;
    description
      "BFD state as defined in RFC 5880.";
  }

  typedef ncs_template_multiplier {
    type string;
    description
      "BFD multiplier as described in RFC 5880.";
  }

  typedef ncs_template_intervals {
    type string;
    units "microseconds";
    description
      "Supported BFD intervals.";
  }

  typedef ncs_template_bfd-session-type {
    type string;
    description
      "BFD session type, this indicates the path type that BFD is
       running on";
  }

  typedef ncs_rpc_notif_discriminator {
    type uint32;
    description
      "BFD discriminator as described in RFC 5880.";
  }

  typedef ncs_rpc_notif_state {
    type enumeration {
      enum "adminDown" {
        value 0;
        description
          "BFD session is administratively down";
      }
      enum "down" {
        value 1;
        description
          "BFD session is down";
      }
      enum "init" {
        value 2;
        description
          "BFD session is in init state";
      }
      enum "up" {
        value 3;
        description
          "BFD session is established";
      }
    }
    description
      "BFD state as defined in RFC 5880.";
  }

  typedef ncs_rpc_notif_multiplier {
    type uint8 {
      range "3..50";
    }
    description
      "BFD multiplier as described in RFC 5880.";
  }

  typedef ncs_rpc_notif_intervals {
    type enumeration {
      enum "10000" {
        value 0;
        description
          "10ms interval";
      }
      enum "20000" {
        value 1;
        description
          "20ms interval";
      }
      enum "50000" {
        value 2;
        description
          "50ms interval";
      }
      enum "100000" {
        value 3;
        description
          "100ms interval";
      }
      enum "300000" {
        value 4;
        description
          "300ms interval";
      }
      enum "1000000" {
        value 5;
        description
          "1second interval";
      }
      enum "10000000" {
        value 6;
        description
          "10seconds interval";
      }
      enum "3300" {
        value 7;
        description
          "3.3ms interval";
      }
    }
    units "microseconds";
    description
      "Supported BFD intervals.";
  }

  typedef ncs_rpc_notif_bfd-session-type {
    type enumeration {
      enum "ip-single-hop" {
        value 0;
        description
          "IP single-hop BFD session";
      }
      enum "ip-multi-hop" {
        value 1;
        description
          "IP multi-hop BFD session";
      }
      enum "tp-ingress-corout" {
        value 2;
        description
          "Ingress MPLS-TP co-routed LSP BFD session";
      }
      enum "tp-egress-corout" {
        value 3;
        description
          "Egress MPLS-TP co-routed LSP BFD session";
      }
    }
    description
      "BFD session type, this indicates the path type that BFD is
       running on";
  }

  typedef live_ncs_discriminator {
    type uint32;
    description
      "BFD discriminator as described in RFC 5880.";
  }

  typedef live_ncs_state {
    type enumeration {
      enum "adminDown" {
        value 0;
        description
          "BFD session is administratively down";
      }
      enum "down" {
        value 1;
        description
          "BFD session is down";
      }
      enum "init" {
        value 2;
        description
          "BFD session is in init state";
      }
      enum "up" {
        value 3;
        description
          "BFD session is established";
      }
    }
    description
      "BFD state as defined in RFC 5880.";
  }

  typedef live_ncs_multiplier {
    type uint8 {
      range "3..50";
    }
    description
      "BFD multiplier as described in RFC 5880.";
  }

  typedef live_ncs_intervals {
    type enumeration {
      enum "10000" {
        value 0;
        description
          "10ms interval";
      }
      enum "20000" {
        value 1;
        description
          "20ms interval";
      }
      enum "50000" {
        value 2;
        description
          "50ms interval";
      }
      enum "100000" {
        value 3;
        description
          "100ms interval";
      }
      enum "300000" {
        value 4;
        description
          "300ms interval";
      }
      enum "1000000" {
        value 5;
        description
          "1second interval";
      }
      enum "10000000" {
        value 6;
        description
          "10seconds interval";
      }
      enum "3300" {
        value 7;
        description
          "3.3ms interval";
      }
    }
    units "microseconds";
    description
      "Supported BFD intervals.";
  }

  typedef live_ncs_bfd-session-type {
    type enumeration {
      enum "ip-single-hop" {
        value 0;
        description
          "IP single-hop BFD session";
      }
      enum "ip-multi-hop" {
        value 1;
        description
          "IP multi-hop BFD session";
      }
      enum "tp-ingress-corout" {
        value 2;
        description
          "Ingress MPLS-TP co-routed LSP BFD session";
      }
      enum "tp-egress-corout" {
        value 3;
        description
          "Egress MPLS-TP co-routed LSP BFD session";
      }
    }
    description
      "BFD session type, this indicates the path type that BFD is
       running on";
  }

  typedef discriminator {
    type uint32;
    description
      "BFD discriminator as described in RFC 5880.";
  }

  typedef state {
    type enumeration {
      enum "adminDown" {
        value 0;
        description
          "BFD session is administratively down";
      }
      enum "down" {
        value 1;
        description
          "BFD session is down";
      }
      enum "init" {
        value 2;
        description
          "BFD session is in init state";
      }
      enum "up" {
        value 3;
        description
          "BFD session is established";
      }
    }
    description
      "BFD state as defined in RFC 5880.";
  }

  typedef multiplier {
    type uint8 {
      range "3..50";
    }
    description
      "BFD multiplier as described in RFC 5880.";
  }

  typedef intervals {
    type enumeration {
      enum "10000" {
        value 0;
        description
          "10ms interval";
      }
      enum "20000" {
        value 1;
        description
          "20ms interval";
      }
      enum "50000" {
        value 2;
        description
          "50ms interval";
      }
      enum "100000" {
        value 3;
        description
          "100ms interval";
      }
      enum "300000" {
        value 4;
        description
          "300ms interval";
      }
      enum "1000000" {
        value 5;
        description
          "1second interval";
      }
      enum "10000000" {
        value 6;
        description
          "10seconds interval";
      }
      enum "3300" {
        value 7;
        description
          "3.3ms interval";
      }
    }
    units "microseconds";
    description
      "Supported BFD intervals.";
  }

  typedef bfd-session-type {
    type enumeration {
      enum "ip-single-hop" {
        value 0;
        description
          "IP single-hop BFD session";
      }
      enum "ip-multi-hop" {
        value 1;
        description
          "IP multi-hop BFD session";
      }
      enum "tp-ingress-corout" {
        value 2;
        description
          "Ingress MPLS-TP co-routed LSP BFD session";
      }
      enum "tp-egress-corout" {
        value 3;
        description
          "Egress MPLS-TP co-routed LSP BFD session";
      }
    }
    description
      "BFD session type, this indicates the path type that BFD is
       running on";
  }

  grouping ncs_template_base-cfg-parms {
    description
      "BFD grouping for base config parameters.";
    leaf local-multiplier {
      type ncs_template_multiplier;
      // NCS drop default statement
      description
        "Multiplier transmitted by local system.";
    }
    leaf desired-min-tx-interval {
      type ncs_template_intervals;
      units "microseconds";
      // NCS drop default statement
      description
        "Desired minimum transmit interval of control packets in microseconds.";
    }
    leaf required-min-rx-interval {
      type ncs_template_intervals;
      units "microseconds";
      // NCS drop default statement
      description
        "Required minimum receive interval of control packets in microseconds.";
    }
    leaf accelerate {
      // NCS drop if-feature statement
      type string;
      // NCS drop default statement
      description
        "If enabled, BFD will run in an accelerated mode (for example, in hardware).";
    }
    leaf statistics-collection {
      // NCS drop when statement
      // NCS drop if-feature statement
      type string;
      // NCS drop default statement
      description
        "Determines whether statistics collection will be turned on or off for accelerated BFD session.";
    }
  }

  grouping ncs_template_client-cfg-parms {
    description
      "BFD grouping for configuration parameters
       used by clients of BFD, e.g. IGP or MPLS.";
    leaf enable {
      type string;
      // NCS drop default statement
      description
        "Enable BFD.";
    }
  }

  grouping ncs_template_bgp-client-cfg-parms {
    description
      "BFD grouping for configuration parameters for BGP";
    leaf enable {
      type string;
      // NCS drop default statement
      description
        "Enable BFD for BGP.";
    }
    leaf multihop {
      type string;
      // NCS drop default statement
      // NCS drop when statement
      description
        "Configure multihop IP BFD for BGP.";
    }
  }

  grouping ncs_template_common-cfg-parms {
    description
      "BFD grouping for common configuration parameters.";
    uses ncs_template_base-cfg-parms;
    leaf admin-down {
      type string;
      // NCS drop default statement
      description
        "Is the BFD session administratively down.";
    }
  }

  grouping ncs_template_all-session {
    description
      "BFD session operational information";
    leaf path-type {
      type string;
      description
        "BFD path type, this indicates the path type that BFD is
         running on.";
    }
    leaf ip-encapsulation {
      type string;
      description
        "Whether BFD encapsulation uses IP.";
    }
    leaf local-discriminator {
      type ncs_template_discriminator;
      description
        "Local discriminator used to uniquely identify the BFD session.";
    }
    leaf remote-discriminator {
      type ncs_template_discriminator;
      description
        "Descriminator chosen by the remote system.";
    }
    leaf source-port {
      // NCS drop when statement
      type string;
      description
        "Source UDP port";
    }
    leaf dest-port {
      // NCS drop when statement
      type string;
      description
        "Destination UDP port.";
    }
    container session-running {
      description
        "BFD session running information.";
      leaf session-index {
        type string;
        description
          "An index used to uniquely identify BFD sessions.";
      }
      leaf local-state {
        type ncs_template_state;
        description
          "Local state of the BFD session.";
      }
      leaf remote-state {
        type ncs_template_state;
        description
          "Remote state of the BFD session.";
      }
      leaf local-diagnostic {
        type iana-bfd-types:ncs_template_diagnostic;
        description
          "Local diagnostic.";
      }
      leaf detection-mode {
        type string;
        description
          "Detection mode.";
      }
      leaf negotiated-tx-interval {
        type string;
        units "microseconds";
        description
          "Negotiated transmit interval.";
      }
      leaf negotiated-rx-interval {
        type string;
        units "microseconds";
        description
          "Negotiated receive interval.";
      }
      leaf detection-time {
        type string;
        units "microseconds";
        description
          "Detection time.";
      }
    }
    container session-statistics {
      description
        "BFD per-session statistics.";
      leaf last-down-time {
        type string;
        description
          "Time and date of last time this session went down.(HH:MM:SS)";
      }
      leaf last-up-time {
        type string;
        description
          "Time and date of last time this session went up.(HH:MM:SS)";
      }
      leaf up-count {
        type string;
        description
          "The number of times this session has transitioned in the
           down state.";
      }
      leaf receive-packet-count {
        type string;
        description
          "Count of received packets in this session. This includes
           valid and invalid received packets.";
      }
      leaf send-packet-count {
        type string;
        description
          "Count of sent packets in this session.";
      }
    }
  }

  grouping ncs_template_bfd-client-info {
    description
      "BFD client info per session.";
    leaf-list client-info {
      // NCS patched for predictable order
      ordered-by user;
      type string;
      description
        "BFD Client list.";
    }
  }

  grouping ncs_template_session-statistics-summary {
    description
      "Grouping for session statistics summary.";
    leaf number-of-sessions {
      type string;
      description
        "Number of BFD sessions.";
    }
    leaf number-of-sessions-up {
      type string;
      description
        "Number of BFD sessions currently in up state (as defined
         in RFC 5880).";
    }
    leaf number-of-sessions-down {
      type string;
      description
        "Number of BFD sessions currently in down or init state
         but not admin-down (as defined in RFC 5880).";
    }
    leaf number-of-sessions-admin-down {
      type string;
      description
        "Number of BFD sessions currently in admin-down state (as
         defined in RFC 5880).";
    }
  }

  grouping ncs_rpc_notif_base-cfg-parms {
    description
      "BFD grouping for base config parameters.";
    leaf local-multiplier {
      type ncs_rpc_notif_multiplier;
      default "3";
      description
        "Multiplier transmitted by local system.";
    }
    leaf desired-min-tx-interval {
      type ncs_rpc_notif_intervals;
      units "microseconds";
      default "100000";
      description
        "Desired minimum transmit interval of control packets in microseconds.";
    }
    leaf required-min-rx-interval {
      type ncs_rpc_notif_intervals;
      units "microseconds";
      default "100000";
      description
        "Required minimum receive interval of control packets in microseconds.";
    }
    leaf accelerate {
      tailf:display-when "not(../ncs:module) or boolean(/ncs:devices/ncs:device[ncs:name=current()/../ncs:name]/capability/feature='accelerated-bfd')";
      type boolean;
      default "false";
      description
        "If enabled, BFD will run in an accelerated mode (for example, in hardware).";
    }
    leaf statistics-collection {
      when "../accelerate = 'true'" {
        tailf:xpath-root 3;
      }
      tailf:display-when "not(../ncs:module) or boolean(/ncs:devices/ncs:device[ncs:name=current()/../ncs:name]/capability/feature='accelerated-bfd')";
      type enumeration {
        enum "on" {
          value 0;
          description
            "Statistics-collection will be on for accelerated BFD session";
        }
        enum "off" {
          value 1;
          description
            "Statistics-collection will be off for accelerated BFD session";
        }
      }
      default "off";
      description
        "Determines whether statistics collection will be turned on or off for accelerated BFD session.";
    }
  }

  grouping ncs_rpc_notif_client-cfg-parms {
    description
      "BFD grouping for configuration parameters
       used by clients of BFD, e.g. IGP or MPLS.";
    leaf enable {
      type boolean;
      default "false";
      description
        "Enable BFD.";
    }
  }

  grouping ncs_rpc_notif_bgp-client-cfg-parms {
    description
      "BFD grouping for configuration parameters for BGP";
    leaf enable {
      type boolean;
      default "false";
      description
        "Enable BFD for BGP.";
    }
    leaf multihop {
      type boolean;
      default "false";
      when "../enable= 'true'" {
        tailf:xpath-root 3;
      }
      description
        "Configure multihop IP BFD for BGP.";
    }
  }

  grouping ncs_rpc_notif_common-cfg-parms {
    description
      "BFD grouping for common configuration parameters.";
    uses ncs_rpc_notif_base-cfg-parms;
    leaf admin-down {
      type boolean;
      default "false";
      description
        "Is the BFD session administratively down.";
    }
  }

  grouping ncs_rpc_notif_all-session {
    description
      "BFD session operational information";
    leaf path-type {
      type identityref {
        base path-type;
      }
      description
        "BFD path type, this indicates the path type that BFD is
         running on.";
    }
    leaf ip-encapsulation {
      type boolean;
      description
        "Whether BFD encapsulation uses IP.";
    }
    leaf local-discriminator {
      type ncs_rpc_notif_discriminator;
      description
        "Local discriminator used to uniquely identify the BFD session.";
    }
    leaf remote-discriminator {
      type ncs_rpc_notif_discriminator;
      description
        "Descriminator chosen by the remote system.";
    }
    leaf source-port {
      when "../ip-encapsulation = 'true'" {
        tailf:xpath-root 3;
        description
          "Source UDP port valid only when IP encapsulation is used.";
      }
      type inet:port-number;
      description
        "Source UDP port";
    }
    leaf dest-port {
      when "../ip-encapsulation = 'true'" {
        tailf:xpath-root 3;
        description
          "Destination UDP port valid only when IP encapsulation is used.";
      }
      type inet:port-number;
      description
        "Destination UDP port.";
    }
    container session-running {
      description
        "BFD session running information.";
      leaf session-index {
        type uint32;
        description
          "An index used to uniquely identify BFD sessions.";
      }
      leaf local-state {
        type ncs_rpc_notif_state;
        description
          "Local state of the BFD session.";
      }
      leaf remote-state {
        type ncs_rpc_notif_state;
        description
          "Remote state of the BFD session.";
      }
      leaf local-diagnostic {
        type iana-bfd-types:ncs_rpc_notif_diagnostic;
        description
          "Local diagnostic.";
      }
      leaf detection-mode {
        type enumeration {
          enum "async-with-echo" {
            value 1;
            description
              "Async with echo.";
          }
          enum "async-without-echo" {
            value 2;
            description
              "Async without echo.";
          }
          enum "demand-with-echo" {
            value 3;
            description
              "Demand with echo.";
          }
          enum "demand-without-echo" {
            value 4;
            description
              "Demand without echo.";
          }
        }
        description
          "Detection mode.";
      }
      leaf negotiated-tx-interval {
        type uint32;
        units "microseconds";
        description
          "Negotiated transmit interval.";
      }
      leaf negotiated-rx-interval {
        type uint32;
        units "microseconds";
        description
          "Negotiated receive interval.";
      }
      leaf detection-time {
        type uint32;
        units "microseconds";
        description
          "Detection time.";
      }
    }
    container session-statistics {
      description
        "BFD per-session statistics.";
      leaf last-down-time {
        type string;
        description
          "Time and date of last time this session went down.(HH:MM:SS)";
      }
      leaf last-up-time {
        type string;
        description
          "Time and date of last time this session went up.(HH:MM:SS)";
      }
      leaf up-count {
        type yang:counter32;
        description
          "The number of times this session has transitioned in the
           down state.";
      }
      leaf receive-packet-count {
        type yang:counter64;
        description
          "Count of received packets in this session. This includes
           valid and invalid received packets.";
      }
      leaf send-packet-count {
        type yang:counter64;
        description
          "Count of sent packets in this session.";
      }
    }
  }

  grouping ncs_rpc_notif_bfd-client-info {
    description
      "BFD client info per session.";
    leaf-list client-info {
      type identityref {
        base bfd-client;
      }
      description
        "BFD Client list.";
    }
  }

  grouping ncs_rpc_notif_session-statistics-summary {
    description
      "Grouping for session statistics summary.";
    leaf number-of-sessions {
      type yang:gauge32;
      description
        "Number of BFD sessions.";
    }
    leaf number-of-sessions-up {
      type yang:gauge32;
      description
        "Number of BFD sessions currently in up state (as defined
         in RFC 5880).";
    }
    leaf number-of-sessions-down {
      type yang:gauge32;
      description
        "Number of BFD sessions currently in down or init state
         but not admin-down (as defined in RFC 5880).";
    }
    leaf number-of-sessions-admin-down {
      type yang:gauge32;
      description
        "Number of BFD sessions currently in admin-down state (as
         defined in RFC 5880).";
    }
  }

  grouping live_ncs_base-cfg-parms {
    description
      "BFD grouping for base config parameters.";
    leaf local-multiplier {
      type live_ncs_multiplier;
      // NCS drop default statement
      description
        "Multiplier transmitted by local system.";
    }
    leaf desired-min-tx-interval {
      type live_ncs_intervals;
      units "microseconds";
      // NCS drop default statement
      description
        "Desired minimum transmit interval of control packets in microseconds.";
    }
    leaf required-min-rx-interval {
      type live_ncs_intervals;
      units "microseconds";
      // NCS drop default statement
      description
        "Required minimum receive interval of control packets in microseconds.";
    }
    leaf accelerate {
      // NCS drop if-feature statement
      type boolean;
      // NCS drop default statement
      description
        "If enabled, BFD will run in an accelerated mode (for example, in hardware).";
    }
    leaf statistics-collection {
      // NCS drop when statement
      // NCS drop if-feature statement
      type enumeration {
        enum "on" {
          value 0;
          description
            "Statistics-collection will be on for accelerated BFD session";
        }
        enum "off" {
          value 1;
          description
            "Statistics-collection will be off for accelerated BFD session";
        }
      }
      // NCS drop default statement
      description
        "Determines whether statistics collection will be turned on or off for accelerated BFD session.";
    }
  }

  grouping live_ncs_client-cfg-parms {
    description
      "BFD grouping for configuration parameters
       used by clients of BFD, e.g. IGP or MPLS.";
    leaf enable {
      type boolean;
      // NCS drop default statement
      description
        "Enable BFD.";
    }
  }

  grouping live_ncs_bgp-client-cfg-parms {
    description
      "BFD grouping for configuration parameters for BGP";
    leaf enable {
      type boolean;
      // NCS drop default statement
      description
        "Enable BFD for BGP.";
    }
    leaf multihop {
      type boolean;
      // NCS drop default statement
      // NCS drop when statement
      description
        "Configure multihop IP BFD for BGP.";
    }
  }

  grouping live_ncs_common-cfg-parms {
    description
      "BFD grouping for common configuration parameters.";
    uses live_ncs_base-cfg-parms;
    leaf admin-down {
      type boolean;
      // NCS drop default statement
      description
        "Is the BFD session administratively down.";
    }
  }

  grouping live_ncs_all-session {
    description
      "BFD session operational information";
    leaf path-type {
      type identityref {
        base path-type;
      }
      description
        "BFD path type, this indicates the path type that BFD is
         running on.";
    }
    leaf ip-encapsulation {
      type boolean;
      description
        "Whether BFD encapsulation uses IP.";
    }
    leaf local-discriminator {
      type live_ncs_discriminator;
      description
        "Local discriminator used to uniquely identify the BFD session.";
    }
    leaf remote-discriminator {
      type live_ncs_discriminator;
      description
        "Descriminator chosen by the remote system.";
    }
    leaf source-port {
      // NCS drop when statement
      type inet:port-number;
      description
        "Source UDP port";
    }
    leaf dest-port {
      // NCS drop when statement
      type inet:port-number;
      description
        "Destination UDP port.";
    }
    container session-running {
      description
        "BFD session running information.";
      leaf session-index {
        type uint32;
        description
          "An index used to uniquely identify BFD sessions.";
      }
      leaf local-state {
        type live_ncs_state;
        description
          "Local state of the BFD session.";
      }
      leaf remote-state {
        type live_ncs_state;
        description
          "Remote state of the BFD session.";
      }
      leaf local-diagnostic {
        type iana-bfd-types:live_ncs_diagnostic;
        description
          "Local diagnostic.";
      }
      leaf detection-mode {
        type enumeration {
          enum "async-with-echo" {
            value 1;
            description
              "Async with echo.";
          }
          enum "async-without-echo" {
            value 2;
            description
              "Async without echo.";
          }
          enum "demand-with-echo" {
            value 3;
            description
              "Demand with echo.";
          }
          enum "demand-without-echo" {
            value 4;
            description
              "Demand without echo.";
          }
        }
        description
          "Detection mode.";
      }
      leaf negotiated-tx-interval {
        type uint32;
        units "microseconds";
        description
          "Negotiated transmit interval.";
      }
      leaf negotiated-rx-interval {
        type uint32;
        units "microseconds";
        description
          "Negotiated receive interval.";
      }
      leaf detection-time {
        type uint32;
        units "microseconds";
        description
          "Detection time.";
      }
    }
    container session-statistics {
      description
        "BFD per-session statistics.";
      leaf last-down-time {
        type string;
        description
          "Time and date of last time this session went down.(HH:MM:SS)";
      }
      leaf last-up-time {
        type string;
        description
          "Time and date of last time this session went up.(HH:MM:SS)";
      }
      leaf up-count {
        type yang:counter32;
        description
          "The number of times this session has transitioned in the
           down state.";
      }
      leaf receive-packet-count {
        type yang:counter64;
        description
          "Count of received packets in this session. This includes
           valid and invalid received packets.";
      }
      leaf send-packet-count {
        type yang:counter64;
        description
          "Count of sent packets in this session.";
      }
    }
  }

  grouping live_ncs_bfd-client-info {
    description
      "BFD client info per session.";
    leaf-list client-info {
      type identityref {
        base bfd-client;
      }
      description
        "BFD Client list.";
    }
  }

  grouping live_ncs_session-statistics-summary {
    description
      "Grouping for session statistics summary.";
    leaf number-of-sessions {
      type yang:gauge32;
      description
        "Number of BFD sessions.";
    }
    leaf number-of-sessions-up {
      type yang:gauge32;
      description
        "Number of BFD sessions currently in up state (as defined
         in RFC 5880).";
    }
    leaf number-of-sessions-down {
      type yang:gauge32;
      description
        "Number of BFD sessions currently in down or init state
         but not admin-down (as defined in RFC 5880).";
    }
    leaf number-of-sessions-admin-down {
      type yang:gauge32;
      description
        "Number of BFD sessions currently in admin-down state (as
         defined in RFC 5880).";
    }
  }

  grouping base-cfg-parms {
    description
      "BFD grouping for base config parameters.";
    leaf local-multiplier {
      type multiplier;
      default "3";
      description
        "Multiplier transmitted by local system.";
    }
    leaf desired-min-tx-interval {
      type intervals;
      units "microseconds";
      default "100000";
      description
        "Desired minimum transmit interval of control packets in microseconds.";
    }
    leaf required-min-rx-interval {
      type intervals;
      units "microseconds";
      default "100000";
      description
        "Required minimum receive interval of control packets in microseconds.";
    }
    leaf accelerate {
      tailf:display-when "not(../ncs:module) or boolean(/ncs:devices/ncs:device[ncs:name=current()/../ncs:name]/capability/feature='accelerated-bfd')";
      type boolean;
      default "false";
      description
        "If enabled, BFD will run in an accelerated mode (for example, in hardware).";
    }
    leaf statistics-collection {
      when "../accelerate = 'true'" {
        tailf:xpath-root 3;
      }
      tailf:display-when "not(../ncs:module) or boolean(/ncs:devices/ncs:device[ncs:name=current()/../ncs:name]/capability/feature='accelerated-bfd')";
      type enumeration {
        enum "on" {
          value 0;
          description
            "Statistics-collection will be on for accelerated BFD session";
        }
        enum "off" {
          value 1;
          description
            "Statistics-collection will be off for accelerated BFD session";
        }
      }
      default "off";
      description
        "Determines whether statistics collection will be turned on or off for accelerated BFD session.";
    }
  }

  grouping client-cfg-parms {
    description
      "BFD grouping for configuration parameters
       used by clients of BFD, e.g. IGP or MPLS.";
    leaf enable {
      type boolean;
      default "false";
      description
        "Enable BFD.";
    }
  }

  grouping bgp-client-cfg-parms {
    description
      "BFD grouping for configuration parameters for BGP";
    leaf enable {
      type boolean;
      default "false";
      description
        "Enable BFD for BGP.";
    }
    leaf multihop {
      type boolean;
      default "false";
      when "../enable= 'true'" {
        tailf:xpath-root 3;
      }
      description
        "Configure multihop IP BFD for BGP.";
    }
  }

  grouping common-cfg-parms {
    description
      "BFD grouping for common configuration parameters.";
    uses base-cfg-parms;
    leaf admin-down {
      type boolean;
      default "false";
      description
        "Is the BFD session administratively down.";
    }
  }

  grouping all-session {
    description
      "BFD session operational information";
    leaf path-type {
      type identityref {
        base path-type;
      }
      description
        "BFD path type, this indicates the path type that BFD is
         running on.";
    }
    leaf ip-encapsulation {
      type boolean;
      description
        "Whether BFD encapsulation uses IP.";
    }
    leaf local-discriminator {
      type discriminator;
      description
        "Local discriminator used to uniquely identify the BFD session.";
    }
    leaf remote-discriminator {
      type discriminator;
      description
        "Descriminator chosen by the remote system.";
    }
    leaf source-port {
      when "../ip-encapsulation = 'true'" {
        tailf:xpath-root 3;
        description
          "Source UDP port valid only when IP encapsulation is used.";
      }
      type inet:port-number;
      description
        "Source UDP port";
    }
    leaf dest-port {
      when "../ip-encapsulation = 'true'" {
        tailf:xpath-root 3;
        description
          "Destination UDP port valid only when IP encapsulation is used.";
      }
      type inet:port-number;
      description
        "Destination UDP port.";
    }
    container session-running {
      description
        "BFD session running information.";
      leaf session-index {
        type uint32;
        description
          "An index used to uniquely identify BFD sessions.";
      }
      leaf local-state {
        type state;
        description
          "Local state of the BFD session.";
      }
      leaf remote-state {
        type state;
        description
          "Remote state of the BFD session.";
      }
      leaf local-diagnostic {
        type iana-bfd-types:diagnostic;
        description
          "Local diagnostic.";
      }
      leaf detection-mode {
        type enumeration {
          enum "async-with-echo" {
            value 1;
            description
              "Async with echo.";
          }
          enum "async-without-echo" {
            value 2;
            description
              "Async without echo.";
          }
          enum "demand-with-echo" {
            value 3;
            description
              "Demand with echo.";
          }
          enum "demand-without-echo" {
            value 4;
            description
              "Demand without echo.";
          }
        }
        description
          "Detection mode.";
      }
      leaf negotiated-tx-interval {
        type uint32;
        units "microseconds";
        description
          "Negotiated transmit interval.";
      }
      leaf negotiated-rx-interval {
        type uint32;
        units "microseconds";
        description
          "Negotiated receive interval.";
      }
      leaf detection-time {
        type uint32;
        units "microseconds";
        description
          "Detection time.";
      }
    }
    container session-statistics {
      description
        "BFD per-session statistics.";
      leaf last-down-time {
        type string;
        description
          "Time and date of last time this session went down.(HH:MM:SS)";
      }
      leaf last-up-time {
        type string;
        description
          "Time and date of last time this session went up.(HH:MM:SS)";
      }
      leaf up-count {
        type yang:counter32;
        description
          "The number of times this session has transitioned in the
           down state.";
      }
      leaf receive-packet-count {
        type yang:counter64;
        description
          "Count of received packets in this session. This includes
           valid and invalid received packets.";
      }
      leaf send-packet-count {
        type yang:counter64;
        description
          "Count of sent packets in this session.";
      }
    }
  }

  grouping bfd-client-info {
    description
      "BFD client info per session.";
    leaf-list client-info {
      type identityref {
        base bfd-client;
      }
      description
        "BFD Client list.";
    }
  }

  grouping session-statistics-summary {
    description
      "Grouping for session statistics summary.";
    leaf number-of-sessions {
      type yang:gauge32;
      description
        "Number of BFD sessions.";
    }
    leaf number-of-sessions-up {
      type yang:gauge32;
      description
        "Number of BFD sessions currently in up state (as defined
         in RFC 5880).";
    }
    leaf number-of-sessions-down {
      type yang:gauge32;
      description
        "Number of BFD sessions currently in down or init state
         but not admin-down (as defined in RFC 5880).";
    }
    leaf number-of-sessions-admin-down {
      type yang:gauge32;
      description
        "Number of BFD sessions currently in admin-down state (as
         defined in RFC 5880).";
    }
  }

  identity bfd-client-bgp {
    base bfd-client;
    description
      "BGP as client.";
  }

  identity bfd-client-ospf {
    base bfd-client;
    description
      "IGP OSPF as client.";
  }

  identity bfd-client-isis {
    base bfd-client;
    description
      "IGP ISIS as client.";
  }

  identity bfd-client-cli {
    base bfd-client;
    description
      "BFD CLI as client.";
  }

  identity bfd-client {
    description
      "Client types for BFD sessions.";
  }

  identity encap-ip {
    base encap-type;
    description
      "BFD with IP encapsulation.";
  }

  identity encap-type {
    description
      "Base identity for BFD encapsulation type.";
  }

  identity path-ip-mh {
    base path-type;
    description
      "BFD on IP multihop paths.";
    reference
      "RFC 5883: Bidirectional Forwarding Detection (BFD) for
       Multihop Paths.";
  }

  identity path-ip-sh {
    base path-type;
    description
      "BFD on IP single hop.";
    reference
      "RFC 5881: Bidirectional Forwarding Detection (BFD)
       for IPv4 and IPv6 (Single Hop).";
  }

  identity path-type {
    description
      "Base identity for BFD path type. The path type indicates
       the type of path on which BFD is running.";
  }

  identity bfdv1 {
    description
      "BFD protocol version 1.";
    reference "RFC 5880: Bidirectional Forwarding Detection (BFD).";
  }

  feature accelerated-bfd {
    description
      "Support for accelerated BFD.";
  }
}
