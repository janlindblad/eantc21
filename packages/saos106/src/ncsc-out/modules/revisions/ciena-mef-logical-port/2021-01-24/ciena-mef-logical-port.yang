module ciena-mef-logical-port {
  // Generated by yanger -t ncs
  tailf:mount-id "saos106-nc-1.0:saos106-nc-1.0";
  tailf:ncs-device-type "netconf";

  namespace "urn:ciena:params:xml:ns:yang:ciena-pn::ciena-mef-logical-port";
  prefix mef-logical-port;

  import openconfig-interfaces {
    prefix oc-if;
  }
  import ietf-yang-types {
    prefix yt;
  }
  import ciena-mef-frame-to-cos-map {
    prefix ftc;
  }
  import ciena-mef-cos-to-frame-map {
    prefix ctf;
  }
  import ciena-mef-meter-profile {
    prefix meter;
  }
  import ciena-mef-flood-containment-profile {
    prefix mef-fc;
  }
  import ciena-mef-pfg-profile {
    prefix mef-pfg;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
                 U.S.A.
     Phone:   +1 800-921-1144
     Fax:     +1 410-694-5750";
  description
    "This YANG module defines Ciena's management data definition for the
     management of a Logical Port.";

  revision 2021-01-24 {
    description
      "Added description for leaf frame-to-cos-map-policy";
    reference
      "RFC 6020: YANG - A Data Modeling Language for
       the Network Configuration Protocol (NETCONF).
       No specific reference; standard not available.";
  }
  revision 2021-01-04 {
    description
      "Added cfm-up-mep-frame-rx leaf in logical-ports container";
    reference
      "RFC 6020: YANG - A Data Modeling Language for
       the Network Configuration Protocol (NETCONF).
       No specific reference; standard not available.";
  }
  revision 2019-10-07 {
    description
      "Logical port events are now part of a list";
    reference
      "RFC 6020: YANG - A Data Modeling Language for
       the Network Configuration Protocol (NETCONF).
       No specific reference; standard not available.";
  }
  revision 2019-09-13 {
    description
      "Removed ingress-cos-to-queue-map leaf from logical-ports container.";
    reference
      "RFC 6020: YANG - A Data Modeling Language for
       the Network Configuration Protocol (NETCONF).
       No specific reference; standard not available.";
  }
  revision 2018-01-09 {
    description
      "10.0 Version.";
    reference
      "RFC 6020: YANG - A Data Modeling Language for
       the Network Configuration Protocol (NETCONF).
       No specific reference; standard not available.";
  }

  typedef ncs_template_logical-port-ref {
    type string;
    description
      "This type is used by the data models that needs to reference
       configured logical ports.";
  }

  typedef ncs_template_lp-admin-state {
    type string;
  }

  typedef ncs_template_lp-oper-state {
    type string;
  }

  typedef ncs_template_logical-port-event-type {
    type string;
    description
      "A generic event type describing the type of events/notifications triggered by logical-port.";
  }

  typedef ncs_rpc_notif_logical-port-ref {
    type string;
    description
      "This type is used by the data models that needs to reference
       configured logical ports.";
  }

  typedef ncs_rpc_notif_lp-admin-state {
    type enumeration {
      enum "disable";
      enum "enable";
    }
  }

  typedef ncs_rpc_notif_lp-oper-state {
    type enumeration {
      enum "up";
      enum "down";
    }
  }

  typedef ncs_rpc_notif_logical-port-event-type {
    type enumeration {
      enum "operational-state" {
        description
          "Logical Port operational state change (link state, error state).";
      }
      enum "any" {
        description
          "Any of the events in this enum";
      }
    }
    description
      "A generic event type describing the type of events/notifications triggered by logical-port.";
  }

  typedef live_ncs_logical-port-ref {
    type leafref {
      path "/ncs:devices/ncs:device/ncs:live-status/mef-logical-port:logical-ports/mef-logical-port:logical-port/mef-logical-port:name" {
        tailf:xpath-root 3;
      }
    }
    description
      "This type is used by the data models that needs to reference
       configured logical ports.";
  }

  typedef live_ncs_lp-admin-state {
    type enumeration {
      enum "disable";
      enum "enable";
    }
  }

  typedef live_ncs_lp-oper-state {
    type enumeration {
      enum "up";
      enum "down";
    }
  }

  typedef live_ncs_logical-port-event-type {
    type enumeration {
      enum "operational-state" {
        description
          "Logical Port operational state change (link state, error state).";
      }
      enum "any" {
        description
          "Any of the events in this enum";
      }
    }
    description
      "A generic event type describing the type of events/notifications triggered by logical-port.";
  }

  typedef logical-port-ref {
    type leafref {
      path "/ncs:devices/ncs:device/ncs:config/mef-logical-port:logical-ports/mef-logical-port:logical-port/mef-logical-port:name" {
        tailf:xpath-root 3;
      }
    }
    description
      "This type is used by the data models that needs to reference
       configured logical ports.";
  }

  typedef lp-admin-state {
    type enumeration {
      enum "disable";
      enum "enable";
    }
  }

  typedef lp-oper-state {
    type enumeration {
      enum "up";
      enum "down";
    }
  }

  typedef logical-port-event-type {
    type enumeration {
      enum "operational-state" {
        description
          "Logical Port operational state change (link state, error state).";
      }
      enum "any" {
        description
          "Any of the events in this enum";
      }
    }
    description
      "A generic event type describing the type of events/notifications triggered by logical-port.";
  }

  grouping ncs_template_pfg-config {
    leaf pfg-profile {
      type mef-pfg:ncs_template_pfg-profile-ref;
      description
        "Reference to a Private Forwarding Group Profile.";
    }
    choice traffic-type {
      case all {
        leaf pfg-group {
          type mef-pfg:ncs_template_pfg-group-enum;
          description
            "The Private-Forwarding-Group that all traffic ingressing a logical-port belongs to for the scope of a
             Private-Forwarding-Group-Profile.";
        }
      }
      case subset {
        leaf broadcast-pfg-group {
          type mef-pfg:ncs_template_pfg-group-enum;
          description
            "The Private-Forwarding-Group that the broadcast traffic ingressing a logical-port belongs to for the scope of a
             Private-Forwarding-Group-Profile.";
        }
        leaf unknown-unicast-pfg-group {
          type mef-pfg:ncs_template_pfg-group-enum;
          description
            "The Private-Forwarding-Group that the unknown-unicast traffic ingressing a logical-port belongs to for the scope of a
             Private-Forwarding-Group-Profile.";
        }
        leaf unknown-multicast-pfg-group {
          type mef-pfg:ncs_template_pfg-group-enum;
          description
            "The Private-Forwarding-Group that the unknown-multicast traffic ingressing a logical-port belongs to for the scope of a
             Private-Forwarding-Group-Profile.";
        }
        leaf known-multicast-pfg-group {
          type mef-pfg:ncs_template_pfg-group-enum;
          description
            "The Private-Forwarding-Group that the known-multicast traffic ingressing a logical-port belongs to for the scope of a
             Private-Forwarding-Group-Profile.";
        }
        leaf known-unicast-pfg-group {
          type mef-pfg:ncs_template_pfg-group-enum;
          description
            "The Private-Forwarding-Group that the known-unicast traffic ingressing a logical-port belongs to for the scope of a
             Private-Forwarding-Group-Profile.";
        }
      }
    }
  }

  grouping ncs_rpc_notif_pfg-config {
    leaf pfg-profile {
      type mef-pfg:ncs_rpc_notif_pfg-profile-ref;
      description
        "Reference to a Private Forwarding Group Profile.";
    }
    choice traffic-type {
      case all {
        leaf pfg-group {
          type mef-pfg:ncs_rpc_notif_pfg-group-enum;
          description
            "The Private-Forwarding-Group that all traffic ingressing a logical-port belongs to for the scope of a
             Private-Forwarding-Group-Profile.";
        }
      }
      case subset {
        leaf broadcast-pfg-group {
          type mef-pfg:ncs_rpc_notif_pfg-group-enum;
          description
            "The Private-Forwarding-Group that the broadcast traffic ingressing a logical-port belongs to for the scope of a
             Private-Forwarding-Group-Profile.";
        }
        leaf unknown-unicast-pfg-group {
          type mef-pfg:ncs_rpc_notif_pfg-group-enum;
          description
            "The Private-Forwarding-Group that the unknown-unicast traffic ingressing a logical-port belongs to for the scope of a
             Private-Forwarding-Group-Profile.";
        }
        leaf unknown-multicast-pfg-group {
          type mef-pfg:ncs_rpc_notif_pfg-group-enum;
          description
            "The Private-Forwarding-Group that the unknown-multicast traffic ingressing a logical-port belongs to for the scope of a
             Private-Forwarding-Group-Profile.";
        }
        leaf known-multicast-pfg-group {
          type mef-pfg:ncs_rpc_notif_pfg-group-enum;
          description
            "The Private-Forwarding-Group that the known-multicast traffic ingressing a logical-port belongs to for the scope of a
             Private-Forwarding-Group-Profile.";
        }
        leaf known-unicast-pfg-group {
          type mef-pfg:ncs_rpc_notif_pfg-group-enum;
          description
            "The Private-Forwarding-Group that the known-unicast traffic ingressing a logical-port belongs to for the scope of a
             Private-Forwarding-Group-Profile.";
        }
      }
    }
  }

  grouping live_ncs_pfg-config {
    leaf pfg-profile {
      type mef-pfg:live_ncs_pfg-profile-ref;
      description
        "Reference to a Private Forwarding Group Profile.";
    }
    choice traffic-type {
      case all {
        leaf pfg-group {
          type mef-pfg:live_ncs_pfg-group-enum;
          description
            "The Private-Forwarding-Group that all traffic ingressing a logical-port belongs to for the scope of a
             Private-Forwarding-Group-Profile.";
        }
      }
      case subset {
        leaf broadcast-pfg-group {
          type mef-pfg:live_ncs_pfg-group-enum;
          description
            "The Private-Forwarding-Group that the broadcast traffic ingressing a logical-port belongs to for the scope of a
             Private-Forwarding-Group-Profile.";
        }
        leaf unknown-unicast-pfg-group {
          type mef-pfg:live_ncs_pfg-group-enum;
          description
            "The Private-Forwarding-Group that the unknown-unicast traffic ingressing a logical-port belongs to for the scope of a
             Private-Forwarding-Group-Profile.";
        }
        leaf unknown-multicast-pfg-group {
          type mef-pfg:live_ncs_pfg-group-enum;
          description
            "The Private-Forwarding-Group that the unknown-multicast traffic ingressing a logical-port belongs to for the scope of a
             Private-Forwarding-Group-Profile.";
        }
        leaf known-multicast-pfg-group {
          type mef-pfg:live_ncs_pfg-group-enum;
          description
            "The Private-Forwarding-Group that the known-multicast traffic ingressing a logical-port belongs to for the scope of a
             Private-Forwarding-Group-Profile.";
        }
        leaf known-unicast-pfg-group {
          type mef-pfg:live_ncs_pfg-group-enum;
          description
            "The Private-Forwarding-Group that the known-unicast traffic ingressing a logical-port belongs to for the scope of a
             Private-Forwarding-Group-Profile.";
        }
      }
    }
  }

  grouping pfg-config {
    leaf pfg-profile {
      type mef-pfg:pfg-profile-ref;
      description
        "Reference to a Private Forwarding Group Profile.";
    }
    choice traffic-type {
      case all {
        leaf pfg-group {
          type mef-pfg:pfg-group-enum;
          description
            "The Private-Forwarding-Group that all traffic ingressing a logical-port belongs to for the scope of a
             Private-Forwarding-Group-Profile.";
        }
      }
      case subset {
        leaf broadcast-pfg-group {
          type mef-pfg:pfg-group-enum;
          description
            "The Private-Forwarding-Group that the broadcast traffic ingressing a logical-port belongs to for the scope of a
             Private-Forwarding-Group-Profile.";
        }
        leaf unknown-unicast-pfg-group {
          type mef-pfg:pfg-group-enum;
          description
            "The Private-Forwarding-Group that the unknown-unicast traffic ingressing a logical-port belongs to for the scope of a
             Private-Forwarding-Group-Profile.";
        }
        leaf unknown-multicast-pfg-group {
          type mef-pfg:pfg-group-enum;
          description
            "The Private-Forwarding-Group that the unknown-multicast traffic ingressing a logical-port belongs to for the scope of a
             Private-Forwarding-Group-Profile.";
        }
        leaf known-multicast-pfg-group {
          type mef-pfg:pfg-group-enum;
          description
            "The Private-Forwarding-Group that the known-multicast traffic ingressing a logical-port belongs to for the scope of a
             Private-Forwarding-Group-Profile.";
        }
        leaf known-unicast-pfg-group {
          type mef-pfg:pfg-group-enum;
          description
            "The Private-Forwarding-Group that the known-unicast traffic ingressing a logical-port belongs to for the scope of a
             Private-Forwarding-Group-Profile.";
        }
      }
    }
  }

  augment "/ncs:devices/ncs:device/ncs:rpc" {
    container rpc-logical-ports-clear-statistics {
      tailf:ncs-device-type "netconf";
      tailf:display-when "not(../../ncs:module) or ../../ncs:module[ncs:name='ciena-mef-logical-port']";
      tailf:action logical-ports-clear-statistics {
        tailf:actionpoint ncsproxy {
          tailf:internal;
        }
        description
          "An RPC operation to clear the statistics for one or all Logical-Ports.";
        input {
          choice clear-scope {
            case logical-port {
              leaf logical-port {
                type mef-logical-port:ncs_rpc_notif_logical-port-ref;
              }
              description
                "Clear stats for this logical-port.";
            }
            case all {
              leaf all {
                type empty;
              }
              description
                "Clear stats for all logical-ports.";
            }
          }
        }
        output {
          leaf status {
            type string;
            description
              "Status of the clear statistics operation.";
          }
        }
      }
    }
  }
  augment "/ncs:devices/ncs:device-group/ncs:ned-id/ncs:rpc" {
    container rpc-logical-ports-clear-statistics {
      tailf:ncs-device-type "netconf";
      tailf:display-when "/ncs:devices/ncs:device[ncs:name=current()/../../../ncs:member]/ncs:module[ncs:name='ciena-mef-logical-port']";
      tailf:action logical-ports-clear-statistics {
        tailf:actionpoint ncsproxy {
          tailf:internal;
        }
        description
          "An RPC operation to clear the statistics for one or all Logical-Ports.";
        input {
          choice clear-scope {
            case logical-port {
              leaf logical-port {
                type mef-logical-port:ncs_rpc_notif_logical-port-ref;
              }
              description
                "Clear stats for this logical-port.";
            }
            case all {
              leaf all {
                type empty;
              }
              description
                "Clear stats for all logical-ports.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:netconf-notifications/ncs:received-notifications/ncs:notification/ncs:data" {
    container logical-port-events {
      presence "";
      config false;
      list logical-port-event {
        leaf logical-port-name {
          type string;
          description
            "The logical-port-name for the notification. '*' means any logical-port-name";
        }
        list event-list {
          leaf logical-port-event-type {
            type string;
            description
              "The logical-port event-type for the notification. 'any' means any event-type";
          }
        }
        leaf oper-state {
          type string;
          description
            "logical-port operational state change (link state)";
        }
      }
    }
  }
  augment "/ncs:devices/ncs:device/ncs:config" {
    container logical-ports {
      tailf:ncs-device-type "netconf";
      tailf:display-when "not(../../ncs:module) or ../../ncs:module[ncs:name='ciena-mef-logical-port']";
      description
        "List of logical-ports.";
      list logical-port {
        key "name";
        leaf name {
          type string;
          description
            "This object indicates the identifier and is a
             text string that is used to identify a logical port.
             Unique string values are chosen to uniquely identify
             the port.

             Octet values of 0x00 through 0x1f are illegal.

             MEF 26.1 restricts the maximum size identifiers to
             45 octets.";
          reference "[MEF 7.2] 6.2.1.4";
        }
        leaf admin-state {
          type lp-admin-state;
          default "enable";
          description
            "Enable or disable this logical-port";
        }
        leaf binding {
          type leafref {
            path "/ncs:devices/ncs:device/ncs:config/oc-if:interfaces/oc-if:interface/oc-if:name" {
              tailf:xpath-root 3;
            }
          }
          description
            "Bind the logical-port to an interface.";
        }
        leaf mtu {
          type uint32 {
            range "64..9216";
          }
          default "1526";
          description
            "The size in bytes of the maximum transmission unit.";
        }
        leaf meter-profile {
          type meter:meter-ref;
          description
            "A reference to a Meter Profile.";
        }
        choice frame-to-cos-policy {
          case map {
            leaf frame-to-cos-map-policy {
              type enumeration {
                enum "outer-tag" {
                  description
                    "Map to internal cos and color based on outer vlan tag of vlan-tagged frame (one or more tags present).
                     Any L2 frame which does not have at least 1 vlan tag is considered non-conforming from frame-to-cos map perspective,
                     and the resolution to an internal cos and color is platform specific for non-conforming frames.";
                }
                enum "inner-tag" {
                  description
                    "Map to internal cos and color based on inner vlan tag of vlan-tagged frame (at least 2 tags present).
                     Any L2 frame which does not have at least 2 vlan tags is considered non-conforming from frame-to-cos map perspective,
                     and the resolution to an internal cos and color is platform specific for non-conforming frames.";
                }
                enum "dscp" {
                  description
                    "Map to internal cos and color based on dscp field of IP of L2-frame (if IP present).
                     Any L2 frame which is non-IP (after vlan tags) is considered non-conforming from frame-to-cos map perspective,
                     and the resolution to an internal cos and color is platform specific for non-conforming frames.";
                }
                enum "outer-mpls-tc" {
                  description
                    "Map to internal cos and color based on mpls-tc of outer MPLS Label of L2-frame (if MPLS Label present).
                     Any L2 frame which is non-MPLS (after vlan tags) is considered non-conforming from frame-to-cos map perspective,
                     and the resolution to an internal cos and color is platform specific for non-conforming frames.";
                }
              }
            }
            leaf frame-to-cos-map {
              type ftc:frame-to-cos-ref;
            }
          }
          case fixed {
            leaf fixed-cos {
              type uint8 {
                range "0..63";
              }
              description
                "The internal-COS value to use for an incoming frame when there is no mapping through a frame-to-cos-map.";
            }
            leaf fixed-color {
              type enumeration {
                enum "green";
                enum "yellow";
                enum "red";
              }
              description
                "The internal-color value to use for an incoming frame when there is no mapping through a frame-to-cos-map.";
            }
          }
        }
        leaf cos-to-frame-map {
          type ctf:cos-to-frame-ref;
        }
        leaf flood-containment-profile {
          type mef-fc:flood-containment-profile-ref;
        }
        leaf description {
          type string;
          description
            "List of logical ports.";
        }
        leaf-list outer-tpid {
          type enumeration {
            enum "tpid-8100";
            enum "tpid-88a8";
            enum "tpid-9100";
          }
          description
            "A list of valid outer-vlan-tag TPIDs for the port.";
        }
        leaf-list inner-tpid {
          type enumeration {
            enum "tpid-8100";
            enum "tpid-88a8";
            enum "tpid-9100";
          }
          description
            "A list of valid inner-vlan-tag TPIDs for the port.";
        }
        leaf egress-qos {
          type enumeration {
            enum "off";
            enum "on";
          }
        }
        leaf cfm-up-mep-frame-rx {
          tailf:display-when "not(../../../ncs:module) or boolean(/ncs:devices/ncs:device[ncs:name=current()/../../../ncs:name]/capability/feature='cfm-up-mep-frame-rx')";
          type enumeration {
            enum "always-on" {
              description
                "Enable cfm up mep frame rx even when logical port operational status is down";
            }
            enum "logical-port-oper-up-only" {
              description
                "Disable cfm up mep frame rx when logical port operational status is down";
            }
          }
          default "always-on";
          description
            "Specifies if cfm up mep frame rx is enabled or disabled when logical port operational status is down";
        }
        uses pfg-config;
        // NCS drop config false leaf 'logical-port-event-type'
      }
    }
    // NCS drop config false container 'logical-port-oper-status'
  }
  augment "/ncs:devices/ncs:device/ncs:live-status" {
    container logical-ports {
      tailf:ncs-device-type "netconf";
      tailf:display-when "not(../../ncs:module) or ../../ncs:module[ncs:name='ciena-mef-logical-port'] or (../../ncs:live-status-protocol[not(ncs:capability)]) or (../../ncs:live-status-protocol/ncs:capability/ncs:module[.='ciena-mef-logical-port'])";
      description
        "List of logical-ports.";
      list logical-port {
        key "name";
        leaf name {
          type string;
          description
            "This object indicates the identifier and is a
             text string that is used to identify a logical port.
             Unique string values are chosen to uniquely identify
             the port.

             Octet values of 0x00 through 0x1f are illegal.

             MEF 26.1 restricts the maximum size identifiers to
             45 octets.";
          reference "[MEF 7.2] 6.2.1.4";
        }
        leaf admin-state {
          type live_ncs_lp-admin-state;
          // NCS drop default statement
          description
            "Enable or disable this logical-port";
        }
        leaf binding {
          type leafref {
            path "/ncs:devices/ncs:device/ncs:live-status/oc-if:interfaces/oc-if:interface/oc-if:name" {
              tailf:xpath-root 3;
            }
          }
          description
            "Bind the logical-port to an interface.";
        }
        leaf mtu {
          type uint32 {
            range "64..9216";
          }
          // NCS drop default statement
          description
            "The size in bytes of the maximum transmission unit.";
        }
        leaf meter-profile {
          type meter:live_ncs_meter-ref;
          description
            "A reference to a Meter Profile.";
        }
        choice frame-to-cos-policy {
          case map {
            leaf frame-to-cos-map-policy {
              type enumeration {
                enum "outer-tag" {
                  description
                    "Map to internal cos and color based on outer vlan tag of vlan-tagged frame (one or more tags present).
                     Any L2 frame which does not have at least 1 vlan tag is considered non-conforming from frame-to-cos map perspective,
                     and the resolution to an internal cos and color is platform specific for non-conforming frames.";
                }
                enum "inner-tag" {
                  description
                    "Map to internal cos and color based on inner vlan tag of vlan-tagged frame (at least 2 tags present).
                     Any L2 frame which does not have at least 2 vlan tags is considered non-conforming from frame-to-cos map perspective,
                     and the resolution to an internal cos and color is platform specific for non-conforming frames.";
                }
                enum "dscp" {
                  description
                    "Map to internal cos and color based on dscp field of IP of L2-frame (if IP present).
                     Any L2 frame which is non-IP (after vlan tags) is considered non-conforming from frame-to-cos map perspective,
                     and the resolution to an internal cos and color is platform specific for non-conforming frames.";
                }
                enum "outer-mpls-tc" {
                  description
                    "Map to internal cos and color based on mpls-tc of outer MPLS Label of L2-frame (if MPLS Label present).
                     Any L2 frame which is non-MPLS (after vlan tags) is considered non-conforming from frame-to-cos map perspective,
                     and the resolution to an internal cos and color is platform specific for non-conforming frames.";
                }
              }
            }
            leaf frame-to-cos-map {
              type ftc:live_ncs_frame-to-cos-ref;
            }
          }
          case fixed {
            leaf fixed-cos {
              type uint8 {
                range "0..63";
              }
              description
                "The internal-COS value to use for an incoming frame when there is no mapping through a frame-to-cos-map.";
            }
            leaf fixed-color {
              type enumeration {
                enum "green";
                enum "yellow";
                enum "red";
              }
              description
                "The internal-color value to use for an incoming frame when there is no mapping through a frame-to-cos-map.";
            }
          }
        }
        leaf cos-to-frame-map {
          type ctf:live_ncs_cos-to-frame-ref;
        }
        leaf flood-containment-profile {
          type mef-fc:live_ncs_flood-containment-profile-ref;
        }
        leaf description {
          type string;
          description
            "List of logical ports.";
        }
        leaf-list outer-tpid {
          type enumeration {
            enum "tpid-8100";
            enum "tpid-88a8";
            enum "tpid-9100";
          }
          description
            "A list of valid outer-vlan-tag TPIDs for the port.";
        }
        leaf-list inner-tpid {
          type enumeration {
            enum "tpid-8100";
            enum "tpid-88a8";
            enum "tpid-9100";
          }
          description
            "A list of valid inner-vlan-tag TPIDs for the port.";
        }
        leaf egress-qos {
          type enumeration {
            enum "off";
            enum "on";
          }
        }
        leaf cfm-up-mep-frame-rx {
          // NCS drop if-feature statement
          type enumeration {
            enum "always-on" {
              description
                "Enable cfm up mep frame rx even when logical port operational status is down";
            }
            enum "logical-port-oper-up-only" {
              description
                "Disable cfm up mep frame rx when logical port operational status is down";
            }
          }
          // NCS drop default statement
          description
            "Specifies if cfm up mep frame rx is enabled or disabled when logical port operational status is down";
        }
        uses live_ncs_pfg-config;
        leaf logical-port-event-type {
          type live_ncs_logical-port-event-type;
          description
            "Description of the logical port interface event types";
        }
      }
    }
    container logical-port-oper-status {
      tailf:ncs-device-type "netconf";
      tailf:display-when "not(../../ncs:module) or ../../ncs:module[ncs:name='ciena-mef-logical-port'] or (../../ncs:live-status-protocol[not(ncs:capability)]) or (../../ncs:live-status-protocol/ncs:capability/ncs:module[.='ciena-mef-logical-port'])";
      list logical-port-status {
        key "name";
        leaf name {
          type string;
        }
        leaf index {
          type uint32;
        }
        leaf mac-address {
          type yt:mac-address;
        }
        leaf oper-state {
          type live_ncs_lp-oper-state;
          description
            "Operational state of this logical port";
        }
      }
    }
  }
  augment "/ncs:devices/ncs:template/ncs:ned-id/ncs:config" {
    container logical-ports {
      description
        "List of logical-ports.";
      list logical-port {
        // NCS patched for predictable order
        ordered-by user;
        key "name";
        leaf name {
          type string;
          description
            "This object indicates the identifier and is a
             text string that is used to identify a logical port.
             Unique string values are chosen to uniquely identify
             the port.

             Octet values of 0x00 through 0x1f are illegal.

             MEF 26.1 restricts the maximum size identifiers to
             45 octets.";
          reference "[MEF 7.2] 6.2.1.4";
        }
        leaf admin-state {
          type ncs_template_lp-admin-state;
          // NCS drop default statement
          description
            "Enable or disable this logical-port";
        }
        leaf binding {
          type string;
          description
            "Bind the logical-port to an interface.";
        }
        leaf mtu {
          type string;
          // NCS drop default statement
          description
            "The size in bytes of the maximum transmission unit.";
        }
        leaf meter-profile {
          type meter:ncs_template_meter-ref;
          description
            "A reference to a Meter Profile.";
        }
        choice frame-to-cos-policy {
          case map {
            leaf frame-to-cos-map-policy {
              type string;
            }
            leaf frame-to-cos-map {
              type ftc:ncs_template_frame-to-cos-ref;
            }
          }
          case fixed {
            leaf fixed-cos {
              type string;
              description
                "The internal-COS value to use for an incoming frame when there is no mapping through a frame-to-cos-map.";
            }
            leaf fixed-color {
              type string;
              description
                "The internal-color value to use for an incoming frame when there is no mapping through a frame-to-cos-map.";
            }
          }
        }
        leaf cos-to-frame-map {
          type ctf:ncs_template_cos-to-frame-ref;
        }
        leaf flood-containment-profile {
          type mef-fc:ncs_template_flood-containment-profile-ref;
        }
        leaf description {
          type string;
          description
            "List of logical ports.";
        }
        leaf-list outer-tpid {
          // NCS patched for predictable order
          ordered-by user;
          type string;
          description
            "A list of valid outer-vlan-tag TPIDs for the port.";
        }
        leaf-list inner-tpid {
          // NCS patched for predictable order
          ordered-by user;
          type string;
          description
            "A list of valid inner-vlan-tag TPIDs for the port.";
        }
        leaf egress-qos {
          type string;
        }
        leaf cfm-up-mep-frame-rx {
          // NCS drop if-feature statement
          type string;
          // NCS drop default statement
          description
            "Specifies if cfm up mep frame rx is enabled or disabled when logical port operational status is down";
        }
        uses ncs_template_pfg-config;
        // NCS drop config false leaf 'logical-port-event-type'
      }
    }
    // NCS drop config false container 'logical-port-oper-status'
  }

  feature cfm-up-mep-frame-rx {
    description
      "Support for cfm up mep frames rx when logical port operational status is down";
  }
}
