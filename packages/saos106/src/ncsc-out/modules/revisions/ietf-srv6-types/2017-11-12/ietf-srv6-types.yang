module ietf-srv6-types {
  // Generated by yanger -t ncs
  tailf:mount-id "saos106-nc-1.0:saos106-nc-1.0";
  tailf:ncs-device-type "netconf";

  namespace "urn:ietf:params:xml:ns:yang:ietf-srv6-types";
  prefix srv6-types;

  import ietf-inet-types {
    prefix inet;
  }
  import tailf-common {
    prefix tailf;
  }
  import tailf-ncs {
    prefix ncs;
  }

  organization
    "IETF SPRING Working Group";
  contact
    "WG Web:   <http://tools.ietf.org/wg/spring/>
     WG List:  <mailto:spring@ietf.org>

     WG Chair: Bruno Decraene
               <mailto:loa@pi.nu>

     WG Chair: Martin Vigoureux
               <mailto:rcallon@juniper.net>

     Editor:   Kamran Raza
               <mailto:skraza@cisco.com>

     Editor:   Jaganbabu Rajamanickam
               <maito:jrajaman@cisco.com>

     Editor:   Xufeng Liu
               <mailto:Xufeng_Liu@jabil.com>

     Editor:   Iftekhar Hussain
               <mailto:IHussain@infinera.com>

     Editor:   Himanshu Shah
               <mailto:hshah@ciena.com>

     Editor:   Daniel Voyer
               <mailto:daniel.voyer@bell.ca>

     Editor:   Hani Elmalky
               <mailto:hani.elmalky@ericsson.com>

     Editor:   Ahmed AbdelSalam
               <mailto:ahmed.abdelsalam@gssi.it>

    ";
  description
    "This YANG module defines the essential types for the
     management of Segment-Routing with IPv6 dataplane (SRv6).

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).";
  reference "RFC XXXX";

  revision 2017-11-12 {
    description
      "Initial revision.";
    reference "RFC XXXX: YANG Data Model for SRv6";
  }

  typedef ncs_template_srv6-end-type {
    type string;
    description
      "SRv6 End behavior types";
  }

  typedef ncs_template_srv6-transit-type {
    type string;
    description
      "SRv6 Transit behavior types";
  }

  typedef ncs_template_srv6-security-rule-type {
    type string;
    description
      "SRv6 Security rule types";
  }

  typedef ncs_template_srv6-counter-type {
    type string;
    description
      "SRv6 counter types";
  }

  typedef ncs_template_srv6-sid {
    type string;
    description
      "This type defines a SID value in SRv6";
  }

  typedef ncs_template_srv6-func-opcode {
    type string;
    description
      "This is a typedef for SID FUNC's opcode type";
  }

  typedef ncs_template_srv6-func-opcode-reserved {
    type string;
    description
      "This is a typedef for SID FUNC's reserved opcode type";
  }

  typedef ncs_template_srv6-func-opcode-unreserved {
    type string;
    description
      "This is a typedef for SID FUNC's allocatable (unreserved) opcode type";
  }

  typedef ncs_template_srv6-func-opcode-reserved-type {
    type string;
    description
      "SRv6 SID FUNC Reserved Opcodes";
  }

  typedef ncs_template_srv6-locator-len {
    type string;
    description
      "This type defines an SRv6 locator len with range constraints";
  }

  typedef ncs_template_srv6-sid-pfxlen {
    type string;
    // NCS drop default statement
    description
      "This type defines a SID prefixlen with range constraints";
  }

  typedef ncs_template_sid-alloc-type {
    type string;
    description
      "Types of sid allocation used.";
  }

  typedef ncs_template_srv6-sid-owner-type {
    type string;
    description
      "SID Client types.";
  }

  typedef ncs_template_table-id {
    type string;
    description
      "Routing Table Id";
  }

  typedef ncs_template_srv6-status-type {
    type string;
    description
      "Status type";
  }

  typedef ncs_template_srv6-nexthop-type {
    type string;
    description
      "Forwarding Next-hop type";
  }

  typedef ncs_rpc_notif_srv6-end-type {
    type enumeration {
      enum "End" {
        value 1;
        description
          "The Endpoint function. This is the most
           basic function";
      }
      enum "End.X" {
        description
          "Endpoint with cross-connect to an array
           of layer-3 adjacencies";
      }
      enum "End.T" {
        description
          "Endpoint with specific IPv6 table lookup";
      }
      enum "End.DX2" {
        description
          "Endpoint with decapsulation and Layer-2
           cross-connect to an L2 interface";
      }
      enum "End.DX2V" {
        description
          "Endpoint with decapsulation and specific
           VLAN L2 table lookup";
      }
      enum "End.DT2U" {
        description
          "Endpoint with decapsulation and specific
           unicast MAC L2 table lookup";
      }
      enum "End.DT2M" {
        description
          "Endpoint with decapsulation and specific L2 table
           flooding";
      }
      enum "End.DX6" {
        description
          "Endpoint with decapsulation and cross-connect
           to an array of IPv6 adjacencies";
      }
      enum "End.DX4" {
        description
          "Endpoint with decapsulation and cross-connect
           to an array of IPv4 adjacencies";
      }
      enum "End.DT6" {
        description
          "Endpoint with decapsulation and specific
           IPv6 table lookup";
      }
      enum "End.DT4" {
        description
          "Endpoint with decapsulation and specific
           IPv4 table lookup";
      }
      enum "End.DT46" {
        description
          "Endpoint with decapsulation and specific IP
           (IPv4 or IPv6) table lookup";
      }
      enum "End.B6" {
        description
          "Endpoint bound to an SRv6 Policy";
      }
      enum "End.B6.Encaps" {
        description
          "This is a variation of the End.B6 behavior
           where the SRv6 Policy also includes an
           IPv6 Source Address A.";
      }
      enum "End.BM" {
        description
          "Endpoint bound to an SR-MPLS Policy";
      }
      enum "End.S" {
        description
          "Endpoint in search of a target in table TE";
      }
      enum "End.AS" {
        description
          "Service-Chaining Static proxy for inner type (Ethernet, IPv4 or IPv6)";
      }
      enum "End.AD" {
        description
          "Service-Chaining Dynamic proxy for inner type (Ethernet, IPv4 or IPv6)";
      }
      enum "End.ASM" {
        description
          "Service-Chaining Shared memory SR proxy for inner type (Ethernet, IPv4 or IPv6)";
      }
      enum "End.AM" {
        description
          "Service-Chaining Masquerading SR proxy";
      }
    }
    description
      "SRv6 End behavior types";
  }

  typedef ncs_rpc_notif_srv6-transit-type {
    type enumeration {
      enum "T" {
        value 1;
        description
          "Transit";
      }
      enum "T.Encaps" {
        description
          "T.Encaps";
      }
      enum "T.Insert" {
        description
          "T.Insert";
      }
      enum "T.Encaps.L2" {
        description
          "T.Encaps.L2";
      }
    }
    description
      "SRv6 Transit behavior types";
  }

  typedef ncs_rpc_notif_srv6-security-rule-type {
    type enumeration {
      enum "SEC1" {
        value 1;
        description
          "Security rule SEC1";
      }
      enum "SEC2" {
        description
          "Security rule SEC2";
      }
      enum "SEC3" {
        description
          "Security rule SEC3";
      }
      enum "SEC4" {
        description
          "Security rule SEC4";
      }
    }
    description
      "SRv6 Security rule types";
  }

  typedef ncs_rpc_notif_srv6-counter-type {
    type enumeration {
      enum "CNT0" {
        value 0;
        description
          "CNT0";
      }
      enum "CNT1" {
        description
          "CNT1";
      }
      enum "CNT2" {
        description
          "CNT2";
      }
    }
    description
      "SRv6 counter types";
  }

  typedef ncs_rpc_notif_srv6-sid {
    type inet:ipv6-prefix;
    description
      "This type defines a SID value in SRv6";
  }

  typedef ncs_rpc_notif_srv6-func-opcode {
    type uint32;
    description
      "This is a typedef for SID FUNC's opcode type";
  }

  typedef ncs_rpc_notif_srv6-func-opcode-reserved {
    type uint32 {
      range "1 .. 63";
    }
    description
      "This is a typedef for SID FUNC's reserved opcode type";
  }

  typedef ncs_rpc_notif_srv6-func-opcode-unreserved {
    type uint32 {
      range "64 .. max";
    }
    description
      "This is a typedef for SID FUNC's allocatable (unreserved) opcode type";
  }

  typedef ncs_rpc_notif_srv6-func-opcode-reserved-type {
    type enumeration {
      enum "invalid" {
        value 0;
        description
          "Invalid opcode";
      }
      enum "default-end-psp" {
        value 1;
        description
          "Opcode for Default End/PSP funcion";
      }
      enum "default-end-usp" {
        value 2;
        description
          "Opcode for Default End/USP funcion";
      }
    }
    description
      "SRv6 SID FUNC Reserved Opcodes";
  }

  typedef ncs_rpc_notif_srv6-locator-len {
    type uint8 {
      range "32 .. 96";
    }
    description
      "This type defines an SRv6 locator len with range constraints";
  }

  typedef ncs_rpc_notif_srv6-sid-pfxlen {
    type uint8 {
      range "33 .. 128";
    }
    default "128";
    description
      "This type defines a SID prefixlen with range constraints";
  }

  typedef ncs_rpc_notif_sid-alloc-type {
    type enumeration {
      enum "Dynamic" {
        description
          "SID allocated dynamically.";
      }
      enum "Explicit" {
        description
          "SID allocated with explicit (static) value";
      }
    }
    description
      "Types of sid allocation used.";
  }

  typedef ncs_rpc_notif_srv6-sid-owner-type {
    type enumeration {
      enum "isis" {
        value 1;
        description
          "ISIS";
      }
      enum "ospfv3" {
        description
          "OSPFv3";
      }
      enum "bgp" {
        description
          "BGP";
      }
      enum "evpn" {
        description
          "EVPN";
      }
      enum "sr-policy" {
        description
          "SR Policy";
      }
      enum "service-chain" {
        description
          "Service-Chaining";
      }
    }
    description
      "SID Client types.";
  }

  typedef ncs_rpc_notif_table-id {
    type uint32;
    description
      "Routing Table Id";
  }

  typedef ncs_rpc_notif_srv6-status-type {
    type enumeration {
      enum "up" {
        value 1;
        description
          "State is Up";
      }
      enum "down" {
        description
          "State is Down";
      }
    }
    description
      "Status type";
  }

  typedef ncs_rpc_notif_srv6-nexthop-type {
    type enumeration {
      enum "ipv4" {
        value 1;
        description
          "IPv4 next-hop";
      }
      enum "ipv6" {
        description
          "IPv6 next-hop";
      }
      enum "mpls" {
        description
          "MPLS next-hop";
      }
      enum "l2" {
        description
          "L2 next-hop";
      }
    }
    description
      "Forwarding Next-hop type";
  }

  typedef live_ncs_srv6-end-type {
    type enumeration {
      enum "End" {
        value 1;
        description
          "The Endpoint function. This is the most
           basic function";
      }
      enum "End.X" {
        description
          "Endpoint with cross-connect to an array
           of layer-3 adjacencies";
      }
      enum "End.T" {
        description
          "Endpoint with specific IPv6 table lookup";
      }
      enum "End.DX2" {
        description
          "Endpoint with decapsulation and Layer-2
           cross-connect to an L2 interface";
      }
      enum "End.DX2V" {
        description
          "Endpoint with decapsulation and specific
           VLAN L2 table lookup";
      }
      enum "End.DT2U" {
        description
          "Endpoint with decapsulation and specific
           unicast MAC L2 table lookup";
      }
      enum "End.DT2M" {
        description
          "Endpoint with decapsulation and specific L2 table
           flooding";
      }
      enum "End.DX6" {
        description
          "Endpoint with decapsulation and cross-connect
           to an array of IPv6 adjacencies";
      }
      enum "End.DX4" {
        description
          "Endpoint with decapsulation and cross-connect
           to an array of IPv4 adjacencies";
      }
      enum "End.DT6" {
        description
          "Endpoint with decapsulation and specific
           IPv6 table lookup";
      }
      enum "End.DT4" {
        description
          "Endpoint with decapsulation and specific
           IPv4 table lookup";
      }
      enum "End.DT46" {
        description
          "Endpoint with decapsulation and specific IP
           (IPv4 or IPv6) table lookup";
      }
      enum "End.B6" {
        description
          "Endpoint bound to an SRv6 Policy";
      }
      enum "End.B6.Encaps" {
        description
          "This is a variation of the End.B6 behavior
           where the SRv6 Policy also includes an
           IPv6 Source Address A.";
      }
      enum "End.BM" {
        description
          "Endpoint bound to an SR-MPLS Policy";
      }
      enum "End.S" {
        description
          "Endpoint in search of a target in table TE";
      }
      enum "End.AS" {
        description
          "Service-Chaining Static proxy for inner type (Ethernet, IPv4 or IPv6)";
      }
      enum "End.AD" {
        description
          "Service-Chaining Dynamic proxy for inner type (Ethernet, IPv4 or IPv6)";
      }
      enum "End.ASM" {
        description
          "Service-Chaining Shared memory SR proxy for inner type (Ethernet, IPv4 or IPv6)";
      }
      enum "End.AM" {
        description
          "Service-Chaining Masquerading SR proxy";
      }
    }
    description
      "SRv6 End behavior types";
  }

  typedef live_ncs_srv6-transit-type {
    type enumeration {
      enum "T" {
        value 1;
        description
          "Transit";
      }
      enum "T.Encaps" {
        description
          "T.Encaps";
      }
      enum "T.Insert" {
        description
          "T.Insert";
      }
      enum "T.Encaps.L2" {
        description
          "T.Encaps.L2";
      }
    }
    description
      "SRv6 Transit behavior types";
  }

  typedef live_ncs_srv6-security-rule-type {
    type enumeration {
      enum "SEC1" {
        value 1;
        description
          "Security rule SEC1";
      }
      enum "SEC2" {
        description
          "Security rule SEC2";
      }
      enum "SEC3" {
        description
          "Security rule SEC3";
      }
      enum "SEC4" {
        description
          "Security rule SEC4";
      }
    }
    description
      "SRv6 Security rule types";
  }

  typedef live_ncs_srv6-counter-type {
    type enumeration {
      enum "CNT0" {
        value 0;
        description
          "CNT0";
      }
      enum "CNT1" {
        description
          "CNT1";
      }
      enum "CNT2" {
        description
          "CNT2";
      }
    }
    description
      "SRv6 counter types";
  }

  typedef live_ncs_srv6-sid {
    type inet:ipv6-prefix;
    description
      "This type defines a SID value in SRv6";
  }

  typedef live_ncs_srv6-func-opcode {
    type uint32;
    description
      "This is a typedef for SID FUNC's opcode type";
  }

  typedef live_ncs_srv6-func-opcode-reserved {
    type uint32 {
      range "1 .. 63";
    }
    description
      "This is a typedef for SID FUNC's reserved opcode type";
  }

  typedef live_ncs_srv6-func-opcode-unreserved {
    type uint32 {
      range "64 .. max";
    }
    description
      "This is a typedef for SID FUNC's allocatable (unreserved) opcode type";
  }

  typedef live_ncs_srv6-func-opcode-reserved-type {
    type enumeration {
      enum "invalid" {
        value 0;
        description
          "Invalid opcode";
      }
      enum "default-end-psp" {
        value 1;
        description
          "Opcode for Default End/PSP funcion";
      }
      enum "default-end-usp" {
        value 2;
        description
          "Opcode for Default End/USP funcion";
      }
    }
    description
      "SRv6 SID FUNC Reserved Opcodes";
  }

  typedef live_ncs_srv6-locator-len {
    type uint8 {
      range "32 .. 96";
    }
    description
      "This type defines an SRv6 locator len with range constraints";
  }

  typedef live_ncs_srv6-sid-pfxlen {
    type uint8 {
      range "33 .. 128";
    }
    // NCS drop default statement
    description
      "This type defines a SID prefixlen with range constraints";
  }

  typedef live_ncs_sid-alloc-type {
    type enumeration {
      enum "Dynamic" {
        description
          "SID allocated dynamically.";
      }
      enum "Explicit" {
        description
          "SID allocated with explicit (static) value";
      }
    }
    description
      "Types of sid allocation used.";
  }

  typedef live_ncs_srv6-sid-owner-type {
    type enumeration {
      enum "isis" {
        value 1;
        description
          "ISIS";
      }
      enum "ospfv3" {
        description
          "OSPFv3";
      }
      enum "bgp" {
        description
          "BGP";
      }
      enum "evpn" {
        description
          "EVPN";
      }
      enum "sr-policy" {
        description
          "SR Policy";
      }
      enum "service-chain" {
        description
          "Service-Chaining";
      }
    }
    description
      "SID Client types.";
  }

  typedef live_ncs_table-id {
    type uint32;
    description
      "Routing Table Id";
  }

  typedef live_ncs_srv6-status-type {
    type enumeration {
      enum "up" {
        value 1;
        description
          "State is Up";
      }
      enum "down" {
        description
          "State is Down";
      }
    }
    description
      "Status type";
  }

  typedef live_ncs_srv6-nexthop-type {
    type enumeration {
      enum "ipv4" {
        value 1;
        description
          "IPv4 next-hop";
      }
      enum "ipv6" {
        description
          "IPv6 next-hop";
      }
      enum "mpls" {
        description
          "MPLS next-hop";
      }
      enum "l2" {
        description
          "L2 next-hop";
      }
    }
    description
      "Forwarding Next-hop type";
  }

  typedef srv6-end-type {
    type enumeration {
      enum "End" {
        value 1;
        description
          "The Endpoint function. This is the most
           basic function";
      }
      enum "End.X" {
        description
          "Endpoint with cross-connect to an array
           of layer-3 adjacencies";
      }
      enum "End.T" {
        description
          "Endpoint with specific IPv6 table lookup";
      }
      enum "End.DX2" {
        description
          "Endpoint with decapsulation and Layer-2
           cross-connect to an L2 interface";
      }
      enum "End.DX2V" {
        description
          "Endpoint with decapsulation and specific
           VLAN L2 table lookup";
      }
      enum "End.DT2U" {
        description
          "Endpoint with decapsulation and specific
           unicast MAC L2 table lookup";
      }
      enum "End.DT2M" {
        description
          "Endpoint with decapsulation and specific L2 table
           flooding";
      }
      enum "End.DX6" {
        description
          "Endpoint with decapsulation and cross-connect
           to an array of IPv6 adjacencies";
      }
      enum "End.DX4" {
        description
          "Endpoint with decapsulation and cross-connect
           to an array of IPv4 adjacencies";
      }
      enum "End.DT6" {
        description
          "Endpoint with decapsulation and specific
           IPv6 table lookup";
      }
      enum "End.DT4" {
        description
          "Endpoint with decapsulation and specific
           IPv4 table lookup";
      }
      enum "End.DT46" {
        description
          "Endpoint with decapsulation and specific IP
           (IPv4 or IPv6) table lookup";
      }
      enum "End.B6" {
        description
          "Endpoint bound to an SRv6 Policy";
      }
      enum "End.B6.Encaps" {
        description
          "This is a variation of the End.B6 behavior
           where the SRv6 Policy also includes an
           IPv6 Source Address A.";
      }
      enum "End.BM" {
        description
          "Endpoint bound to an SR-MPLS Policy";
      }
      enum "End.S" {
        description
          "Endpoint in search of a target in table TE";
      }
      enum "End.AS" {
        description
          "Service-Chaining Static proxy for inner type (Ethernet, IPv4 or IPv6)";
      }
      enum "End.AD" {
        description
          "Service-Chaining Dynamic proxy for inner type (Ethernet, IPv4 or IPv6)";
      }
      enum "End.ASM" {
        description
          "Service-Chaining Shared memory SR proxy for inner type (Ethernet, IPv4 or IPv6)";
      }
      enum "End.AM" {
        description
          "Service-Chaining Masquerading SR proxy";
      }
    }
    description
      "SRv6 End behavior types";
  }

  typedef srv6-transit-type {
    type enumeration {
      enum "T" {
        value 1;
        description
          "Transit";
      }
      enum "T.Encaps" {
        description
          "T.Encaps";
      }
      enum "T.Insert" {
        description
          "T.Insert";
      }
      enum "T.Encaps.L2" {
        description
          "T.Encaps.L2";
      }
    }
    description
      "SRv6 Transit behavior types";
  }

  typedef srv6-security-rule-type {
    type enumeration {
      enum "SEC1" {
        value 1;
        description
          "Security rule SEC1";
      }
      enum "SEC2" {
        description
          "Security rule SEC2";
      }
      enum "SEC3" {
        description
          "Security rule SEC3";
      }
      enum "SEC4" {
        description
          "Security rule SEC4";
      }
    }
    description
      "SRv6 Security rule types";
  }

  typedef srv6-counter-type {
    type enumeration {
      enum "CNT0" {
        value 0;
        description
          "CNT0";
      }
      enum "CNT1" {
        description
          "CNT1";
      }
      enum "CNT2" {
        description
          "CNT2";
      }
    }
    description
      "SRv6 counter types";
  }

  typedef srv6-sid {
    type inet:ipv6-prefix;
    description
      "This type defines a SID value in SRv6";
  }

  typedef srv6-func-opcode {
    type uint32;
    description
      "This is a typedef for SID FUNC's opcode type";
  }

  typedef srv6-func-opcode-reserved {
    type uint32 {
      range "1 .. 63";
    }
    description
      "This is a typedef for SID FUNC's reserved opcode type";
  }

  typedef srv6-func-opcode-unreserved {
    type uint32 {
      range "64 .. max";
    }
    description
      "This is a typedef for SID FUNC's allocatable (unreserved) opcode type";
  }

  typedef srv6-func-opcode-reserved-type {
    type enumeration {
      enum "invalid" {
        value 0;
        description
          "Invalid opcode";
      }
      enum "default-end-psp" {
        value 1;
        description
          "Opcode for Default End/PSP funcion";
      }
      enum "default-end-usp" {
        value 2;
        description
          "Opcode for Default End/USP funcion";
      }
    }
    description
      "SRv6 SID FUNC Reserved Opcodes";
  }

  typedef srv6-locator-len {
    type uint8 {
      range "32 .. 96";
    }
    description
      "This type defines an SRv6 locator len with range constraints";
  }

  typedef srv6-sid-pfxlen {
    type uint8 {
      range "33 .. 128";
    }
    default "128";
    description
      "This type defines a SID prefixlen with range constraints";
  }

  typedef sid-alloc-type {
    type enumeration {
      enum "Dynamic" {
        description
          "SID allocated dynamically.";
      }
      enum "Explicit" {
        description
          "SID allocated with explicit (static) value";
      }
    }
    description
      "Types of sid allocation used.";
  }

  typedef srv6-sid-owner-type {
    type enumeration {
      enum "isis" {
        value 1;
        description
          "ISIS";
      }
      enum "ospfv3" {
        description
          "OSPFv3";
      }
      enum "bgp" {
        description
          "BGP";
      }
      enum "evpn" {
        description
          "EVPN";
      }
      enum "sr-policy" {
        description
          "SR Policy";
      }
      enum "service-chain" {
        description
          "Service-Chaining";
      }
    }
    description
      "SID Client types.";
  }

  typedef table-id {
    type uint32;
    description
      "Routing Table Id";
  }

  typedef srv6-status-type {
    type enumeration {
      enum "up" {
        value 1;
        description
          "State is Up";
      }
      enum "down" {
        description
          "State is Down";
      }
    }
    description
      "Status type";
  }

  typedef srv6-nexthop-type {
    type enumeration {
      enum "ipv4" {
        value 1;
        description
          "IPv4 next-hop";
      }
      enum "ipv6" {
        description
          "IPv6 next-hop";
      }
      enum "mpls" {
        description
          "MPLS next-hop";
      }
      enum "l2" {
        description
          "L2 next-hop";
      }
    }
    description
      "Forwarding Next-hop type";
  }
}
