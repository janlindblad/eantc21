module ciena-bfd-mpls {
  // Generated by yanger -t ncs
  tailf:mount-id "saos106-nc-1.0:saos106-nc-1.0";
  tailf:ncs-device-type "netconf";

  namespace "http://ciena.com/ns/yang/ciena-bfd-mpls";
  prefix bfd-mpls;

  import ciena-bfd-types {
    prefix bfd-types;
  }
  import tailf-common {
    prefix tailf;
  }
  import tailf-ncs {
    prefix ncs;
  }

  organization
    "Ciena Corporation";
  contact
    "Web URL: http://www.ciena.com/
     E-mail:  yang@ciena.com
     Postal:  7035 Ridge Road
                 Hanover, Maryland 21076
                 U.S.A.
     Phone:   +1 800-921-1144
     Fax:     +1 410-694-5750";
  description
    "This module contains the YANG definition for BFD parameters for
     MPLS LSPs as per RFC 5884.

     Copyright (c) 2020  Ciena Corporation.  All rights
     reserved.

     All information contained herein is, and remains the
     property of Ciena Corporation. Dissemination of this
     information or reproduction of this material is strictly
     forbidden unless prior written permission is obtained
     from Ciena Corporation.";

  revision 2020-01-27 {
    description
      "Initial revision.";
  }

  typedef ncs_template_gach-value {
    type string;
    description
      "Configuration for BFD G-ACh encapsulation";
    // NCS drop default statement
  }

  typedef ncs_rpc_notif_gach-value {
    type enumeration {
      enum "mpls-tp-cc" {
        value 22;
        description
          "MPLS-TP CC message";
      }
      enum "mpls-tp-cv" {
        value 23;
        description
          "MPLS-TP CV message";
      }
      enum "pw-ach" {
        value 7;
        description
          "BFD Control, PW-ACH encapsulation (without IP/UDP Headers).";
      }
    }
    description
      "Configuration for BFD G-ACh encapsulation";
    default "mpls-tp-cc";
  }

  typedef live_ncs_gach-value {
    type enumeration {
      enum "mpls-tp-cc" {
        value 22;
        description
          "MPLS-TP CC message";
      }
      enum "mpls-tp-cv" {
        value 23;
        description
          "MPLS-TP CV message";
      }
      enum "pw-ach" {
        value 7;
        description
          "BFD Control, PW-ACH encapsulation (without IP/UDP Headers).";
      }
    }
    description
      "Configuration for BFD G-ACh encapsulation";
    // NCS drop default statement
  }

  typedef gach-value {
    type enumeration {
      enum "mpls-tp-cc" {
        value 22;
        description
          "MPLS-TP CC message";
      }
      enum "mpls-tp-cv" {
        value 23;
        description
          "MPLS-TP CV message";
      }
      enum "pw-ach" {
        value 7;
        description
          "BFD Control, PW-ACH encapsulation (without IP/UDP Headers).";
      }
    }
    description
      "Configuration for BFD G-ACh encapsulation";
    default "mpls-tp-cc";
  }

  grouping ncs_template_encap-cfg {
    description
      "Configuration for BFD encapsulation";
    leaf encap {
      type string;
      // NCS drop default statement
      description
        "BFD encapsulation";
    }
  }

  grouping ncs_rpc_notif_encap-cfg {
    description
      "Configuration for BFD encapsulation";
    leaf encap {
      type identityref {
        base bfd-types:encap-type;
      }
      default "encap-gach";
      description
        "BFD encapsulation";
    }
  }

  grouping live_ncs_encap-cfg {
    description
      "Configuration for BFD encapsulation";
    leaf encap {
      type identityref {
        base bfd-types:encap-type;
      }
      // NCS drop default statement
      description
        "BFD encapsulation";
    }
  }

  grouping encap-cfg {
    description
      "Configuration for BFD encapsulation";
    leaf encap {
      type identityref {
        base bfd-types:encap-type;
      }
      default "encap-gach";
      description
        "BFD encapsulation";
    }
  }

  identity encap-ip-gach {
    base bfd-types:encap-type;
    description
      "BFD with IP and G-ACh encapsulation as per RFC 5586.";
  }

  identity encap-gach {
    base bfd-types:encap-type;
    description
      "BFD with G-ACh encapsulation as per RFC 5586.";
  }
}
