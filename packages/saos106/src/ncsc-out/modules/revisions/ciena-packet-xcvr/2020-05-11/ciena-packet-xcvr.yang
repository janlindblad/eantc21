module ciena-packet-xcvr {
  // Generated by yanger -t ncs
  tailf:mount-id "saos106-nc-1.0:saos106-nc-1.0";
  tailf:ncs-device-type "netconf";

  namespace "http://www.ciena.com/ns/yang/ciena-packet-xcvr";
  prefix xcvr;

  import ciena-packet-typedefs {
    prefix cntypes;
  }
  import tailf-common {
    prefix tailf;
  }
  import tailf-ncs {
    prefix ncs;
  }

  organization
    "Ciena Corporation";
  contact
    "Web URL: http://www.ciena.com/
     Postal:  7035 Ridge Road
              Hanover, Maryland 21076
              U.S.A.
     Phone:   +1 800-921-1144
     Fax:     +1 410-694-5750";
  description
    "This module defines the common XCVR model. The XCVR is augmented by specific types of transceiver modules if applicable. XCVR objects are permanently available for all ports and reported as empty if the device is not physically present. Attributes read from the device are only available while the device is present.";

  revision 2020-05-11 {
    description
      "Removed max-elements from the list lane.";
  }
  revision 2019-10-31 {
    description
      "Adding rx-los and rx-los-cleared enum values along with laser-temperature and lane support. Removing optic-unrecognized-vendor and optic-unrecognized-part-number from xcvr-event-type enum.";
  }
  revision 2019-10-07 {
    description
      "Changed 'notification xcvr-event' to 'notification xcvr-events' and added a list of 'xcvr-event' to the notification.
       Also added a list of 'event-list' as well.";
  }
  revision 2019-09-09 {
    description
      "Changes to xcvr events and associated data used to publish state of xcvr instances.";
  }
  revision 2018-05-17 {
    description
      "Based off of ciena-waveserver-xcvr.yang";
  }

  typedef ncs_template_xcvr-op-enum {
    type string;
    description
      "XCVR operational state values.";
  }

  typedef ncs_template_xcvr-event-type {
    type string;
    description
      "A generic event type describing the type of events/notifications triggered by xcvr.";
  }

  typedef ncs_rpc_notif_xcvr-op-enum {
    type enumeration {
      enum "unknown" {
        description
          "Unknown operational state.";
      }
      enum "up" {
        description
          "XCVR is up/operational.";
      }
      enum "down" {
        description
          "XCVR is down/failed.";
      }
      enum "fault" {
        description
          "There is an active alarm associated with the XCVR.";
      }
      enum "shutdown" {
        description
          "XCVR is shutdown/off.";
      }
      enum "lower-layer-down" {
        description
          "The XCVR is enabled, but a parent object is faulted.";
      }
      enum "unequipped" {
        description
          "XCVR is unequipped.";
      }
      enum "uncertified" {
        description
          "XCVR is uncertified.";
      }
    }
    description
      "XCVR operational state values.";
  }

  typedef ncs_rpc_notif_xcvr-event-type {
    type enumeration {
      enum "operational-state" {
        description
          "Transceiver operational state change (link state, error state).";
      }
      enum "operational-speed" {
        description
          "Transceiver operational speed change.";
      }
      enum "xcvr-inserted" {
        description
          "Transceiver has been inserted.";
      }
      enum "xcvr-removed" {
        description
          "Transceiver has been removed.";
      }
      enum "optic-temp-high-alarm-threshold" {
        description
          "Temperature went over the maximum temperature threshold.";
      }
      enum "optic-temp-low-alarm-threshold" {
        description
          "Temperature went below the minimum temperature threshold.";
      }
      enum "optic-temp-normal" {
        description
          "Temperature has returned to normal having previously crossed an alarm threshold.";
      }
      enum "optic-unrecognized-unqualified" {
        description
          "An unrecognized or Unqualified Transceiver is present.";
      }
      enum "optic-capability-incompatible" {
        description
          "Transceiver Optic Capability is Incompatible.";
      }
      enum "tx-power-bias-high-threshold" {
        description
          "Tx Power Bias went over the maximum threshold.";
      }
      enum "tx-power-bias-low-threshold" {
        description
          "Tx Power Bias went below the maximum threshold.";
      }
      enum "tx-power-bias-normal" {
        description
          "Tx Power Bias has returned to normal having previously crossed a threshold.";
      }
      enum "rx-power-bias-high-threshold" {
        description
          "Rx Power Bias went over the maximum threshold.";
      }
      enum "rx-power-bias-low-threshold" {
        description
          "Rx Power Bias went below the maximum threshold.";
      }
      enum "rx-power-bias-normal" {
        description
          "Rx Power Bias has returned to normal having previously crossed a threshold.";
      }
      enum "voltage-high-alarm-threshold" {
        description
          "Voltage high threshold";
      }
      enum "voltage-low-alarm-threshold" {
        description
          "Voltage low threshold";
      }
      enum "voltage-normal" {
        description
          "Voltage has returned to normal having previously crossed a threshold.";
      }
      enum "laser-bias-high-alarm-threshold" {
        description
          "Laser Bias high threshold";
      }
      enum "laser-bias-low-alarm-threshold" {
        description
          "Laser Bias low threshold";
      }
      enum "laser-bias-normal" {
        description
          "Laser Bias has returned to normal having previously crossed a threshold.";
      }
      enum "laser-temperature-high-alarm-threshold" {
        description
          "Laser Temperature high threshold";
      }
      enum "laser-temperature-low-alarm-threshold" {
        description
          "Laser Temperature low threshold";
      }
      enum "laser-temperature-normal" {
        description
          "Laser Temperature has returned to normal having previously crossed a threshold.";
      }
      enum "rx-los" {
        description
          "Rx LOS detected.";
      }
      enum "rx-los-cleared" {
        description
          "Rx LOS cleared.";
      }
      enum "any" {
        description
          "An enum value used by notification registrants to specify any of the enumerated values in the enumeration list.";
      }
    }
    description
      "A generic event type describing the type of events/notifications triggered by xcvr.";
  }

  typedef live_ncs_xcvr-op-enum {
    type enumeration {
      enum "unknown" {
        description
          "Unknown operational state.";
      }
      enum "up" {
        description
          "XCVR is up/operational.";
      }
      enum "down" {
        description
          "XCVR is down/failed.";
      }
      enum "fault" {
        description
          "There is an active alarm associated with the XCVR.";
      }
      enum "shutdown" {
        description
          "XCVR is shutdown/off.";
      }
      enum "lower-layer-down" {
        description
          "The XCVR is enabled, but a parent object is faulted.";
      }
      enum "unequipped" {
        description
          "XCVR is unequipped.";
      }
      enum "uncertified" {
        description
          "XCVR is uncertified.";
      }
    }
    description
      "XCVR operational state values.";
  }

  typedef live_ncs_xcvr-event-type {
    type enumeration {
      enum "operational-state" {
        description
          "Transceiver operational state change (link state, error state).";
      }
      enum "operational-speed" {
        description
          "Transceiver operational speed change.";
      }
      enum "xcvr-inserted" {
        description
          "Transceiver has been inserted.";
      }
      enum "xcvr-removed" {
        description
          "Transceiver has been removed.";
      }
      enum "optic-temp-high-alarm-threshold" {
        description
          "Temperature went over the maximum temperature threshold.";
      }
      enum "optic-temp-low-alarm-threshold" {
        description
          "Temperature went below the minimum temperature threshold.";
      }
      enum "optic-temp-normal" {
        description
          "Temperature has returned to normal having previously crossed an alarm threshold.";
      }
      enum "optic-unrecognized-unqualified" {
        description
          "An unrecognized or Unqualified Transceiver is present.";
      }
      enum "optic-capability-incompatible" {
        description
          "Transceiver Optic Capability is Incompatible.";
      }
      enum "tx-power-bias-high-threshold" {
        description
          "Tx Power Bias went over the maximum threshold.";
      }
      enum "tx-power-bias-low-threshold" {
        description
          "Tx Power Bias went below the maximum threshold.";
      }
      enum "tx-power-bias-normal" {
        description
          "Tx Power Bias has returned to normal having previously crossed a threshold.";
      }
      enum "rx-power-bias-high-threshold" {
        description
          "Rx Power Bias went over the maximum threshold.";
      }
      enum "rx-power-bias-low-threshold" {
        description
          "Rx Power Bias went below the maximum threshold.";
      }
      enum "rx-power-bias-normal" {
        description
          "Rx Power Bias has returned to normal having previously crossed a threshold.";
      }
      enum "voltage-high-alarm-threshold" {
        description
          "Voltage high threshold";
      }
      enum "voltage-low-alarm-threshold" {
        description
          "Voltage low threshold";
      }
      enum "voltage-normal" {
        description
          "Voltage has returned to normal having previously crossed a threshold.";
      }
      enum "laser-bias-high-alarm-threshold" {
        description
          "Laser Bias high threshold";
      }
      enum "laser-bias-low-alarm-threshold" {
        description
          "Laser Bias low threshold";
      }
      enum "laser-bias-normal" {
        description
          "Laser Bias has returned to normal having previously crossed a threshold.";
      }
      enum "laser-temperature-high-alarm-threshold" {
        description
          "Laser Temperature high threshold";
      }
      enum "laser-temperature-low-alarm-threshold" {
        description
          "Laser Temperature low threshold";
      }
      enum "laser-temperature-normal" {
        description
          "Laser Temperature has returned to normal having previously crossed a threshold.";
      }
      enum "rx-los" {
        description
          "Rx LOS detected.";
      }
      enum "rx-los-cleared" {
        description
          "Rx LOS cleared.";
      }
      enum "any" {
        description
          "An enum value used by notification registrants to specify any of the enumerated values in the enumeration list.";
      }
    }
    description
      "A generic event type describing the type of events/notifications triggered by xcvr.";
  }

  typedef xcvr-op-enum {
    type enumeration {
      enum "unknown" {
        description
          "Unknown operational state.";
      }
      enum "up" {
        description
          "XCVR is up/operational.";
      }
      enum "down" {
        description
          "XCVR is down/failed.";
      }
      enum "fault" {
        description
          "There is an active alarm associated with the XCVR.";
      }
      enum "shutdown" {
        description
          "XCVR is shutdown/off.";
      }
      enum "lower-layer-down" {
        description
          "The XCVR is enabled, but a parent object is faulted.";
      }
      enum "unequipped" {
        description
          "XCVR is unequipped.";
      }
      enum "uncertified" {
        description
          "XCVR is uncertified.";
      }
    }
    description
      "XCVR operational state values.";
  }

  typedef xcvr-event-type {
    type enumeration {
      enum "operational-state" {
        description
          "Transceiver operational state change (link state, error state).";
      }
      enum "operational-speed" {
        description
          "Transceiver operational speed change.";
      }
      enum "xcvr-inserted" {
        description
          "Transceiver has been inserted.";
      }
      enum "xcvr-removed" {
        description
          "Transceiver has been removed.";
      }
      enum "optic-temp-high-alarm-threshold" {
        description
          "Temperature went over the maximum temperature threshold.";
      }
      enum "optic-temp-low-alarm-threshold" {
        description
          "Temperature went below the minimum temperature threshold.";
      }
      enum "optic-temp-normal" {
        description
          "Temperature has returned to normal having previously crossed an alarm threshold.";
      }
      enum "optic-unrecognized-unqualified" {
        description
          "An unrecognized or Unqualified Transceiver is present.";
      }
      enum "optic-capability-incompatible" {
        description
          "Transceiver Optic Capability is Incompatible.";
      }
      enum "tx-power-bias-high-threshold" {
        description
          "Tx Power Bias went over the maximum threshold.";
      }
      enum "tx-power-bias-low-threshold" {
        description
          "Tx Power Bias went below the maximum threshold.";
      }
      enum "tx-power-bias-normal" {
        description
          "Tx Power Bias has returned to normal having previously crossed a threshold.";
      }
      enum "rx-power-bias-high-threshold" {
        description
          "Rx Power Bias went over the maximum threshold.";
      }
      enum "rx-power-bias-low-threshold" {
        description
          "Rx Power Bias went below the maximum threshold.";
      }
      enum "rx-power-bias-normal" {
        description
          "Rx Power Bias has returned to normal having previously crossed a threshold.";
      }
      enum "voltage-high-alarm-threshold" {
        description
          "Voltage high threshold";
      }
      enum "voltage-low-alarm-threshold" {
        description
          "Voltage low threshold";
      }
      enum "voltage-normal" {
        description
          "Voltage has returned to normal having previously crossed a threshold.";
      }
      enum "laser-bias-high-alarm-threshold" {
        description
          "Laser Bias high threshold";
      }
      enum "laser-bias-low-alarm-threshold" {
        description
          "Laser Bias low threshold";
      }
      enum "laser-bias-normal" {
        description
          "Laser Bias has returned to normal having previously crossed a threshold.";
      }
      enum "laser-temperature-high-alarm-threshold" {
        description
          "Laser Temperature high threshold";
      }
      enum "laser-temperature-low-alarm-threshold" {
        description
          "Laser Temperature low threshold";
      }
      enum "laser-temperature-normal" {
        description
          "Laser Temperature has returned to normal having previously crossed a threshold.";
      }
      enum "rx-los" {
        description
          "Rx LOS detected.";
      }
      enum "rx-los-cleared" {
        description
          "Rx LOS cleared.";
      }
      enum "any" {
        description
          "An enum value used by notification registrants to specify any of the enumerated values in the enumeration list.";
      }
    }
    description
      "A generic event type describing the type of events/notifications triggered by xcvr.";
  }

  grouping ncs_template_optical-power-group {
    description
      "Group of optical power related operational data leafs. Can be used for Rx or Tx";
    // NCS drop config false leaf actual
    // NCS drop config false leaf maximum
    // NCS drop config false leaf minimum
    // NCS drop config false leaf 'maximum-recorded-time'
    // NCS drop config false leaf 'minimum-recorded-time'
  }

  grouping ncs_template_optical-power-threshold-group {
    description
      "Group of optical power alarm related operational data leafs. Can be used for Rx or Tx.";
    // NCS drop config false leaf 'high-alarm-threshold'
    // NCS drop config false leaf 'low-alarm-threshold'
    // NCS drop config false leaf 'high-warning-threshold'
    // NCS drop config false leaf 'low-warning-threshold'
  }

  grouping ncs_template_optical-power-status-group {
    description
      "Group of optical power status related operational data leafs. Can be used for Rx or Tx";
    // NCS drop config false leaf 'high-alarm-status'
    // NCS drop config false leaf 'low-alarm-status'
    // NCS drop config false leaf 'high-warning-status'
    // NCS drop config false leaf 'low-warning-status'
  }

  grouping ncs_template_optical-bias-status-group {
    description
      "Group of optical bias related operational data leafs.";
    // NCS drop config false leaf 'high-alarm-status'
    // NCS drop config false leaf 'low-alarm-status'
    // NCS drop config false leaf 'high-warning-status'
    // NCS drop config false leaf 'low-warning-status'
  }

  grouping ncs_template_temperature-threshold-group {
    description
      "Group of XCVR temperature alarm and warning operational data leafs.";
    // NCS drop config false leaf 'high-alarm-threshold'
    // NCS drop config false leaf 'low-alarm-threshold'
    // NCS drop config false leaf 'high-warning-threshold'
    // NCS drop config false leaf 'low-warning-threshold'
  }

  grouping ncs_template_temperature-status-group {
    description
      "Group of XCVR temperature related operational data leafs.";
    // NCS drop config false leaf 'high-alarm-status'
    // NCS drop config false leaf 'low-alarm-status'
    // NCS drop config false leaf 'high-warning-status'
    // NCS drop config false leaf 'low-warning-status'
  }

  grouping ncs_template_supply-voltage-threshold-group {
    description
      "Group of Supply Voltage alarm and warning operational data leafs.";
    // NCS drop config false leaf 'high-alarm-threshold'
    // NCS drop config false leaf 'low-alarm-threshold'
    // NCS drop config false leaf 'high-warning-threshold'
    // NCS drop config false leaf 'low-warning-threshold'
  }

  grouping ncs_template_supply-voltage-status-group {
    description
      "group of Supply Voltage related operational data leafs. The grouping may be used by various XCVR containers, lists, and augments.";
    // NCS drop config false leaf 'high-alarm-status'
    // NCS drop config false leaf 'low-alarm-status'
    // NCS drop config false leaf 'high-warning-status'
    // NCS drop config false leaf 'low-warning-status'
  }

  grouping ncs_rpc_notif_optical-power-group {
    description
      "Group of optical power related operational data leafs. Can be used for Rx or Tx";
    leaf actual {
      type cntypes:ncs_rpc_notif_decimal-1-dig;
      units "dBm";
      config false;
      description
        "Actual Tx or Rx optical power in dBm.";
    }
    leaf maximum {
      type cntypes:ncs_rpc_notif_decimal-1-dig;
      units "dBm";
      config false;
      description
        "Maximum actual recorded Tx or Rx optical power in dBm.";
    }
    leaf minimum {
      type cntypes:ncs_rpc_notif_decimal-1-dig;
      units "dBm";
      config false;
      description
        "Minimum actual recorded Tx or Rx optical power in dBm.";
    }
    leaf maximum-recorded-time {
      type cntypes:ncs_rpc_notif_string-maxl-32;
      config false;
      description
        "The exact date and time when the maximum optical power (Tx or Rx) was recorded. In the format of a date time string.";
    }
    leaf minimum-recorded-time {
      type cntypes:ncs_rpc_notif_string-maxl-32;
      config false;
      description
        "The exact date and time when the minimum optical power (Tx or Rx) was recorded. In the format of a date time string.";
    }
  }

  grouping ncs_rpc_notif_optical-power-threshold-group {
    description
      "Group of optical power alarm related operational data leafs. Can be used for Rx or Tx.";
    leaf high-alarm-threshold {
      type cntypes:ncs_rpc_notif_decimal-1-dig;
      units "dBm";
      config false;
      description
        "Optical power high alarm threshold, in dBm. If it is modem Tx-power, the threshold can change based on provisioned tx power. High threshold = target power + 3.";
    }
    leaf low-alarm-threshold {
      type cntypes:ncs_rpc_notif_decimal-1-dig;
      units "dBm";
      config false;
      description
        "Optical power low alarm threshold, in dBm. If it is modem Tx-power, the threshold can change based on provisioned tx power. Low threshold = target power - 10.";
    }
    leaf high-warning-threshold {
      type cntypes:ncs_rpc_notif_decimal-1-dig;
      units "dBm";
      config false;
      description
        "Optical power high warning threshold, in dBm.";
    }
    leaf low-warning-threshold {
      type cntypes:ncs_rpc_notif_decimal-1-dig;
      units "dBm";
      config false;
      description
        "Optical power low warning threshold, in dBm.";
    }
  }

  grouping ncs_rpc_notif_optical-power-status-group {
    description
      "Group of optical power status related operational data leafs. Can be used for Rx or Tx";
    leaf high-alarm-status {
      type boolean;
      config false;
      description
        "Optical power high alarm status, boolean, true if alarm is raised, false if alarm is not raised.";
    }
    leaf low-alarm-status {
      type boolean;
      config false;
      description
        "Optical power low alarm status, boolean, true if alarm is raised, false if alarm is not raised.";
    }
    leaf high-warning-status {
      type boolean;
      config false;
      description
        "Optical power high warning status, boolean, true if warning is raised, false if warning is not raised.";
    }
    leaf low-warning-status {
      type boolean;
      config false;
      description
        "Optical power low warning status, boolean, true if warning is raised, false if warning is not raised.";
    }
  }

  grouping ncs_rpc_notif_optical-bias-status-group {
    description
      "Group of optical bias related operational data leafs.";
    leaf high-alarm-status {
      type boolean;
      config false;
      description
        "Optical bias high alarm status, boolean, true if alarm is raised, false if alarm is not raised.";
    }
    leaf low-alarm-status {
      type boolean;
      config false;
      description
        "Optical bias low alarm status, boolean, true if alarm is raised, false if alarm is not raised.";
    }
    leaf high-warning-status {
      type boolean;
      config false;
      description
        "Optical bias high warning status, boolean, true if warning is raised, false if warning is not raised.";
    }
    leaf low-warning-status {
      type boolean;
      config false;
      description
        "Optical bias low warning status, boolean, true if warning is raised, false if warning is not raised.";
    }
  }

  grouping ncs_rpc_notif_temperature-threshold-group {
    description
      "Group of XCVR temperature alarm and warning operational data leafs.";
    leaf high-alarm-threshold {
      type int16;
      units "C";
      config false;
      description
        "Temperature high alarm threshold, in degrees Celsius (C).";
    }
    leaf low-alarm-threshold {
      type int16;
      units "C";
      config false;
      description
        "Temperature low alarm threshold, in degrees Celsius (C)";
    }
    leaf high-warning-threshold {
      type int16;
      units "C";
      config false;
      description
        "Temperature high warning threshold, in degrees Celsius (C)";
    }
    leaf low-warning-threshold {
      type int16;
      units "C";
      config false;
      description
        "Temperature low warning threshold, in degrees Celsius (C)";
    }
  }

  grouping ncs_rpc_notif_temperature-status-group {
    description
      "Group of XCVR temperature related operational data leafs.";
    leaf high-alarm-status {
      type boolean;
      config false;
      description
        "Temperature high alarm status, boolean, true if alarm is raised, false if alarm is not raised.";
    }
    leaf low-alarm-status {
      type boolean;
      config false;
      description
        "Temperature low alarm status, boolean, true if alarm is raised, false if alarm is not raised.";
    }
    leaf high-warning-status {
      type boolean;
      config false;
      description
        "Temperature high warning status, boolean, true if warning is raised, false if warning is not raised.";
    }
    leaf low-warning-status {
      type boolean;
      config false;
      description
        "Temperature low warning status, boolean, true if warning is raised, false if warning is not raised.";
    }
  }

  grouping ncs_rpc_notif_supply-voltage-threshold-group {
    description
      "Group of Supply Voltage alarm and warning operational data leafs.";
    leaf high-alarm-threshold {
      type cntypes:ncs_rpc_notif_decimal-2-dig;
      units "V";
      config false;
      description
        "Supply voltage high alarm threshold, in volts (V).";
    }
    leaf low-alarm-threshold {
      type cntypes:ncs_rpc_notif_decimal-2-dig;
      units "V";
      config false;
      description
        "Supply voltage low alarm threshold, in volts (V).";
    }
    leaf high-warning-threshold {
      type cntypes:ncs_rpc_notif_decimal-2-dig;
      units "V";
      config false;
      description
        "Supply voltage high warning threshold, in volts (V).";
    }
    leaf low-warning-threshold {
      type cntypes:ncs_rpc_notif_decimal-2-dig;
      units "V";
      config false;
      description
        "Supply voltage low warning threshold, in volts (V).";
    }
  }

  grouping ncs_rpc_notif_supply-voltage-status-group {
    description
      "group of Supply Voltage related operational data leafs. The grouping may be used by various XCVR containers, lists, and augments.";
    leaf high-alarm-status {
      type boolean;
      config false;
      description
        "Supply voltage high alarm status, boolean, true if alarm is raised, false if alarm is not raised.";
    }
    leaf low-alarm-status {
      type boolean;
      config false;
      description
        "Supply voltage low alarm status, boolean, true if alarm is raised, false if alarm is not raised.";
    }
    leaf high-warning-status {
      type boolean;
      config false;
      description
        "Supply voltage high warning status, boolean, true if warning is raised, false if warning is not raised.";
    }
    leaf low-warning-status {
      type boolean;
      config false;
      description
        "Supply voltage low warning status, boolean, true if warning is raised, false if warning is not raised.";
    }
  }

  grouping live_ncs_optical-power-group {
    description
      "Group of optical power related operational data leafs. Can be used for Rx or Tx";
    leaf actual {
      type cntypes:live_ncs_decimal-1-dig;
      units "dBm";
      description
        "Actual Tx or Rx optical power in dBm.";
    }
    leaf maximum {
      type cntypes:live_ncs_decimal-1-dig;
      units "dBm";
      description
        "Maximum actual recorded Tx or Rx optical power in dBm.";
    }
    leaf minimum {
      type cntypes:live_ncs_decimal-1-dig;
      units "dBm";
      description
        "Minimum actual recorded Tx or Rx optical power in dBm.";
    }
    leaf maximum-recorded-time {
      type cntypes:live_ncs_string-maxl-32;
      description
        "The exact date and time when the maximum optical power (Tx or Rx) was recorded. In the format of a date time string.";
    }
    leaf minimum-recorded-time {
      type cntypes:live_ncs_string-maxl-32;
      description
        "The exact date and time when the minimum optical power (Tx or Rx) was recorded. In the format of a date time string.";
    }
  }

  grouping live_ncs_optical-power-threshold-group {
    description
      "Group of optical power alarm related operational data leafs. Can be used for Rx or Tx.";
    leaf high-alarm-threshold {
      type cntypes:live_ncs_decimal-1-dig;
      units "dBm";
      description
        "Optical power high alarm threshold, in dBm. If it is modem Tx-power, the threshold can change based on provisioned tx power. High threshold = target power + 3.";
    }
    leaf low-alarm-threshold {
      type cntypes:live_ncs_decimal-1-dig;
      units "dBm";
      description
        "Optical power low alarm threshold, in dBm. If it is modem Tx-power, the threshold can change based on provisioned tx power. Low threshold = target power - 10.";
    }
    leaf high-warning-threshold {
      type cntypes:live_ncs_decimal-1-dig;
      units "dBm";
      description
        "Optical power high warning threshold, in dBm.";
    }
    leaf low-warning-threshold {
      type cntypes:live_ncs_decimal-1-dig;
      units "dBm";
      description
        "Optical power low warning threshold, in dBm.";
    }
  }

  grouping live_ncs_optical-power-status-group {
    description
      "Group of optical power status related operational data leafs. Can be used for Rx or Tx";
    leaf high-alarm-status {
      type boolean;
      description
        "Optical power high alarm status, boolean, true if alarm is raised, false if alarm is not raised.";
    }
    leaf low-alarm-status {
      type boolean;
      description
        "Optical power low alarm status, boolean, true if alarm is raised, false if alarm is not raised.";
    }
    leaf high-warning-status {
      type boolean;
      description
        "Optical power high warning status, boolean, true if warning is raised, false if warning is not raised.";
    }
    leaf low-warning-status {
      type boolean;
      description
        "Optical power low warning status, boolean, true if warning is raised, false if warning is not raised.";
    }
  }

  grouping live_ncs_optical-bias-status-group {
    description
      "Group of optical bias related operational data leafs.";
    leaf high-alarm-status {
      type boolean;
      description
        "Optical bias high alarm status, boolean, true if alarm is raised, false if alarm is not raised.";
    }
    leaf low-alarm-status {
      type boolean;
      description
        "Optical bias low alarm status, boolean, true if alarm is raised, false if alarm is not raised.";
    }
    leaf high-warning-status {
      type boolean;
      description
        "Optical bias high warning status, boolean, true if warning is raised, false if warning is not raised.";
    }
    leaf low-warning-status {
      type boolean;
      description
        "Optical bias low warning status, boolean, true if warning is raised, false if warning is not raised.";
    }
  }

  grouping live_ncs_temperature-threshold-group {
    description
      "Group of XCVR temperature alarm and warning operational data leafs.";
    leaf high-alarm-threshold {
      type int16;
      units "C";
      description
        "Temperature high alarm threshold, in degrees Celsius (C).";
    }
    leaf low-alarm-threshold {
      type int16;
      units "C";
      description
        "Temperature low alarm threshold, in degrees Celsius (C)";
    }
    leaf high-warning-threshold {
      type int16;
      units "C";
      description
        "Temperature high warning threshold, in degrees Celsius (C)";
    }
    leaf low-warning-threshold {
      type int16;
      units "C";
      description
        "Temperature low warning threshold, in degrees Celsius (C)";
    }
  }

  grouping live_ncs_temperature-status-group {
    description
      "Group of XCVR temperature related operational data leafs.";
    leaf high-alarm-status {
      type boolean;
      description
        "Temperature high alarm status, boolean, true if alarm is raised, false if alarm is not raised.";
    }
    leaf low-alarm-status {
      type boolean;
      description
        "Temperature low alarm status, boolean, true if alarm is raised, false if alarm is not raised.";
    }
    leaf high-warning-status {
      type boolean;
      description
        "Temperature high warning status, boolean, true if warning is raised, false if warning is not raised.";
    }
    leaf low-warning-status {
      type boolean;
      description
        "Temperature low warning status, boolean, true if warning is raised, false if warning is not raised.";
    }
  }

  grouping live_ncs_supply-voltage-threshold-group {
    description
      "Group of Supply Voltage alarm and warning operational data leafs.";
    leaf high-alarm-threshold {
      type cntypes:live_ncs_decimal-2-dig;
      units "V";
      description
        "Supply voltage high alarm threshold, in volts (V).";
    }
    leaf low-alarm-threshold {
      type cntypes:live_ncs_decimal-2-dig;
      units "V";
      description
        "Supply voltage low alarm threshold, in volts (V).";
    }
    leaf high-warning-threshold {
      type cntypes:live_ncs_decimal-2-dig;
      units "V";
      description
        "Supply voltage high warning threshold, in volts (V).";
    }
    leaf low-warning-threshold {
      type cntypes:live_ncs_decimal-2-dig;
      units "V";
      description
        "Supply voltage low warning threshold, in volts (V).";
    }
  }

  grouping live_ncs_supply-voltage-status-group {
    description
      "group of Supply Voltage related operational data leafs. The grouping may be used by various XCVR containers, lists, and augments.";
    leaf high-alarm-status {
      type boolean;
      description
        "Supply voltage high alarm status, boolean, true if alarm is raised, false if alarm is not raised.";
    }
    leaf low-alarm-status {
      type boolean;
      description
        "Supply voltage low alarm status, boolean, true if alarm is raised, false if alarm is not raised.";
    }
    leaf high-warning-status {
      type boolean;
      description
        "Supply voltage high warning status, boolean, true if warning is raised, false if warning is not raised.";
    }
    leaf low-warning-status {
      type boolean;
      description
        "Supply voltage low warning status, boolean, true if warning is raised, false if warning is not raised.";
    }
  }

  grouping optical-power-group {
    description
      "Group of optical power related operational data leafs. Can be used for Rx or Tx";
    // NCS drop config false leaf actual
    // NCS drop config false leaf maximum
    // NCS drop config false leaf minimum
    // NCS drop config false leaf 'maximum-recorded-time'
    // NCS drop config false leaf 'minimum-recorded-time'
  }

  grouping optical-power-threshold-group {
    description
      "Group of optical power alarm related operational data leafs. Can be used for Rx or Tx.";
    // NCS drop config false leaf 'high-alarm-threshold'
    // NCS drop config false leaf 'low-alarm-threshold'
    // NCS drop config false leaf 'high-warning-threshold'
    // NCS drop config false leaf 'low-warning-threshold'
  }

  grouping optical-power-status-group {
    description
      "Group of optical power status related operational data leafs. Can be used for Rx or Tx";
    // NCS drop config false leaf 'high-alarm-status'
    // NCS drop config false leaf 'low-alarm-status'
    // NCS drop config false leaf 'high-warning-status'
    // NCS drop config false leaf 'low-warning-status'
  }

  grouping optical-bias-status-group {
    description
      "Group of optical bias related operational data leafs.";
    // NCS drop config false leaf 'high-alarm-status'
    // NCS drop config false leaf 'low-alarm-status'
    // NCS drop config false leaf 'high-warning-status'
    // NCS drop config false leaf 'low-warning-status'
  }

  grouping temperature-threshold-group {
    description
      "Group of XCVR temperature alarm and warning operational data leafs.";
    // NCS drop config false leaf 'high-alarm-threshold'
    // NCS drop config false leaf 'low-alarm-threshold'
    // NCS drop config false leaf 'high-warning-threshold'
    // NCS drop config false leaf 'low-warning-threshold'
  }

  grouping temperature-status-group {
    description
      "Group of XCVR temperature related operational data leafs.";
    // NCS drop config false leaf 'high-alarm-status'
    // NCS drop config false leaf 'low-alarm-status'
    // NCS drop config false leaf 'high-warning-status'
    // NCS drop config false leaf 'low-warning-status'
  }

  grouping supply-voltage-threshold-group {
    description
      "Group of Supply Voltage alarm and warning operational data leafs.";
    // NCS drop config false leaf 'high-alarm-threshold'
    // NCS drop config false leaf 'low-alarm-threshold'
    // NCS drop config false leaf 'high-warning-threshold'
    // NCS drop config false leaf 'low-warning-threshold'
  }

  grouping supply-voltage-status-group {
    description
      "group of Supply Voltage related operational data leafs. The grouping may be used by various XCVR containers, lists, and augments.";
    // NCS drop config false leaf 'high-alarm-status'
    // NCS drop config false leaf 'low-alarm-status'
    // NCS drop config false leaf 'high-warning-status'
    // NCS drop config false leaf 'low-warning-status'
  }

  augment "/ncs:devices/ncs:device/ncs:netconf-notifications/ncs:received-notifications/ncs:notification/ncs:data" {
    container xcvr-events {
      presence "";
      config false;
      list xcvr-event {
        description
          "Defines xcvr related events and associated data used to publish change in the state of the xcvr instance.";
        leaf name {
          type string;
        }
        list event-list {
          leaf event-type {
            type string;
            description
              "The event-type for the notification. 'any' means any event-type";
          }
        }
        leaf lane-number-0 {
          type cntypes:ncs_rpc_notif_lanes-number;
          description
            "Lane number 0 of XCVR.";
        }
        leaf lane-number-1 {
          type cntypes:ncs_rpc_notif_lanes-number;
          description
            "Lane number 1 of XCVR.";
        }
        leaf lane-number-2 {
          type cntypes:ncs_rpc_notif_lanes-number;
          description
            "Lane number 2 of XCVR.";
        }
        leaf lane-number-3 {
          type cntypes:ncs_rpc_notif_lanes-number;
          description
            "Lane number 3 of XCVR.";
        }
        leaf operational-state {
          type string;
          description
            "Transceiver operational state change (link state, error state)";
        }
        leaf operational-speed {
          type string;
          description
            "Transceiver operational speed change";
        }
        leaf xcvr-inserted {
          type empty;
          description
            "Transceiver is inserted";
        }
        leaf xcvr-removed {
          type empty;
          description
            "Transceiver is removed";
        }
        leaf optic-temp-high-alarm-threshold {
          type empty;
          description
            "Temperature went over the maximum temperature threshold.";
        }
        leaf optic-temp-low-alarm-threshold {
          type empty;
          description
            "Temperature went below the minimum temperature threshold.";
        }
        leaf optic-temp-normal {
          type empty;
          description
            "Temperature has returned to normal having previously crossed an alarm threshold.";
        }
        leaf optic-unrecognized-unqualified {
          type empty;
          description
            "An unrecognized or Unqualified Transceiver is present.";
        }
        leaf optic-unrecognized-vendor {
          type string;
          description
            "An unrecognized Vendor Transceiver is present.";
        }
        leaf optic-unrecognized-part-number {
          type string;
          description
            "An unrecognized Part Number for a Transceiver.";
        }
        leaf optic-capability-incompatible {
          type empty;
          description
            "is xcvr optic capability compatible or not";
        }
        leaf tx-power-bias-high-alarm-threshold {
          type empty;
          description
            "Tx high power threshold";
        }
        leaf tx-power-bias-low-alarm-threshold {
          type empty;
          description
            "Tx low power threshold";
        }
        leaf tx-power-bias-normal {
          type empty;
          description
            "Tx Power Bias has returned to normal having previously crossed a threshold.";
        }
        leaf rx-power-bias-high-alarm-threshold {
          type empty;
          description
            "Rx high power threshold";
        }
        leaf rx-power-bias-low-alarm-threshold {
          type empty;
          description
            "Rx low power threshold";
        }
        leaf rx-power-bias-normal {
          type empty;
          description
            "Rx Power Bias has returned to normal having previously crossed a threshold.";
        }
        leaf laser-bias-high-alarm-threshold {
          type empty;
          description
            "Laser Bias high threshold";
        }
        leaf laser-bias-low-alarm-threshold {
          type empty;
          description
            "Laser Bias low threshold";
        }
        leaf laser-bias-normal {
          type empty;
          description
            "Laser Bias has returned to normal having previously crossed a threshold.";
        }
        leaf laser-temperature-high-alarm-threshold {
          type empty;
          description
            "Laser Temperature high threshold";
        }
        leaf laser-temperature-low-alarm-threshold {
          type empty;
          description
            "Laser Temperature low threshold";
        }
        leaf laser-temperature-normal {
          type empty;
          description
            "Laser Temperature has returned to normal having previously crossed a threshold.";
        }
        leaf rx-los {
          type empty;
          description
            "Transceiver detected Rx Loss of Signal.";
        }
        leaf rx-los-cleared {
          type empty;
          description
            "Transceiver no longer detected Rx Loss of Signal.";
        }
      }
    }
  }
  augment "/ncs:devices/ncs:device/ncs:config" {
    container xcvrs {
      tailf:ncs-device-type "netconf";
      tailf:display-when "not(../../ncs:module) or ../../ncs:module[ncs:name='ciena-packet-xcvr']";
      description
        "Transceivers (XCVR) configuration and operational data.";
      list xcvr {
        key "xcvr-id";
        description
          "Transceiver (XCVR) list.";
        leaf xcvr-id {
          type cntypes:name-string;
          mandatory true;
          description
            "Unique, access identifier string of the XCVR (e.g. '1/1'). Key value for the XCVR List.";
        }
        // NCS drop config false container id
        container state {
          description
            "State information of this XCVR instance.";
          leaf admin-state {
            type cntypes:enabled-disabled-enum;
            description
              "Whether Admin State is enabled or disabled for this XCVR's PTP.";
          }
          // NCS drop config false leaf 'operational-state'
          // NCS drop config false leaf 'power-state'
          // NCS drop config false leaf 'actual-mode'
          // NCS drop config false leaf 'rx-los'
        }
        container properties {
          description
            "All the Configurable and operational data of this XCVR instance.";
          // NCS drop config false leaf type
          leaf mode {
            type cntypes:xcvr-mode;
            mandatory true;
            description
              "Mode of the XCVR.";
          }
          // NCS drop config false leaf 'number-of-lanes'
          // NCS drop config false leaf-list 'child-ptp-id'
          leaf fec-type {
            type cntypes:xcvr-fec-type;
            description
              "FEC type of the XCVR.";
          }
          // NCS drop config false container 'vendor-data'
          // NCS drop config false container diagnostics
          // NCS drop config false leaf 'xcvr-event-type'
        }
      }
    }
  }
  augment "/ncs:devices/ncs:device/ncs:live-status" {
    container xcvrs {
      tailf:ncs-device-type "netconf";
      tailf:display-when "not(../../ncs:module) or ../../ncs:module[ncs:name='ciena-packet-xcvr'] or (../../ncs:live-status-protocol[not(ncs:capability)]) or (../../ncs:live-status-protocol/ncs:capability/ncs:module[.='ciena-packet-xcvr'])";
      description
        "Transceivers (XCVR) configuration and operational data.";
      list xcvr {
        key "xcvr-id";
        description
          "Transceiver (XCVR) list.";
        leaf xcvr-id {
          type cntypes:live_ncs_name-string;
          // NCS drop mandatory statement
          description
            "Unique, access identifier string of the XCVR (e.g. '1/1'). Key value for the XCVR List.";
        }
        container id {
          description
            "Identification information of this XCVR instance.";
          leaf name {
            type cntypes:live_ncs_name-string;
            description
              "Name of the XCVR transceiver. Auto generated, and cannot be modified.";
          }
        }
        container state {
          description
            "State information of this XCVR instance.";
          leaf admin-state {
            type cntypes:live_ncs_enabled-disabled-enum;
            description
              "Whether Admin State is enabled or disabled for this XCVR's PTP.";
          }
          leaf operational-state {
            type live_ncs_xcvr-op-enum;
            description
              "Operational state of this XCVR, it will be empty by default.";
          }
          leaf power-state {
            type cntypes:live_ncs_power-state;
            description
              "Power State of the XCVR. If it is in automatic (normal) or shutdown (low power).";
          }
          leaf actual-mode {
            type cntypes:live_ncs_xcvr-mode;
            description
              "Actual mode of the XCVR.";
          }
          leaf rx-los {
            type cntypes:live_ncs_yes-no-enum;
            description
              "RX-LOS state of this XCVR.";
          }
        }
        container properties {
          description
            "All the Configurable and operational data of this XCVR instance.";
          leaf type {
            type cntypes:live_ncs_xcvr-type;
            description
              "Transceiver type, different transceiver types will have different operational data. Type depends on what is physically plugged in.";
          }
          leaf mode {
            type cntypes:live_ncs_xcvr-mode;
            // NCS drop mandatory statement
            description
              "Mode of the XCVR.";
          }
          leaf number-of-lanes {
            type cntypes:live_ncs_lanes-number;
            description
              "Number of lanes this tranceiver has. Only applicable if a transceiver is plugged in.";
          }
          leaf-list child-ptp-id {
            type cntypes:live_ncs_name-string;
            description
              "The child ptp this xcvr is associated with.";
          }
          leaf fec-type {
            type cntypes:live_ncs_xcvr-fec-type;
            description
              "FEC type of the XCVR.";
          }
          container vendor-data {
            description
              "vendor-data, the container or its subcontainers may be augmented by pluggable or modem specific yang modules, depending on transceiver type.";
            container id {
              description
                "XCVR Vendor ID";
              container ciena-id {
                description
                  "If the plugged transceiver is a Ciena product, display the Ciena product information. The leafs in this container will be blank if the transceiver is not plugged in or if it is not a Ciena product.";
                leaf ciena-item-number {
                  type cntypes:live_ncs_string-maxl-32;
                  description
                    "If the plugged transceiver is a Ciena product, display the product item number. If it is not a Ciena product or if nothing is plugged in, this field will be blank";
                }
                leaf revision {
                  type cntypes:live_ncs_string-maxl-32;
                  description
                    "If the plugged transceiver is a Ciena product, display the Ciena revision in the format of <prefix>.<number>.<suffix>. If it is not a Ciena product or if nothing is plugged in, this field will be blank";
                }
                leaf description {
                  type cntypes:live_ncs_string-maxl-254;
                  description
                    "If the plugged transceiver is a Ciena product, display the Ciena description. If it is not a Ciena product or if nothing is plugged in, this field will be blank";
                }
              }
              container vendor-id {
                description
                  "Display the transceiver vendor identification information.";
                leaf name {
                  type cntypes:live_ncs_string-maxl-32;
                  description
                    "Name of the Vendor that produced this transceiver. For Ciena transceiver, the value will be Ciena.";
                }
                leaf part-number {
                  type cntypes:live_ncs_string-maxl-32;
                  description
                    "Vendor part number of the transceiver.";
                }
                leaf revision {
                  type cntypes:live_ncs_string-maxl-32;
                  description
                    "Vendor Revision of the transceiver.";
                }
                leaf serial-number {
                  type cntypes:live_ncs_string-maxl-32;
                  description
                    "Vendor serial number of the XCVR transceiver.";
                }
                leaf manufactured-date {
                  type cntypes:live_ncs_string-maxl-16;
                  description
                    "Manufactured Date, in the format of mm/dd/yy.";
                }
              }
            }
            container properties {
              description
                "XCVR vendor data properties.";
              container device-id {
                description
                  "Vendor Device ID properties.";
                leaf connector-type {
                  type cntypes:live_ncs_connector-type-desc-enum;
                  description
                    "Human readable description of Vendor's connector type byte value. Reference SFF-8024, table 4-3";
                }
              }
              container transmitter {
                description
                  "Transmitter properties.";
                leaf nominal-bit-rate {
                  type cntypes:live_ncs_string-maxl-16;
                  units "Gbps";
                  description
                    "Bit rate, nominal, in Gbps for pluggable XCVRs. For modem XCVR objects, this will be OTUCn.";
                }
              }
              container diagnostic-monitoring {
                description
                  "XCVR diagnostic monitoring properties.";
                leaf rx-power-measurement {
                  type enumeration {
                    enum "OMA" {
                      description
                        "Optical Modulation Amplitude (OMA) Rx measurement type.";
                    }
                    enum "average-power" {
                      description
                        "Average Power Rx measurement type.";
                    }
                    enum "yes" {
                      description
                        "yes";
                    }
                    enum "no" {
                      description
                        "no";
                    }
                  }
                  description
                    "Rx power measurement, bit 3 of diagnostic monitoring type. Reference SFF 8472 section 8.8 and table 8-5 for detail.";
                }
                leaf tx-power-measurement {
                  type enumeration {
                    enum "yes" {
                      description
                        "yes";
                    }
                    enum "no" {
                      description
                        "no";
                    }
                  }
                  description
                    "Tx power measurement, related to diagnostic monitoring type.";
                }
              }
              list supported-modes {
                key "xcvr-mode";
                description
                  "A matrix of supported capabilities for each of the supported
                   XCVR modes for this object. XCVR type specific capabilities
                   may be augmented into this list.";
                leaf xcvr-mode {
                  type cntypes:live_ncs_xcvr-mode;
                  description
                    "The XCVR mode to which the capabilities are ascribed. If a
                     mode is not listed, then it is not supported on this XCVR
                     object.";
                }
              }
            }
          }
          container diagnostics {
            description
              "XCVR diagnostic data, the container or its subcontainers may be augmented by pluggable or modem specific yang modules, depending on the transceiver type.";
            container device {
              description
                "container for all common device diagnostic data fields for the XCVR.";
              container temperature {
                description
                  "XCVR temperature measurements.";
                leaf actual {
                  type int16;
                  units "C";
                  description
                    "Temperature Status, actual temperature in degrees Celsius (C). Range must be between -128 and 128.";
                }
                container status {
                  description
                    "XCVR temperature status.";
                  uses xcvr:live_ncs_temperature-status-group;
                }
                container threshold {
                  description
                    "XCVR temperature threshold.";
                  uses xcvr:live_ncs_temperature-threshold-group;
                }
              }
            }
            list lane {
              key "lane-number";
              description
                "List of common xcvr lane diagnostic data fields of the XCVR.";
              leaf lane-number {
                type cntypes:live_ncs_lanes-number;
                description
                  "Lane number of XCVR.";
              }
              container rx-power {
                description
                  "Lane Tx power measurements.";
                leaf actual {
                  type cntypes:live_ncs_decimal-1-dig;
                  units "dBm";
                  description
                    "Actual Rx optical power in dBm.";
                }
                container status {
                  description
                    "Rx power status.";
                  uses xcvr:live_ncs_optical-power-status-group;
                }
                container threshold {
                  description
                    "Rx power threshold.";
                  uses xcvr:live_ncs_optical-power-threshold-group;
                }
              }
              container tx-power {
                description
                  "Lane Tx power measurements.";
                leaf actual {
                  type cntypes:live_ncs_decimal-1-dig;
                  units "dBm";
                  description
                    "Actual Tx optical power in dBm.";
                }
                container status {
                  description
                    "Tx power status.";
                  uses xcvr:live_ncs_optical-power-status-group;
                }
                container threshold {
                  description
                    "Tx power threshold.";
                  uses xcvr:live_ncs_optical-power-threshold-group;
                }
              }
              container laser-temperature {
                description
                  "Lane Laser Temperature measurements.";
                leaf actual {
                  type int16;
                  units "C";
                  description
                    "Temperature Status, actual temperature in degrees Celsius (C). Range must be between -128 and 128.";
                }
                container status {
                  description
                    "Lane Laser temperature status.";
                  uses xcvr:live_ncs_temperature-status-group;
                }
                container threshold {
                  description
                    "Lane Laser temperature threshold.";
                  uses xcvr:live_ncs_temperature-threshold-group;
                }
              }
            }
          }
          leaf xcvr-event-type {
            type live_ncs_xcvr-event-type;
            description
              "Description of the xcvr event types";
          }
        }
      }
    }
  }
  augment "/ncs:devices/ncs:template/ncs:ned-id/ncs:config" {
    container xcvrs {
      description
        "Transceivers (XCVR) configuration and operational data.";
      list xcvr {
        // NCS patched for predictable order
        ordered-by user;
        key "xcvr-id";
        description
          "Transceiver (XCVR) list.";
        leaf xcvr-id {
          type cntypes:ncs_template_name-string;
          // NCS drop mandatory statement
          description
            "Unique, access identifier string of the XCVR (e.g. '1/1'). Key value for the XCVR List.";
        }
        // NCS drop config false container id
        container state {
          description
            "State information of this XCVR instance.";
          leaf admin-state {
            type cntypes:ncs_template_enabled-disabled-enum;
            description
              "Whether Admin State is enabled or disabled for this XCVR's PTP.";
          }
          // NCS drop config false leaf 'operational-state'
          // NCS drop config false leaf 'power-state'
          // NCS drop config false leaf 'actual-mode'
          // NCS drop config false leaf 'rx-los'
        }
        container properties {
          description
            "All the Configurable and operational data of this XCVR instance.";
          // NCS drop config false leaf type
          leaf mode {
            type cntypes:ncs_template_xcvr-mode;
            // NCS drop mandatory statement
            description
              "Mode of the XCVR.";
          }
          // NCS drop config false leaf 'number-of-lanes'
          // NCS drop config false leaf-list 'child-ptp-id'
          leaf fec-type {
            type cntypes:ncs_template_xcvr-fec-type;
            description
              "FEC type of the XCVR.";
          }
          // NCS drop config false container 'vendor-data'
          // NCS drop config false container diagnostics
          // NCS drop config false leaf 'xcvr-event-type'
        }
      }
    }
  }
}
