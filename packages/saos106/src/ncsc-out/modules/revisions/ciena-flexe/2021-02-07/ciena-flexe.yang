module ciena-flexe {
  // Generated by yanger -t ncs
  tailf:mount-id "saos106-nc-1.0:saos106-nc-1.0";
  tailf:ncs-device-type "netconf";

  namespace "http://www.ciena.com/ns/yang/ciena-flexe";
  prefix ciena-flexe;

  import openconfig-interfaces {
    prefix oc-if;
  }
  import ciena-openconfig-interfaces {
    prefix cn-oc-if;
  }
  import ciena-types {
    prefix ciena;
  }
  import ciena-packet-typedefs {
    prefix cntypes;
  }
  import ciena-packet-ptp {
    prefix cn-pkt-ptp;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data definition for the
     management of FlexE related parameters.

     Copyright (c) 2020 Ciena Corporation.  All rights
     reserved.

     All information contained herein is, and remains
     the property of Ciena Corporation. Dissemination of this
     information or reproduction of this material is strictly
     forbidden unless prior written permission is obtained from
     Ciena Corporation.";

  revision 2021-02-07 {
    description
      "Following changes have been added.
         - Addition of FlexE port alarm status.
         - Addition of FlexE group and FlexE port notifications.
         - Addition of min-elements restriction for FlexE phys.
         - change of L2-L3-mapped to L2-mapped";
    reference "OIF Implementation Agreement Flex Ethernet 2.1";
  }
  revision 2020-02-07 {
    description
      "Initial Version.";
    reference "OIF Implementation Agreement Flex Ethernet 2.1";
  }

  typedef ncs_template_name-string {
    type string;
    description
      "A text string of up to 45 characters.";
  }

  typedef ncs_template_flexe-port-ref {
    type string;
    description
      "This type is used by the data models that needs to reference
       configured flexe ports.";
  }

  typedef ncs_template_flexe-group-ref {
    type string;
    description
      "This type is used by the data models that needs to reference
       configured flexe groups.";
  }

  typedef ncs_template_flexe-channel-ref {
    type string;
    description
      "This type is used by the data models that needs to reference
       configured flexe channels.";
  }

  typedef ncs_template_flexe-port-event-type {
    type string;
    description
      "A generic FlexE port event type describing the type of events/notifications.";
  }

  typedef ncs_template_flexe-group-event-type {
    type string;
    description
      "A generic FlexE group event type describing the type of events/notifications.";
  }

  typedef ncs_rpc_notif_name-string {
    type string {
      length "1..45";
    }
    description
      "A text string of up to 45 characters.";
  }

  typedef ncs_rpc_notif_flexe-port-ref {
    type string;
    description
      "This type is used by the data models that needs to reference
       configured flexe ports.";
  }

  typedef ncs_rpc_notif_flexe-group-ref {
    type string;
    description
      "This type is used by the data models that needs to reference
       configured flexe groups.";
  }

  typedef ncs_rpc_notif_flexe-channel-ref {
    type string;
    description
      "This type is used by the data models that needs to reference
       configured flexe channels.";
  }

  typedef ncs_rpc_notif_flexe-port-event-type {
    type enumeration {
      enum "flexe-calendar-mismatch" {
        description
          "FlexE group calendar mismatch";
      }
      enum "group-id-mismatch" {
        description
          "FlexE group-ID mismatch alarm";
      }
      enum "phy-id-mismatch" {
        description
          "FlexE PHY ID mismatch";
      }
      enum "loss-of-oh-frame" {
        description
          "Loss of overhead frame error";
      }
      enum "loss-of-oh-multi-frame" {
        description
          "Loss of overhead multi frame error";
      }
      enum "c-bit-error" {
        description
          "FlexE overhead has C-bit error";
      }
      enum "crc-error" {
        description
          "FlexE overhead CRC-16 error";
      }
      enum "remote-phy-failure-error" {
        description
          "Remote PHY failure error in FlexE overhead";
      }
      enum "oh-block-1-alarm" {
        description
          "Block 1 error in FlexE overhead";
      }
      enum "sync-config-mismatch-alarm" {
        description
          "Synchronization configuration mismatch alarm";
      }
    }
    description
      "A generic FlexE port event type describing the type of events/notifications.";
  }

  typedef ncs_rpc_notif_flexe-group-event-type {
    type enumeration {
      enum "phy-map-mismatch" {
        description
          "FlexE PHY map mismatch";
      }
      enum "group-deskew" {
        description
          "FlexE group deskew error";
      }
    }
    description
      "A generic FlexE group event type describing the type of events/notifications.";
  }

  typedef live_ncs_name-string {
    type string {
      length "1..45";
    }
    description
      "A text string of up to 45 characters.";
  }

  typedef live_ncs_flexe-port-ref {
    type leafref {
      path "/ncs:devices/ncs:device/ncs:live-status/ciena-flexe:flexe-ports/ciena-flexe:flexe-port/ciena-flexe:name" {
        tailf:xpath-root 3;
      }
    }
    description
      "This type is used by the data models that needs to reference
       configured flexe ports.";
  }

  typedef live_ncs_flexe-group-ref {
    type leafref {
      path "/ncs:devices/ncs:device/ncs:live-status/ciena-flexe:flexe-groups/ciena-flexe:flexe-group/ciena-flexe:name" {
        tailf:xpath-root 3;
      }
    }
    description
      "This type is used by the data models that needs to reference
       configured flexe groups.";
  }

  typedef live_ncs_flexe-channel-ref {
    type leafref {
      path "/ncs:devices/ncs:device/ncs:live-status/ciena-flexe:flexe-channels/ciena-flexe:flexe-channel/ciena-flexe:name" {
        tailf:xpath-root 3;
      }
    }
    description
      "This type is used by the data models that needs to reference
       configured flexe channels.";
  }

  typedef live_ncs_flexe-port-event-type {
    type enumeration {
      enum "flexe-calendar-mismatch" {
        description
          "FlexE group calendar mismatch";
      }
      enum "group-id-mismatch" {
        description
          "FlexE group-ID mismatch alarm";
      }
      enum "phy-id-mismatch" {
        description
          "FlexE PHY ID mismatch";
      }
      enum "loss-of-oh-frame" {
        description
          "Loss of overhead frame error";
      }
      enum "loss-of-oh-multi-frame" {
        description
          "Loss of overhead multi frame error";
      }
      enum "c-bit-error" {
        description
          "FlexE overhead has C-bit error";
      }
      enum "crc-error" {
        description
          "FlexE overhead CRC-16 error";
      }
      enum "remote-phy-failure-error" {
        description
          "Remote PHY failure error in FlexE overhead";
      }
      enum "oh-block-1-alarm" {
        description
          "Block 1 error in FlexE overhead";
      }
      enum "sync-config-mismatch-alarm" {
        description
          "Synchronization configuration mismatch alarm";
      }
    }
    description
      "A generic FlexE port event type describing the type of events/notifications.";
  }

  typedef live_ncs_flexe-group-event-type {
    type enumeration {
      enum "phy-map-mismatch" {
        description
          "FlexE PHY map mismatch";
      }
      enum "group-deskew" {
        description
          "FlexE group deskew error";
      }
    }
    description
      "A generic FlexE group event type describing the type of events/notifications.";
  }

  typedef name-string {
    type string {
      length "1..45";
    }
    description
      "A text string of up to 45 characters.";
  }

  typedef flexe-port-ref {
    type leafref {
      path "/ncs:devices/ncs:device/ncs:config/ciena-flexe:flexe-ports/ciena-flexe:flexe-port/ciena-flexe:name" {
        tailf:xpath-root 3;
      }
    }
    description
      "This type is used by the data models that needs to reference
       configured flexe ports.";
  }

  typedef flexe-group-ref {
    type leafref {
      path "/ncs:devices/ncs:device/ncs:config/ciena-flexe:flexe-groups/ciena-flexe:flexe-group/ciena-flexe:name" {
        tailf:xpath-root 3;
      }
    }
    description
      "This type is used by the data models that needs to reference
       configured flexe groups.";
  }

  typedef flexe-channel-ref {
    type leafref {
      path "/ncs:devices/ncs:device/ncs:config/ciena-flexe:flexe-channels/ciena-flexe:flexe-channel/ciena-flexe:name" {
        tailf:xpath-root 3;
      }
    }
    description
      "This type is used by the data models that needs to reference
       configured flexe channels.";
  }

  typedef flexe-port-event-type {
    type enumeration {
      enum "flexe-calendar-mismatch" {
        description
          "FlexE group calendar mismatch";
      }
      enum "group-id-mismatch" {
        description
          "FlexE group-ID mismatch alarm";
      }
      enum "phy-id-mismatch" {
        description
          "FlexE PHY ID mismatch";
      }
      enum "loss-of-oh-frame" {
        description
          "Loss of overhead frame error";
      }
      enum "loss-of-oh-multi-frame" {
        description
          "Loss of overhead multi frame error";
      }
      enum "c-bit-error" {
        description
          "FlexE overhead has C-bit error";
      }
      enum "crc-error" {
        description
          "FlexE overhead CRC-16 error";
      }
      enum "remote-phy-failure-error" {
        description
          "Remote PHY failure error in FlexE overhead";
      }
      enum "oh-block-1-alarm" {
        description
          "Block 1 error in FlexE overhead";
      }
      enum "sync-config-mismatch-alarm" {
        description
          "Synchronization configuration mismatch alarm";
      }
    }
    description
      "A generic FlexE port event type describing the type of events/notifications.";
  }

  typedef flexe-group-event-type {
    type enumeration {
      enum "phy-map-mismatch" {
        description
          "FlexE PHY map mismatch";
      }
      enum "group-deskew" {
        description
          "FlexE group deskew error";
      }
    }
    description
      "A generic FlexE group event type describing the type of events/notifications.";
  }

  grouping ncs_template_flexe-channel-slot {
    description
      "Slots allocated for a FlexE channel.";
    leaf phy-number-in-group {
      type string;
      description
        "PHY number index from the list of PHYs associated to
         the FlexE group.

         Refer to the clause 6.1 in FlexE IA 2.1.
         For 100GBASE-R, the FlexE PHY num and the 100G
         FlexE instance num are the same and in the range
         [1-254]; For 200GBASE-R, each PHY num is in the
         range [1-126]. For 400GBASE-R, each PHY num is
         in the range [1-62]. For 50GBASE-R, each PHY num is
         in the range [1-126].";
    }
    leaf slot-id {
      type string;
      description
        "Slot number within the list of slots associated to the PHY.
         Ex: For 100G PHY range is [1..20]
            For 200G PHY range is [1..40]
            For 400G PHY range is [1..80]";
    }
  }

  grouping ncs_template_flexe-group-slot {
    description
      "Slots allocated for a FlexE channel.";
    leaf phy-number-in-group {
      type string;
      description
        "PHY number the slot resides in.";
    }
    leaf slot-id {
      type string;
      description
        "Slot number within the PHY.";
    }
    leaf associated-flexe-channel {
      type ncs_template_name-string;
      description
        "Name of FlexE channel this slot is associated to.";
    }
  }

  grouping ncs_template_flexe-group-oh-status-grouping {
    description
      "FlexE group overhead status";
    leaf flexe-calendar-mismatch {
      type string;
      // NCS drop default statement
      description
        "FlexE group calendar mismatch";
    }
    leaf group-id-mismatch {
      type string;
      // NCS drop default statement
      description
        "FlexE group-ID mismatch alarm";
    }
    leaf group-deskew {
      type string;
      // NCS drop default statement
      description
        "FlexE group deskew error";
    }
    leaf phy-id-mismatch {
      type string;
      // NCS drop default statement
      description
        "FlexE PHY ID mismatch";
    }
    leaf phy-map-mismatch {
      type string;
      // NCS drop default statement
      description
        "FlexE PHY map mismatch";
    }
    leaf loss-of-oh-frame {
      type string;
      // NCS drop default statement
      description
        "Loss of overhead frame error";
    }
    leaf loss-of-oh-multi-frame {
      type string;
      // NCS drop default statement
      description
        "Loss of overhead multi frame error";
    }
    leaf c-bit-error {
      type string;
      // NCS drop default statement
      description
        "FlexE overhead has C-bit error";
    }
    leaf crc-error {
      type string;
      // NCS drop default statement
      description
        "FlexE overhead CRC-16 error";
    }
    leaf remote-phy-failure-error {
      type string;
      // NCS drop default statement
      description
        "Remote PHY failure error in FlexE overhead";
    }
    leaf sync-config-mismatch-error {
      type string;
      // NCS drop default statement
      description
        "Synchronization configuration mismatch error";
    }
    leaf oh-block-1-error {
      type string;
      // NCS drop default statement
      description
        "Overhead block 1 error in FlexE overhead";
    }
  }

  grouping ncs_template_flexe-port-oh-status-grouping {
    description
      "FlexE group overhead status";
    leaf phy-calendar-mismatch {
      type string;
      // NCS drop default statement
      description
        "FlexE group calendar mismatch";
    }
    leaf phy-id-mismatch {
      type string;
      // NCS drop default statement
      description
        "FlexE PHY ID mismatch";
    }
    leaf group-id-mismatch {
      type string;
      // NCS drop default statement
      description
        "FlexE group-ID mismatch alarm";
    }
    leaf loss-of-oh-frame {
      type string;
      // NCS drop default statement
      description
        "Loss of overhead frame error";
    }
    leaf loss-of-oh-multi-frame {
      type string;
      // NCS drop default statement
      description
        "Loss of overhead multi frame error";
    }
    leaf c-bit-error {
      type string;
      // NCS drop default statement
      description
        "FlexE overhead has C-bit error";
    }
    leaf crc-error {
      type string;
      // NCS drop default statement
      description
        "FlexE overhead CRC-16 error";
    }
    leaf remote-phy-failure-error {
      type string;
      // NCS drop default statement
      description
        "Remote PHY failure error in FlexE overhead";
    }
    leaf sync-config-mismatch-error {
      type string;
      // NCS drop default statement
      description
        "Synchronization configuration mismatch error";
    }
    leaf oh-block-1-error {
      type string;
      // NCS drop default statement
      description
        "Overhead block 1 error in FlexE overhead";
    }
  }

  grouping ncs_rpc_notif_flexe-channel-slot {
    description
      "Slots allocated for a FlexE channel.";
    leaf phy-number-in-group {
      type string;
      description
        "PHY number index from the list of PHYs associated to
         the FlexE group.

         Refer to the clause 6.1 in FlexE IA 2.1.
         For 100GBASE-R, the FlexE PHY num and the 100G
         FlexE instance num are the same and in the range
         [1-254]; For 200GBASE-R, each PHY num is in the
         range [1-126]. For 400GBASE-R, each PHY num is
         in the range [1-62]. For 50GBASE-R, each PHY num is
         in the range [1-126].";
    }
    leaf slot-id {
      type uint32 {
        range "1 .. 80";
      }
      description
        "Slot number within the list of slots associated to the PHY.
         Ex: For 100G PHY range is [1..20]
            For 200G PHY range is [1..40]
            For 400G PHY range is [1..80]";
    }
  }

  grouping ncs_rpc_notif_flexe-group-slot {
    description
      "Slots allocated for a FlexE channel.";
    leaf phy-number-in-group {
      type uint32 {
        range "1 .. 254";
      }
      description
        "PHY number the slot resides in.";
    }
    leaf slot-id {
      type uint32 {
        range "1 .. 80";
      }
      description
        "Slot number within the PHY.";
    }
    leaf associated-flexe-channel {
      type ncs_rpc_notif_name-string;
      description
        "Name of FlexE channel this slot is associated to.";
    }
  }

  grouping ncs_rpc_notif_flexe-group-oh-status-grouping {
    description
      "FlexE group overhead status";
    leaf flexe-calendar-mismatch {
      type boolean;
      default "false";
      description
        "FlexE group calendar mismatch";
    }
    leaf group-id-mismatch {
      type boolean;
      default "false";
      description
        "FlexE group-ID mismatch alarm";
    }
    leaf group-deskew {
      type boolean;
      default "false";
      description
        "FlexE group deskew error";
    }
    leaf phy-id-mismatch {
      type boolean;
      default "false";
      description
        "FlexE PHY ID mismatch";
    }
    leaf phy-map-mismatch {
      type boolean;
      default "false";
      description
        "FlexE PHY map mismatch";
    }
    leaf loss-of-oh-frame {
      type boolean;
      default "false";
      description
        "Loss of overhead frame error";
    }
    leaf loss-of-oh-multi-frame {
      type boolean;
      default "false";
      description
        "Loss of overhead multi frame error";
    }
    leaf c-bit-error {
      type boolean;
      default "false";
      description
        "FlexE overhead has C-bit error";
    }
    leaf crc-error {
      type boolean;
      default "false";
      description
        "FlexE overhead CRC-16 error";
    }
    leaf remote-phy-failure-error {
      type boolean;
      default "false";
      description
        "Remote PHY failure error in FlexE overhead";
    }
    leaf sync-config-mismatch-error {
      type boolean;
      default "false";
      description
        "Synchronization configuration mismatch error";
    }
    leaf oh-block-1-error {
      type boolean;
      default "false";
      description
        "Overhead block 1 error in FlexE overhead";
    }
  }

  grouping ncs_rpc_notif_flexe-port-oh-status-grouping {
    description
      "FlexE group overhead status";
    leaf phy-calendar-mismatch {
      type boolean;
      default "false";
      description
        "FlexE group calendar mismatch";
    }
    leaf phy-id-mismatch {
      type boolean;
      default "false";
      description
        "FlexE PHY ID mismatch";
    }
    leaf group-id-mismatch {
      type boolean;
      default "false";
      description
        "FlexE group-ID mismatch alarm";
    }
    leaf loss-of-oh-frame {
      type boolean;
      default "false";
      description
        "Loss of overhead frame error";
    }
    leaf loss-of-oh-multi-frame {
      type boolean;
      default "false";
      description
        "Loss of overhead multi frame error";
    }
    leaf c-bit-error {
      type boolean;
      default "false";
      description
        "FlexE overhead has C-bit error";
    }
    leaf crc-error {
      type boolean;
      default "false";
      description
        "FlexE overhead CRC-16 error";
    }
    leaf remote-phy-failure-error {
      type boolean;
      default "false";
      description
        "Remote PHY failure error in FlexE overhead";
    }
    leaf sync-config-mismatch-error {
      type boolean;
      default "false";
      description
        "Synchronization configuration mismatch error";
    }
    leaf oh-block-1-error {
      type boolean;
      default "false";
      description
        "Overhead block 1 error in FlexE overhead";
    }
  }

  grouping live_ncs_flexe-channel-slot {
    description
      "Slots allocated for a FlexE channel.";
    leaf phy-number-in-group {
      type leafref {
        path "/ncs:devices/ncs:device/ncs:live-status/ciena-flexe:flexe-groups/ciena-flexe:flexe-group[name=current()/../../group-name]/ciena-flexe:flexe-phys/ciena-flexe:phy-number-in-group" {
          tailf:xpath-root 3;
        }
      }
      description
        "PHY number index from the list of PHYs associated to
         the FlexE group.

         Refer to the clause 6.1 in FlexE IA 2.1.
         For 100GBASE-R, the FlexE PHY num and the 100G
         FlexE instance num are the same and in the range
         [1-254]; For 200GBASE-R, each PHY num is in the
         range [1-126]. For 400GBASE-R, each PHY num is
         in the range [1-62]. For 50GBASE-R, each PHY num is
         in the range [1-126].";
    }
    leaf slot-id {
      type uint32 {
        range "1 .. 80";
      }
      description
        "Slot number within the list of slots associated to the PHY.
         Ex: For 100G PHY range is [1..20]
            For 200G PHY range is [1..40]
            For 400G PHY range is [1..80]";
    }
  }

  grouping live_ncs_flexe-group-slot {
    description
      "Slots allocated for a FlexE channel.";
    leaf phy-number-in-group {
      type uint32 {
        range "1 .. 254";
      }
      description
        "PHY number the slot resides in.";
    }
    leaf slot-id {
      type uint32 {
        range "1 .. 80";
      }
      description
        "Slot number within the PHY.";
    }
    leaf associated-flexe-channel {
      type live_ncs_name-string;
      description
        "Name of FlexE channel this slot is associated to.";
    }
  }

  grouping live_ncs_flexe-group-oh-status-grouping {
    description
      "FlexE group overhead status";
    leaf flexe-calendar-mismatch {
      type boolean;
      // NCS drop default statement
      description
        "FlexE group calendar mismatch";
    }
    leaf group-id-mismatch {
      type boolean;
      // NCS drop default statement
      description
        "FlexE group-ID mismatch alarm";
    }
    leaf group-deskew {
      type boolean;
      // NCS drop default statement
      description
        "FlexE group deskew error";
    }
    leaf phy-id-mismatch {
      type boolean;
      // NCS drop default statement
      description
        "FlexE PHY ID mismatch";
    }
    leaf phy-map-mismatch {
      type boolean;
      // NCS drop default statement
      description
        "FlexE PHY map mismatch";
    }
    leaf loss-of-oh-frame {
      type boolean;
      // NCS drop default statement
      description
        "Loss of overhead frame error";
    }
    leaf loss-of-oh-multi-frame {
      type boolean;
      // NCS drop default statement
      description
        "Loss of overhead multi frame error";
    }
    leaf c-bit-error {
      type boolean;
      // NCS drop default statement
      description
        "FlexE overhead has C-bit error";
    }
    leaf crc-error {
      type boolean;
      // NCS drop default statement
      description
        "FlexE overhead CRC-16 error";
    }
    leaf remote-phy-failure-error {
      type boolean;
      // NCS drop default statement
      description
        "Remote PHY failure error in FlexE overhead";
    }
    leaf sync-config-mismatch-error {
      type boolean;
      // NCS drop default statement
      description
        "Synchronization configuration mismatch error";
    }
    leaf oh-block-1-error {
      type boolean;
      // NCS drop default statement
      description
        "Overhead block 1 error in FlexE overhead";
    }
  }

  grouping live_ncs_flexe-port-oh-status-grouping {
    description
      "FlexE group overhead status";
    leaf phy-calendar-mismatch {
      type boolean;
      // NCS drop default statement
      description
        "FlexE group calendar mismatch";
    }
    leaf phy-id-mismatch {
      type boolean;
      // NCS drop default statement
      description
        "FlexE PHY ID mismatch";
    }
    leaf group-id-mismatch {
      type boolean;
      // NCS drop default statement
      description
        "FlexE group-ID mismatch alarm";
    }
    leaf loss-of-oh-frame {
      type boolean;
      // NCS drop default statement
      description
        "Loss of overhead frame error";
    }
    leaf loss-of-oh-multi-frame {
      type boolean;
      // NCS drop default statement
      description
        "Loss of overhead multi frame error";
    }
    leaf c-bit-error {
      type boolean;
      // NCS drop default statement
      description
        "FlexE overhead has C-bit error";
    }
    leaf crc-error {
      type boolean;
      // NCS drop default statement
      description
        "FlexE overhead CRC-16 error";
    }
    leaf remote-phy-failure-error {
      type boolean;
      // NCS drop default statement
      description
        "Remote PHY failure error in FlexE overhead";
    }
    leaf sync-config-mismatch-error {
      type boolean;
      // NCS drop default statement
      description
        "Synchronization configuration mismatch error";
    }
    leaf oh-block-1-error {
      type boolean;
      // NCS drop default statement
      description
        "Overhead block 1 error in FlexE overhead";
    }
  }

  grouping flexe-channel-slot {
    description
      "Slots allocated for a FlexE channel.";
    leaf phy-number-in-group {
      type leafref {
        path "/ncs:devices/ncs:device/ncs:config/ciena-flexe:flexe-groups/ciena-flexe:flexe-group[name=current()/../../group-name]/ciena-flexe:flexe-phys/ciena-flexe:phy-number-in-group" {
          tailf:xpath-root 3;
        }
      }
      description
        "PHY number index from the list of PHYs associated to
         the FlexE group.

         Refer to the clause 6.1 in FlexE IA 2.1.
         For 100GBASE-R, the FlexE PHY num and the 100G
         FlexE instance num are the same and in the range
         [1-254]; For 200GBASE-R, each PHY num is in the
         range [1-126]. For 400GBASE-R, each PHY num is
         in the range [1-62]. For 50GBASE-R, each PHY num is
         in the range [1-126].";
    }
    leaf slot-id {
      type uint32 {
        range "1 .. 80";
      }
      description
        "Slot number within the list of slots associated to the PHY.
         Ex: For 100G PHY range is [1..20]
            For 200G PHY range is [1..40]
            For 400G PHY range is [1..80]";
    }
  }

  grouping flexe-group-slot {
    description
      "Slots allocated for a FlexE channel.";
    leaf phy-number-in-group {
      type uint32 {
        range "1 .. 254";
      }
      description
        "PHY number the slot resides in.";
    }
    leaf slot-id {
      type uint32 {
        range "1 .. 80";
      }
      description
        "Slot number within the PHY.";
    }
    leaf associated-flexe-channel {
      type name-string;
      description
        "Name of FlexE channel this slot is associated to.";
    }
  }

  grouping flexe-group-oh-status-grouping {
    description
      "FlexE group overhead status";
    leaf flexe-calendar-mismatch {
      type boolean;
      default "false";
      description
        "FlexE group calendar mismatch";
    }
    leaf group-id-mismatch {
      type boolean;
      default "false";
      description
        "FlexE group-ID mismatch alarm";
    }
    leaf group-deskew {
      type boolean;
      default "false";
      description
        "FlexE group deskew error";
    }
    leaf phy-id-mismatch {
      type boolean;
      default "false";
      description
        "FlexE PHY ID mismatch";
    }
    leaf phy-map-mismatch {
      type boolean;
      default "false";
      description
        "FlexE PHY map mismatch";
    }
    leaf loss-of-oh-frame {
      type boolean;
      default "false";
      description
        "Loss of overhead frame error";
    }
    leaf loss-of-oh-multi-frame {
      type boolean;
      default "false";
      description
        "Loss of overhead multi frame error";
    }
    leaf c-bit-error {
      type boolean;
      default "false";
      description
        "FlexE overhead has C-bit error";
    }
    leaf crc-error {
      type boolean;
      default "false";
      description
        "FlexE overhead CRC-16 error";
    }
    leaf remote-phy-failure-error {
      type boolean;
      default "false";
      description
        "Remote PHY failure error in FlexE overhead";
    }
    leaf sync-config-mismatch-error {
      type boolean;
      default "false";
      description
        "Synchronization configuration mismatch error";
    }
    leaf oh-block-1-error {
      type boolean;
      default "false";
      description
        "Overhead block 1 error in FlexE overhead";
    }
  }

  grouping flexe-port-oh-status-grouping {
    description
      "FlexE group overhead status";
    leaf phy-calendar-mismatch {
      type boolean;
      default "false";
      description
        "FlexE group calendar mismatch";
    }
    leaf phy-id-mismatch {
      type boolean;
      default "false";
      description
        "FlexE PHY ID mismatch";
    }
    leaf group-id-mismatch {
      type boolean;
      default "false";
      description
        "FlexE group-ID mismatch alarm";
    }
    leaf loss-of-oh-frame {
      type boolean;
      default "false";
      description
        "Loss of overhead frame error";
    }
    leaf loss-of-oh-multi-frame {
      type boolean;
      default "false";
      description
        "Loss of overhead multi frame error";
    }
    leaf c-bit-error {
      type boolean;
      default "false";
      description
        "FlexE overhead has C-bit error";
    }
    leaf crc-error {
      type boolean;
      default "false";
      description
        "FlexE overhead CRC-16 error";
    }
    leaf remote-phy-failure-error {
      type boolean;
      default "false";
      description
        "Remote PHY failure error in FlexE overhead";
    }
    leaf sync-config-mismatch-error {
      type boolean;
      default "false";
      description
        "Synchronization configuration mismatch error";
    }
    leaf oh-block-1-error {
      type boolean;
      default "false";
      description
        "Overhead block 1 error in FlexE overhead";
    }
  }

  augment "/ncs:devices/ncs:device/ncs:netconf-notifications/ncs:received-notifications/ncs:notification/ncs:data" {
    container flexe-group-alarm {
      presence "";
      config false;
      description
        "Generated when an alarm condition is reached on FlexE group.";
      leaf flexe-group-name {
        type ciena-flexe:ncs_rpc_notif_flexe-group-ref;
        description
          "Name of FlexE group.";
      }
      leaf alarm-type {
        type ciena-flexe:ncs_rpc_notif_flexe-group-event-type;
        description
          "Alarm type generating this notification.";
      }
    }
  }
  augment "/ncs:devices/ncs:device/ncs:netconf-notifications/ncs:received-notifications/ncs:notification/ncs:data" {
    container flexe-port-alarm {
      presence "";
      config false;
      description
        "Generated when an alarm condition is reached on FlexE port.";
      leaf flexe-port-name {
        type ciena-flexe:ncs_rpc_notif_flexe-port-ref;
        description
          "Name of FlexE port.";
      }
      leaf alarm-type {
        type ciena-flexe:ncs_rpc_notif_flexe-port-event-type;
        description
          "Alarm type generating this notification.";
      }
    }
  }
  augment "/ncs:devices/ncs:device/ncs:config" {
    container flexe-ports {
      tailf:ncs-device-type "netconf";
      tailf:display-when "not(../../ncs:module) or ../../ncs:module[ncs:name='ciena-flexe']";
      description
        "FlexE port configurations";
      list flexe-port {
        key "name";
        description
          "List of FlexE ports.";
        leaf name {
          type name-string;
          description
            "Name for FlexE port.";
        }
        leaf admin-state {
          type ciena:admin-state;
          default "enabled";
          description
            "Overall port admin state.";
        }
        leaf ptp-id {
          type leafref {
            path "/ncs:devices/ncs:device/ncs:config/cn-pkt-ptp:ptps/cn-pkt-ptp:ptp/cn-pkt-ptp:ptp-id" {
              tailf:xpath-root 3;
            }
          }
          mandatory true;
          description
            "Unique, access identifier string of the PTP (e.g., '1/1').";
        }
        leaf port-speed {
          type enumeration {
            enum "50Gb" {
              description
                "50 Gbps FlexE";
            }
            enum "100Gb" {
              description
                "100 Gbps FlexE";
            }
            enum "200Gb" {
              description
                "200 Gbps FlexE";
            }
            enum "400Gb" {
              description
                "400 Gbps FlexE";
            }
          }
          mandatory true;
          description
            "FlexE port speed.";
        }
        leaf forward-error-correction {
          type cntypes:ettp-fec-enum;
          default "auto";
          description
            "Forward error correction";
        }
      }
    }
    container flexe-groups {
      tailf:ncs-device-type "netconf";
      tailf:display-when "not(../../ncs:module) or ../../ncs:module[ncs:name='ciena-flexe']";
      description
        "FlexE group configurations";
      list flexe-group {
        key "name";
        description
          "List of FlexE groups.";
        leaf name {
          type name-string;
          description
            "Name for FlexE group.";
        }
        leaf admin-state {
          type ciena:admin-state;
          default "enabled";
          description
            "Overall FlexE group admin state.";
        }
        leaf group-number {
          type uint32 {
            range "1..254";
          }
          mandatory true;
          description
            "FlexE group number associated to the FlexE group";
        }
        leaf calendar-slot-granularity {
          type enumeration {
            enum "slot-5G" {
              value 1;
              description
                "Calendar slot is of 5G granularity";
            }
            enum "slot-25G" {
              value 2;
              description
                "Calendar slot is of 25G granularity";
            }
          }
          default "slot-5G";
          description
            "The granularity of calendar slot is 5G or 25G";
          reference "Refer to the clause 6.8 in OIF FlexE IA 2.1";
        }
        leaf phy-type {
          type enumeration {
            enum "flexe-phy-50GBASE-R" {
              value 1;
              description
                "50GBASE-R PHY";
            }
            enum "flexe-phy-100GBASE-R" {
              value 2;
              description
                "100GBASE-R PHY";
            }
            enum "flexe-phy-200GBASE-R" {
              value 3;
              description
                "200GBASE-R PHY";
            }
            enum "flexe-phy-400GBASE-R" {
              value 4;
              description
                "400GBASE-R PHY";
            }
          }
          mandatory true;
          description
            "Type of PHY used in the FlexE group, such as 50/100/200/400GBASE-R.
             All PHYs in a FlexE group should be of same type";
          reference "OIF FlexE IA 2.1";
        }
        leaf calendar {
          type enumeration {
            enum "calendar-A" {
              value 0;
              description
                "Set the A calendar configuration.";
            }
            enum "calendar-B" {
              value 1;
              description
                "Set the B calendar configuration.";
            }
          }
          default "calendar-A";
          description
            "Calendar configuration used in FlexE Mux/Demux";
        }
        leaf calendar-protocol-enable {
          type boolean;
          default "false";
          description
            "Whether calendar negotiation protocol is enabled or not.";
          reference "OIF Flex 2.1: Section 7.3.4";
        }
        list flexe-phys {
          key "phy-number-in-group";
          min-elements 1;
          description
            "List of the participating PHYs in a FlexE group";
          leaf phy-number-in-group {
            type uint32 {
              range "1 .. 254";
            }
            description
              "Refer to the clause 6.1 in FlexE IA 2.1.
               For 100GBASE-R, the FlexE PHY num and the 100G
               FlexE instance num are the same and in the range
               [1-254]; For 200GBASE-R, each PHY num is in the
               range [1-126]. For 400GBASE-R, each PHY num is
               in the range [1-62]. For 50GBASE-R, each PHY num is
               in the range [1-126]. PHY num configured in list of
               flexe-phys should be in ascending order.";
          }
          leaf local-interface {
            type ciena-flexe:flexe-port-ref;
            mandatory true;
            description
              "Local FlexE port interface related to the current
               phy-number in a FlexE group.";
          }
        }
      }
    }
    container flexe-channels {
      tailf:ncs-device-type "netconf";
      tailf:display-when "not(../../ncs:module) or ../../ncs:module[ncs:name='ciena-flexe']";
      description
        "FlexE channel configurations";
      list flexe-channel {
        key "name";
        description
          "List of FlexE channels.";
        leaf name {
          type name-string;
          description
            "Name for FlexE channel.";
        }
        leaf channel-number {
          type uint32 {
            range "1..65534";
          }
          mandatory true;
          description
            "Channel number associated to the FlexE channel.";
        }
        leaf group-name {
          type ciena-flexe:flexe-group-ref;
          mandatory true;
          description
            "Name of FlexE group to which this FlexE channel will be associated to.";
        }
        leaf channel-mapping {
          type enumeration {
            enum "L1-mapped" {
              value 1;
              description
                "L1 switching between faceplate ETTP and FlexE MAC ETTP at matched rate or
                 2 FlexE channels.";
            }
            enum "L2-mapped" {
              value 2;
              description
                "L2 forwarding between Logical port/flowpoints created over faceplate ETTPs/FlexE MAC ETTPs";
            }
          }
          default "L1-mapped";
          description
            "FlexE Datapath, traffic mapped at L1/L2/L3";
        }
        list calendar-A-slots-list {
          key "phy-number-in-group slot-id";
          description
            "List of slots allocated on Calendar A for a FlexE channel.
             Number of slots allocated for a FlexE channel is based on
             the bandwidth allocated for it. Ex: For a system with
             calendar slot granularity of 5G, a 10G FlexE channel
             would be allocated 2 slots (10G/5G)";
          uses flexe-channel-slot;
        }
        list calendar-B-slots-list {
          key "phy-number-in-group slot-id";
          description
            "List of slots allocated on Calendar B for a FlexE channel.
             Number of slots allocated for a FlexE channel is based on
             the bandwidth allocated for it. Ex: For a system with
             calendar slot granularity of 5G, a 10G FlexE-channel
             would be allocated 2 slots (10G/5G)";
          uses flexe-channel-slot;
        }
      }
    }
    container flexe-cross-connects {
      tailf:ncs-device-type "netconf";
      tailf:display-when "not(../../ncs:module) or ../../ncs:module[ncs:name='ciena-flexe']";
      description
        "FlexE cross connect configurations";
      list flexe-cross-connect {
        key "name";
        description
          "List of FlexE cross-connects.
           FlexE cross-connect can be between Faceplate standard ethernet ETTP
           and FlexE MAC ETTP or two FlexE channels";
        leaf name {
          type name-string;
          description
            "Name for FlexE cross-connect.";
        }
        choice end-point-a-type {
          mandatory true;
          description
            "Type of cross-connect member for end-point-a";
          case ettp {
            leaf ettp-end-point-a {
              type leafref {
                path "/ncs:devices/ncs:device/ncs:config/oc-if:interfaces/oc-if:interface/oc-if:name" {
                  tailf:xpath-root 3;
                }
              }
              must "/oc-if:interfaces/oc-if:interface[oc-if:name = current()]/oc-if:config/cn-oc-if:type = 'ettp'" {
                tailf:xpath-root 3;
                error-message "Referenced interface must be of type 'ettp'.";
              }
              description
                "ETTP endpoint.";
            }
          }
          case flexe-channel {
            leaf flexe-channel-end-point-a {
              type ciena-flexe:flexe-channel-ref;
              description
                "FlexE channel endpoint.";
            }
          }
        }
        choice end-point-b-type {
          mandatory true;
          description
            "Type of cross-connect member for end-point-b";
          case ettp {
            leaf ettp-end-point-b {
              type leafref {
                path "/ncs:devices/ncs:device/ncs:config/oc-if:interfaces/oc-if:interface/oc-if:name" {
                  tailf:xpath-root 3;
                }
              }
              must "/oc-if:interfaces/oc-if:interface[oc-if:name = current()]/oc-if:config/cn-oc-if:type = 'ettp'" {
                tailf:xpath-root 3;
                error-message "Referenced interface must be of type 'ettp'.";
              }
              description
                "ETTP endpoint.";
            }
          }
          case flexe-channel {
            leaf flexe-channel-end-point-b {
              type ciena-flexe:flexe-channel-ref;
              description
                "FlexE channel endpoint.";
            }
          }
        }
      }
    }
    // NCS drop config false container 'flexe-operational-state'
  }
  augment "/ncs:devices/ncs:device/ncs:live-status" {
    container flexe-ports {
      tailf:ncs-device-type "netconf";
      tailf:display-when "not(../../ncs:module) or ../../ncs:module[ncs:name='ciena-flexe'] or (../../ncs:live-status-protocol[not(ncs:capability)]) or (../../ncs:live-status-protocol/ncs:capability/ncs:module[.='ciena-flexe'])";
      description
        "FlexE port configurations";
      list flexe-port {
        key "name";
        description
          "List of FlexE ports.";
        leaf name {
          type live_ncs_name-string;
          description
            "Name for FlexE port.";
        }
        leaf admin-state {
          type ciena:live_ncs_admin-state;
          // NCS drop default statement
          description
            "Overall port admin state.";
        }
        leaf ptp-id {
          type leafref {
            path "/ncs:devices/ncs:device/ncs:live-status/cn-pkt-ptp:ptps/cn-pkt-ptp:ptp/cn-pkt-ptp:ptp-id" {
              tailf:xpath-root 3;
            }
          }
          // NCS drop mandatory statement
          description
            "Unique, access identifier string of the PTP (e.g., '1/1').";
        }
        leaf port-speed {
          type enumeration {
            enum "50Gb" {
              description
                "50 Gbps FlexE";
            }
            enum "100Gb" {
              description
                "100 Gbps FlexE";
            }
            enum "200Gb" {
              description
                "200 Gbps FlexE";
            }
            enum "400Gb" {
              description
                "400 Gbps FlexE";
            }
          }
          // NCS drop mandatory statement
          description
            "FlexE port speed.";
        }
        leaf forward-error-correction {
          type cntypes:live_ncs_ettp-fec-enum;
          // NCS drop default statement
          description
            "Forward error correction";
        }
      }
    }
    container flexe-groups {
      tailf:ncs-device-type "netconf";
      tailf:display-when "not(../../ncs:module) or ../../ncs:module[ncs:name='ciena-flexe'] or (../../ncs:live-status-protocol[not(ncs:capability)]) or (../../ncs:live-status-protocol/ncs:capability/ncs:module[.='ciena-flexe'])";
      description
        "FlexE group configurations";
      list flexe-group {
        key "name";
        description
          "List of FlexE groups.";
        leaf name {
          type live_ncs_name-string;
          description
            "Name for FlexE group.";
        }
        leaf admin-state {
          type ciena:live_ncs_admin-state;
          // NCS drop default statement
          description
            "Overall FlexE group admin state.";
        }
        leaf group-number {
          type uint32 {
            range "1..254";
          }
          // NCS drop mandatory statement
          description
            "FlexE group number associated to the FlexE group";
        }
        leaf calendar-slot-granularity {
          type enumeration {
            enum "slot-5G" {
              value 1;
              description
                "Calendar slot is of 5G granularity";
            }
            enum "slot-25G" {
              value 2;
              description
                "Calendar slot is of 25G granularity";
            }
          }
          // NCS drop default statement
          description
            "The granularity of calendar slot is 5G or 25G";
          reference "Refer to the clause 6.8 in OIF FlexE IA 2.1";
        }
        leaf phy-type {
          type enumeration {
            enum "flexe-phy-50GBASE-R" {
              value 1;
              description
                "50GBASE-R PHY";
            }
            enum "flexe-phy-100GBASE-R" {
              value 2;
              description
                "100GBASE-R PHY";
            }
            enum "flexe-phy-200GBASE-R" {
              value 3;
              description
                "200GBASE-R PHY";
            }
            enum "flexe-phy-400GBASE-R" {
              value 4;
              description
                "400GBASE-R PHY";
            }
          }
          // NCS drop mandatory statement
          description
            "Type of PHY used in the FlexE group, such as 50/100/200/400GBASE-R.
             All PHYs in a FlexE group should be of same type";
          reference "OIF FlexE IA 2.1";
        }
        leaf calendar {
          type enumeration {
            enum "calendar-A" {
              value 0;
              description
                "Set the A calendar configuration.";
            }
            enum "calendar-B" {
              value 1;
              description
                "Set the B calendar configuration.";
            }
          }
          // NCS drop default statement
          description
            "Calendar configuration used in FlexE Mux/Demux";
        }
        leaf calendar-protocol-enable {
          type boolean;
          // NCS drop default statement
          description
            "Whether calendar negotiation protocol is enabled or not.";
          reference "OIF Flex 2.1: Section 7.3.4";
        }
        list flexe-phys {
          key "phy-number-in-group";
          // NCS drop min-elements statement
          description
            "List of the participating PHYs in a FlexE group";
          leaf phy-number-in-group {
            type uint32 {
              range "1 .. 254";
            }
            description
              "Refer to the clause 6.1 in FlexE IA 2.1.
               For 100GBASE-R, the FlexE PHY num and the 100G
               FlexE instance num are the same and in the range
               [1-254]; For 200GBASE-R, each PHY num is in the
               range [1-126]. For 400GBASE-R, each PHY num is
               in the range [1-62]. For 50GBASE-R, each PHY num is
               in the range [1-126]. PHY num configured in list of
               flexe-phys should be in ascending order.";
          }
          leaf local-interface {
            type ciena-flexe:live_ncs_flexe-port-ref;
            // NCS drop mandatory statement
            description
              "Local FlexE port interface related to the current
               phy-number in a FlexE group.";
          }
        }
      }
    }
    container flexe-channels {
      tailf:ncs-device-type "netconf";
      tailf:display-when "not(../../ncs:module) or ../../ncs:module[ncs:name='ciena-flexe'] or (../../ncs:live-status-protocol[not(ncs:capability)]) or (../../ncs:live-status-protocol/ncs:capability/ncs:module[.='ciena-flexe'])";
      description
        "FlexE channel configurations";
      list flexe-channel {
        key "name";
        description
          "List of FlexE channels.";
        leaf name {
          type live_ncs_name-string;
          description
            "Name for FlexE channel.";
        }
        leaf channel-number {
          type uint32 {
            range "1..65534";
          }
          // NCS drop mandatory statement
          description
            "Channel number associated to the FlexE channel.";
        }
        leaf group-name {
          type ciena-flexe:live_ncs_flexe-group-ref;
          // NCS drop mandatory statement
          description
            "Name of FlexE group to which this FlexE channel will be associated to.";
        }
        leaf channel-mapping {
          type enumeration {
            enum "L1-mapped" {
              value 1;
              description
                "L1 switching between faceplate ETTP and FlexE MAC ETTP at matched rate or
                 2 FlexE channels.";
            }
            enum "L2-mapped" {
              value 2;
              description
                "L2 forwarding between Logical port/flowpoints created over faceplate ETTPs/FlexE MAC ETTPs";
            }
          }
          // NCS drop default statement
          description
            "FlexE Datapath, traffic mapped at L1/L2/L3";
        }
        list calendar-A-slots-list {
          key "phy-number-in-group slot-id";
          description
            "List of slots allocated on Calendar A for a FlexE channel.
             Number of slots allocated for a FlexE channel is based on
             the bandwidth allocated for it. Ex: For a system with
             calendar slot granularity of 5G, a 10G FlexE channel
             would be allocated 2 slots (10G/5G)";
          uses live_ncs_flexe-channel-slot;
        }
        list calendar-B-slots-list {
          key "phy-number-in-group slot-id";
          description
            "List of slots allocated on Calendar B for a FlexE channel.
             Number of slots allocated for a FlexE channel is based on
             the bandwidth allocated for it. Ex: For a system with
             calendar slot granularity of 5G, a 10G FlexE-channel
             would be allocated 2 slots (10G/5G)";
          uses live_ncs_flexe-channel-slot;
        }
      }
    }
    container flexe-cross-connects {
      tailf:ncs-device-type "netconf";
      tailf:display-when "not(../../ncs:module) or ../../ncs:module[ncs:name='ciena-flexe'] or (../../ncs:live-status-protocol[not(ncs:capability)]) or (../../ncs:live-status-protocol/ncs:capability/ncs:module[.='ciena-flexe'])";
      description
        "FlexE cross connect configurations";
      list flexe-cross-connect {
        key "name";
        description
          "List of FlexE cross-connects.
           FlexE cross-connect can be between Faceplate standard ethernet ETTP
           and FlexE MAC ETTP or two FlexE channels";
        leaf name {
          type live_ncs_name-string;
          description
            "Name for FlexE cross-connect.";
        }
        choice end-point-a-type {
          // NCS drop mandatory statement
          description
            "Type of cross-connect member for end-point-a";
          case ettp {
            leaf ettp-end-point-a {
              type leafref {
                path "/ncs:devices/ncs:device/ncs:live-status/oc-if:interfaces/oc-if:interface/oc-if:name" {
                  tailf:xpath-root 3;
                }
              }
              // NCS drop must statement
              description
                "ETTP endpoint.";
            }
          }
          case flexe-channel {
            leaf flexe-channel-end-point-a {
              type ciena-flexe:live_ncs_flexe-channel-ref;
              description
                "FlexE channel endpoint.";
            }
          }
        }
        choice end-point-b-type {
          // NCS drop mandatory statement
          description
            "Type of cross-connect member for end-point-b";
          case ettp {
            leaf ettp-end-point-b {
              type leafref {
                path "/ncs:devices/ncs:device/ncs:live-status/oc-if:interfaces/oc-if:interface/oc-if:name" {
                  tailf:xpath-root 3;
                }
              }
              // NCS drop must statement
              description
                "ETTP endpoint.";
            }
          }
          case flexe-channel {
            leaf flexe-channel-end-point-b {
              type ciena-flexe:live_ncs_flexe-channel-ref;
              description
                "FlexE channel endpoint.";
            }
          }
        }
      }
    }
    container flexe-operational-state {
      tailf:ncs-device-type "netconf";
      tailf:display-when "not(../../ncs:module) or ../../ncs:module[ncs:name='ciena-flexe'] or (../../ncs:live-status-protocol[not(ncs:capability)]) or (../../ncs:live-status-protocol/ncs:capability/ncs:module[.='ciena-flexe'])";
      description
        "Operational data for FlexE.";
      list flexe-port-status {
        key "name";
        description
          "Operational status related to FlexE ports.";
        leaf name {
          type ciena-flexe:live_ncs_flexe-port-ref;
          description
            "Name for FlexE port.";
        }
        leaf oper-state {
          type ciena:live_ncs_oper-state;
          description
            "Flexe port operational enable/disable.";
        }
        container flexe-port-oh-status {
          description
            "Overhead status related to FlexE port ";
          uses live_ncs_flexe-port-oh-status-grouping;
        }
      }
      list flexe-group-status {
        key "name";
        description
          "Operational status related to FlexE group.";
        leaf name {
          type ciena-flexe:live_ncs_flexe-group-ref;
          description
            "Name for FlexE group.";
        }
        leaf flexe-group-oper-status {
          type ciena:live_ncs_oper-state;
          description
            "Status for a FlexE group. If any PHY is in fault,
             or any FlexE configuration is mismatched, the FlexE
             group status is indicated in fault.";
        }
        leaf total-bandwidth {
          type uint32;
          description
            "Total bandwidth of FlexE group in Gbps.";
        }
        leaf available-bandwidth {
          type uint32;
          description
            "Available bandwidth of FlexE group in Gbps.";
        }
        leaf allocated-bandwidth {
          type uint32;
          description
            "Bandwidth in Gbps allocated to channels associated
             to the FlexE group in Gbps";
        }
        leaf total-slots {
          type uint32;
          description
            "Total number of slots in FlexE group.";
        }
        leaf available-slots {
          type uint32;
          description
            "Number of slots available in active calendar of FlexE group.";
        }
        leaf allocated-slots {
          type uint32;
          description
            "Number of slots in use by FlexE channels associated to FlexE group.";
        }
        container flexe-group-oh-status {
          description
            "Overhead status related to FlexE group ";
          uses live_ncs_flexe-group-oh-status-grouping;
        }
      }
      list flexe-group-slot-map {
        key "name";
        description
          "Operational status related to FlexE group.";
        leaf name {
          type ciena-flexe:live_ncs_flexe-group-ref;
          description
            "Name for FlexE group.";
        }
        list calendar-A-slot-map {
          key "phy-number-in-group slot-id";
          description
            "FlexE channel mapping of Calendar-A slots on FlexE group.";
          uses live_ncs_flexe-group-slot;
        }
        list calendar-B-slot-map {
          key "phy-number-in-group slot-id";
          description
            "FlexE channel mapping of Calendar-B slots on FlexE group.";
          uses live_ncs_flexe-group-slot;
        }
      }
      list flexe-channel-status {
        key "name";
        description
          "Operational status related to FlexE group.";
        leaf name {
          type ciena-flexe:live_ncs_flexe-channel-ref;
          description
            "Name for FlexE channel.";
        }
        leaf flexe-channel-oper-status {
          type ciena:live_ncs_oper-state;
          description
            "Status for a FlexE channel.";
        }
        leaf active-bandwidth {
          type uint32;
          description
            "Bandwidth used by FlexE channel.";
        }
      }
    }
  }
  augment "/ncs:devices/ncs:template/ncs:ned-id/ncs:config" {
    container flexe-ports {
      description
        "FlexE port configurations";
      list flexe-port {
        // NCS patched for predictable order
        ordered-by user;
        key "name";
        description
          "List of FlexE ports.";
        leaf name {
          type ncs_template_name-string;
          description
            "Name for FlexE port.";
        }
        leaf admin-state {
          type ciena:ncs_template_admin-state;
          // NCS drop default statement
          description
            "Overall port admin state.";
        }
        leaf ptp-id {
          type string;
          // NCS drop mandatory statement
          description
            "Unique, access identifier string of the PTP (e.g., '1/1').";
        }
        leaf port-speed {
          type string;
          // NCS drop mandatory statement
          description
            "FlexE port speed.";
        }
        leaf forward-error-correction {
          type cntypes:ncs_template_ettp-fec-enum;
          // NCS drop default statement
          description
            "Forward error correction";
        }
      }
    }
    container flexe-groups {
      description
        "FlexE group configurations";
      list flexe-group {
        // NCS patched for predictable order
        ordered-by user;
        key "name";
        description
          "List of FlexE groups.";
        leaf name {
          type ncs_template_name-string;
          description
            "Name for FlexE group.";
        }
        leaf admin-state {
          type ciena:ncs_template_admin-state;
          // NCS drop default statement
          description
            "Overall FlexE group admin state.";
        }
        leaf group-number {
          type string;
          // NCS drop mandatory statement
          description
            "FlexE group number associated to the FlexE group";
        }
        leaf calendar-slot-granularity {
          type string;
          // NCS drop default statement
          description
            "The granularity of calendar slot is 5G or 25G";
          reference "Refer to the clause 6.8 in OIF FlexE IA 2.1";
        }
        leaf phy-type {
          type string;
          // NCS drop mandatory statement
          description
            "Type of PHY used in the FlexE group, such as 50/100/200/400GBASE-R.
             All PHYs in a FlexE group should be of same type";
          reference "OIF FlexE IA 2.1";
        }
        leaf calendar {
          type string;
          // NCS drop default statement
          description
            "Calendar configuration used in FlexE Mux/Demux";
        }
        leaf calendar-protocol-enable {
          type string;
          // NCS drop default statement
          description
            "Whether calendar negotiation protocol is enabled or not.";
          reference "OIF Flex 2.1: Section 7.3.4";
        }
        list flexe-phys {
          // NCS patched for predictable order
          ordered-by user;
          key "phy-number-in-group";
          // NCS drop min-elements statement
          description
            "List of the participating PHYs in a FlexE group";
          leaf phy-number-in-group {
            type string;
            description
              "Refer to the clause 6.1 in FlexE IA 2.1.
               For 100GBASE-R, the FlexE PHY num and the 100G
               FlexE instance num are the same and in the range
               [1-254]; For 200GBASE-R, each PHY num is in the
               range [1-126]. For 400GBASE-R, each PHY num is
               in the range [1-62]. For 50GBASE-R, each PHY num is
               in the range [1-126]. PHY num configured in list of
               flexe-phys should be in ascending order.";
          }
          leaf local-interface {
            type ciena-flexe:ncs_template_flexe-port-ref;
            // NCS drop mandatory statement
            description
              "Local FlexE port interface related to the current
               phy-number in a FlexE group.";
          }
        }
      }
    }
    container flexe-channels {
      description
        "FlexE channel configurations";
      list flexe-channel {
        // NCS patched for predictable order
        ordered-by user;
        key "name";
        description
          "List of FlexE channels.";
        leaf name {
          type ncs_template_name-string;
          description
            "Name for FlexE channel.";
        }
        leaf channel-number {
          type string;
          // NCS drop mandatory statement
          description
            "Channel number associated to the FlexE channel.";
        }
        leaf group-name {
          type ciena-flexe:ncs_template_flexe-group-ref;
          // NCS drop mandatory statement
          description
            "Name of FlexE group to which this FlexE channel will be associated to.";
        }
        leaf channel-mapping {
          type string;
          // NCS drop default statement
          description
            "FlexE Datapath, traffic mapped at L1/L2/L3";
        }
        list calendar-A-slots-list {
          // NCS patched for predictable order
          ordered-by user;
          key "phy-number-in-group slot-id";
          description
            "List of slots allocated on Calendar A for a FlexE channel.
             Number of slots allocated for a FlexE channel is based on
             the bandwidth allocated for it. Ex: For a system with
             calendar slot granularity of 5G, a 10G FlexE channel
             would be allocated 2 slots (10G/5G)";
          uses ncs_template_flexe-channel-slot;
        }
        list calendar-B-slots-list {
          // NCS patched for predictable order
          ordered-by user;
          key "phy-number-in-group slot-id";
          description
            "List of slots allocated on Calendar B for a FlexE channel.
             Number of slots allocated for a FlexE channel is based on
             the bandwidth allocated for it. Ex: For a system with
             calendar slot granularity of 5G, a 10G FlexE-channel
             would be allocated 2 slots (10G/5G)";
          uses ncs_template_flexe-channel-slot;
        }
      }
    }
    container flexe-cross-connects {
      description
        "FlexE cross connect configurations";
      list flexe-cross-connect {
        // NCS patched for predictable order
        ordered-by user;
        key "name";
        description
          "List of FlexE cross-connects.
           FlexE cross-connect can be between Faceplate standard ethernet ETTP
           and FlexE MAC ETTP or two FlexE channels";
        leaf name {
          type ncs_template_name-string;
          description
            "Name for FlexE cross-connect.";
        }
        choice end-point-a-type {
          // NCS drop mandatory statement
          description
            "Type of cross-connect member for end-point-a";
          case ettp {
            leaf ettp-end-point-a {
              type string;
              // NCS drop must statement
              description
                "ETTP endpoint.";
            }
          }
          case flexe-channel {
            leaf flexe-channel-end-point-a {
              type ciena-flexe:ncs_template_flexe-channel-ref;
              description
                "FlexE channel endpoint.";
            }
          }
        }
        choice end-point-b-type {
          // NCS drop mandatory statement
          description
            "Type of cross-connect member for end-point-b";
          case ettp {
            leaf ettp-end-point-b {
              type string;
              // NCS drop must statement
              description
                "ETTP endpoint.";
            }
          }
          case flexe-channel {
            leaf flexe-channel-end-point-b {
              type ciena-flexe:ncs_template_flexe-channel-ref;
              description
                "FlexE channel endpoint.";
            }
          }
        }
      }
    }
    // NCS drop config false container 'flexe-operational-state'
  }
}
