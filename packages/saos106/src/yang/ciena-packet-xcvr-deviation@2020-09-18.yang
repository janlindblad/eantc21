module ciena-packet-xcvr-deviation {
  namespace "http://www.ciena.com/ns/yang/ciena-packet-xcvr-dev";
  prefix xcvr-dev;

  import ciena-packet-xcvr {
    prefix xcvr;
  }

  organization
    "Ciena Corporation";
  contact
    "Web URL: http://www.ciena.com/
     Postal:  7035 Ridge Road
              Hanover, Maryland 21076
              U.S.A.
     Phone:   +1 800-921-1144
     Fax:     +1 410-694-5750";
  description
    "This module defines the common XCVR model deviations. The XCVR is augmented by specific types of transceiver modules if applicable. XCVR objects are permanently available for all ports and reported as empty if the device is not physically present. Attributes read from the device are only available while the device is present.";

  revision 2020-09-18 {
    description
      "Added XCVR mode OC12-STM4 and OC48-STM16.";
  }

  revision 2020-08-28 {
    description
      "Initial version.";
  }

  deviation /xcvr:xcvrs/xcvr:xcvr/xcvr:properties/xcvr:mode {
    deviate replace {
      type enumeration {
        enum "blank" {
          description
            "XCVR/slot is blank.";
        }
        enum "auto" {
          description
            "Various speed XCVRs can be inserted (e.g. 40GbE versus 100GbE)
             as long as the hardware supports them, and the system will
             automatically adjust the port speed based on the XCVRs
             capabilities. For multi rate XCVRs, the highest speed
             supported will be selected.";
        }
        enum "100M" {
          description
            "XCVR mode FastEthernet.";
        }
        enum "1GE" {
          description
            "XCVR mode 1 Gigabit Ethernet.";
        }
        enum "10GE" {
          description
            "XCVR mode 10 Gigabit Ethernet.";
        }
        enum "25GE" {
          description
            "XCVR mode 25 Gigabit Ethernet.";
        }
        enum "40GE" {
          description
            "XCVR mode 40 Gigabit Ethernet.";
        }
        enum "100GE" {
          description
            "XCVR mode 100 Gigabit Ethernet.";
        }
        enum "400GE" {
          description
            "XCVR mode 400 Gigabit Ethernet.";
        }

        // Line XCVR Modes - Baud/Modulation Values
        enum "35-100" {
          description
            "XCVR mode 35Gbaud, 100Gbps.";
        }
        enum "35-200" {
          description
            "XCVR mode 35Gbaud, 200Gbps.";
        }
        enum "56-100" {
          description
            "XCVR mode 56Gbaud, 100Gbps.";
        }
        enum "56-200" {
          description
            "XCVR mode 56Gbaud, 200Gbps.";
        }
        enum "56-300" {
          description
            "XCVR mode 56Gbaud, 300Gbps.";
        }
        enum "56-400" {
          description
            "XCVR mode 56Gbaud, 400Gbps.";
        }
        enum "28-100" {
          description
            "XCVR mode 28Gbaud, 100Gbps.";
        }
        enum "32-100" {
          description
            "XCVR mode 32Gbaud, 100Gbps.";
        }
        enum "32-200" {
          description
            "XCVR mode 32Gbaud, 200Gbps.";
        }
        enum "DS1-E1" {
          description
            "XCVR mode DS1-E1.";
        }
        enum "OC3-STM1" {
          description
            "XCVR mode OC3-STM1.";
        }
        enum "OC12-STM4" {
          description
            "XCVR mode OC12-STM4.";
        }
        enum "OC48-STM16" {
          description
            "XCVR mode OC48-STM16.";
        }
        enum "200GE" {
          description
            "XCVR mode 200 Gigabit Ethernet.";
        }

      }
      mandatory true;
    }
  }
}
