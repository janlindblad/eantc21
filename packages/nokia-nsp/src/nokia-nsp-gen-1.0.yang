module nokia-nsp-gen-1.0 {
  yang-version 1.1;
  namespace "http://tail-f.com/ns/ned-id/nokia-nsp-gen-1.0";
  prefix nokia-nsp-gen-1.0;

  import nokia-nsp-gen {
    prefix family;
  }

  identity nokia-nsp-gen-1.0 {
    base family:nokia-nsp-gen;
  }
}
