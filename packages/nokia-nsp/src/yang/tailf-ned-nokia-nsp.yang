module tailf-ned-nokia-nsp {

  namespace "http://tail-f.com/ned/nokia-nsp";
  prefix nokia-nsp;

  import tailf-common {
    prefix tailf;
  }

  revision 2021-04-28 {
    description "1.0, See CHANGES";
  }

  leaf skeletor {
    tailf:info "Skeletor says: This is a dummy...";
    type string; 
  }
}
