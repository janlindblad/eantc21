module saos1051-nc-1.0 {
  yang-version 1.1;
  namespace "http://tail-f.com/ns/ned-id/saos1051-nc-1.0";
  prefix saos1051-nc-1.0;

  import saos1051-nc {
    prefix family;
  }

  identity saos1051-nc-1.0 {
    base family:saos1051-nc;
  }
}
