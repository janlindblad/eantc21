module ciena-oam-ping-deviation {
  // Generated by yanger -t ncs
  tailf:mount-id "saos1051-nc-1.0:saos1051-nc-1.0";
  tailf:ncs-device-type "netconf";

  yang-version 1.1;
  namespace "http://ciena.com/ns/yang/ciena-oam-ping-deviation";
  prefix oam-ping-deviation;

  import ciena-oam-ping {
    prefix oam-ping;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena proprietary YANG deviations
     of the IP ping and traceroute module.

     Copyright (c) 2020  Ciena Corporation.  All rights
     reserved.

     All information contained herein is, and remains the
     property of Ciena Corporation. Dissemination of this
     information or reproduction of this material is strictly
     forbidden unless prior written permission is obtained
     from Ciena Corporation.";

  revision 2020-01-29 {
    description
      "Initial Version of deviation ping model.";
  }

  deviation "/ncs:devices/ncs:device/ncs:rpc/oam-ping:rpc-start-ping/oam-ping:start-ping/oam-ping:input/oam-ping:reply-mode" {
    deviate not-supported;
  }
  deviation "/ncs:devices/ncs:device/ncs:rpc/oam-ping:rpc-start-ping/oam-ping:start-ping/oam-ping:input/oam-ping:traffic-class" {
    deviate not-supported;
  }
  deviation "/ncs:devices/ncs:device/ncs:rpc/oam-ping:rpc-start-ping/oam-ping:start-ping/oam-ping:input/oam-ping:encap" {
    deviate not-supported;
  }
  deviation "/ncs:devices/ncs:device/ncs:rpc/oam-ping:rpc-start-ping/oam-ping:start-ping/oam-ping:input/oam-ping:reverse-fec-stack-validation" {
    deviate not-supported;
  }
  deviation "/ncs:devices/ncs:device/ncs:live-status/oam-ping:oam-ping-sessions/oam-ping:oam-ping-session/oam-ping:oam-ping-config-params/oam-ping:reply-mode" {
    deviate not-supported;
  }
  deviation "/ncs:devices/ncs:device/ncs:live-status/oam-ping:oam-ping-sessions/oam-ping:oam-ping-session/oam-ping:oam-ping-config-params/oam-ping:traffic-class" {
    deviate not-supported;
  }
  deviation "/ncs:devices/ncs:device/ncs:live-status/oam-ping:oam-ping-sessions/oam-ping:oam-ping-session/oam-ping:oam-ping-config-params/oam-ping:encap" {
    deviate not-supported;
  }
  deviation "/ncs:devices/ncs:device/ncs:live-status/oam-ping:oam-ping-sessions/oam-ping:oam-ping-session/oam-ping:oam-ping-config-params/oam-ping:reverse-fec-stack-validation" {
    deviate not-supported;
  }
  deviation "/ncs:devices/ncs:device/ncs:live-status/oam-ping:oam-ping-sessions/oam-ping:oam-ping-session/oam-ping:ping-results/oam-ping:ping-probe-results/oam-ping:ping-probe-result/oam-ping:return-sub-code" {
    deviate not-supported;
  }
}
