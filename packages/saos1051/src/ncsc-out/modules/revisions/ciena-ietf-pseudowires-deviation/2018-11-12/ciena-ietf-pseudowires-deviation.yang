module ciena-ietf-pseudowires-deviation {
  // Generated by yanger -t ncs
  tailf:mount-id "saos1051-nc-1.0:saos1051-nc-1.0";
  tailf:ncs-device-type "netconf";

  namespace "http://ciena.com/ns/yang/ciena-ietf-pseudowires-deviation";
  prefix cn-pw-deviation;

  import ietf-pseudowires {
    prefix pw;
  }
  import ciena-ietf-pseudowires {
    prefix cnpw;
  }
  import ietf-inet-types {
    prefix inet;
  }
  import yuma-ncx {
    prefix ncx;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
       U.S.A.
     Phone:   +1 800-921-1144
     Fax:     +1 410-694-5750";
  description
    "This module contains the Ciena proprietary YANG deviations
     of the standard pseudowire YANG module.
     Copyright (c) 2016 Ciena Corporation.  All rights reserved.

     All information contained herein is, and remains
     the property of Ciena Corporation. Dissemination of this
     information or reproduction of this material is strictly
     forbidden unless prior written permission is obtained from
     Ciena Corporation.";

  revision 2018-11-12 {
    description
      "Initial version";
  }

  deviation "/ncs:devices/ncs:device/ncs:live-status/pw:pseudowires/pw:pseudowire/pw:state" {
    deviate not-supported;
  }
  deviation "/ncs:devices/ncs:template/ncs:ned-id/ncs:config/pw:pseudowires/pw:pseudowire/pw:template" {
    deviate not-supported;
  }
  deviation "/ncs:devices/ncs:device/ncs:live-status/pw:pseudowires/pw:pseudowire/pw:template" {
    deviate not-supported;
  }
  deviation "/ncs:devices/ncs:device/ncs:config/pw:pseudowires/pw:pseudowire/pw:template" {
    deviate not-supported;
  }
  deviation "/ncs:devices/ncs:template/ncs:ned-id/ncs:config/pw:pseudowires/pw:pseudowire/pw:tunnel-policy" {
    deviate not-supported;
  }
  deviation "/ncs:devices/ncs:device/ncs:live-status/pw:pseudowires/pw:pseudowire/pw:tunnel-policy" {
    deviate not-supported;
  }
  deviation "/ncs:devices/ncs:device/ncs:config/pw:pseudowires/pw:pseudowire/pw:tunnel-policy" {
    deviate not-supported;
  }
  deviation "/ncs:devices/ncs:template/ncs:ned-id/ncs:config/pw:pseudowires/pw:pw-templates/pw:pw-template/pw:tunnel-policy" {
    deviate not-supported;
  }
  deviation "/ncs:devices/ncs:device/ncs:live-status/pw:pseudowires/pw:pw-templates/pw:pw-template/pw:tunnel-policy" {
    deviate not-supported;
  }
  deviation "/ncs:devices/ncs:device/ncs:config/pw:pseudowires/pw:pw-templates/pw:pw-template/pw:tunnel-policy" {
    deviate not-supported;
  }
  deviation "/ncs:devices/ncs:template/ncs:ned-id/ncs:config/pw:pseudowires/pw:pseudowire/pw:pw-type/pw:configured-pw/pw:configured-pw/pw:peer-ip" {
    deviate replace {
      type string;
    }
  }
  deviation "/ncs:devices/ncs:device/ncs:live-status/pw:pseudowires/pw:pseudowire/pw:pw-type/pw:configured-pw/pw:configured-pw/pw:peer-ip" {
    deviate replace {
      type inet:ipv4-address;
    }
  }
  deviation "/ncs:devices/ncs:device/ncs:config/pw:pseudowires/pw:pseudowire/pw:pw-type/pw:configured-pw/pw:configured-pw/pw:peer-ip" {
    deviate replace {
      type inet:ipv4-address;
    }
  }
  deviation "/ncs:devices/ncs:template/ncs:ned-id/ncs:config/pw:pseudowires/pw:pseudowire/pw:pw-type/pw:configured-pw/pw:configured-pw/pw:peer-ip" {
    deviate add {
      // NCS drop mandatory statement
      ncx:user-write "create";
    }
  }
  deviation "/ncs:devices/ncs:device/ncs:live-status/pw:pseudowires/pw:pseudowire/pw:pw-type/pw:configured-pw/pw:configured-pw/pw:peer-ip" {
    deviate add {
      // NCS drop mandatory statement
      ncx:user-write "create";
    }
  }
  deviation "/ncs:devices/ncs:device/ncs:config/pw:pseudowires/pw:pseudowire/pw:pw-type/pw:configured-pw/pw:configured-pw/pw:peer-ip" {
    deviate add {
      mandatory true;
      ncx:user-write "create";
    }
  }
  deviation "/ncs:devices/ncs:template/ncs:ned-id/ncs:config/pw:pseudowires/pw:pseudowire/pw:pw-type/pw:configured-pw/pw:configured-pw/pw:pw-id" {
    deviate add {
      // NCS drop mandatory statement
      ncx:user-write "create";
    }
  }
  deviation "/ncs:devices/ncs:device/ncs:live-status/pw:pseudowires/pw:pseudowire/pw:pw-type/pw:configured-pw/pw:configured-pw/pw:pw-id" {
    deviate add {
      // NCS drop mandatory statement
      ncx:user-write "create";
    }
  }
  deviation "/ncs:devices/ncs:device/ncs:config/pw:pseudowires/pw:pseudowire/pw:pw-type/pw:configured-pw/pw:configured-pw/pw:pw-id" {
    deviate add {
      mandatory true;
      ncx:user-write "create";
    }
  }
  deviation "/ncs:devices/ncs:template/ncs:ned-id/ncs:config/pw:pseudowires/pw:pseudowire/pw:mtu" {
    deviate add {
      // NCS drop default statement
    }
  }
  deviation "/ncs:devices/ncs:device/ncs:live-status/pw:pseudowires/pw:pseudowire/pw:mtu" {
    deviate add {
      // NCS drop default statement
    }
  }
  deviation "/ncs:devices/ncs:device/ncs:config/pw:pseudowires/pw:pseudowire/pw:mtu" {
    deviate add {
      default "1500";
    }
  }
  deviation "/ncs:devices/ncs:template/ncs:ned-id/ncs:config/pw:pseudowires/pw:pseudowire/pw:cw-negotiation" {
    deviate add {
      // NCS drop default statement
    }
  }
  deviation "/ncs:devices/ncs:device/ncs:live-status/pw:pseudowires/pw:pseudowire/pw:cw-negotiation" {
    deviate add {
      // NCS drop default statement
    }
  }
  deviation "/ncs:devices/ncs:device/ncs:config/pw:pseudowires/pw:pseudowire/pw:cw-negotiation" {
    deviate add {
      default "non-preferred";
    }
  }
  deviation "/ncs:devices/ncs:template/ncs:ned-id/ncs:config/pw:pseudowires/pw:pseudowire/pw:pw-type/pw:configured-pw/pw:configured-pw/pw:icb" {
    deviate not-supported;
  }
  deviation "/ncs:devices/ncs:device/ncs:live-status/pw:pseudowires/pw:pseudowire/pw:pw-type/pw:configured-pw/pw:configured-pw/pw:icb" {
    deviate not-supported;
  }
  deviation "/ncs:devices/ncs:device/ncs:config/pw:pseudowires/pw:pseudowire/pw:pw-type/pw:configured-pw/pw:configured-pw/pw:icb" {
    deviate not-supported;
  }
  deviation "/ncs:devices/ncs:template/ncs:ned-id/ncs:config/pw:pseudowires/pw:pseudowire/pw:mac-withdraw" {
    deviate not-supported;
  }
  deviation "/ncs:devices/ncs:device/ncs:live-status/pw:pseudowires/pw:pseudowire/pw:mac-withdraw" {
    deviate not-supported;
  }
  deviation "/ncs:devices/ncs:device/ncs:config/pw:pseudowires/pw:pseudowire/pw:mac-withdraw" {
    deviate not-supported;
  }
  deviation "/ncs:devices/ncs:template/ncs:ned-id/ncs:config/pw:pseudowires/pw:pw-templates" {
    deviate not-supported;
  }
  deviation "/ncs:devices/ncs:device/ncs:live-status/pw:pseudowires/pw:pw-templates" {
    deviate not-supported;
  }
  deviation "/ncs:devices/ncs:device/ncs:config/pw:pseudowires/pw:pw-templates" {
    deviate not-supported;
  }
  deviation "/ncs:devices/ncs:template/ncs:ned-id/ncs:config/pw:pseudowires/pw:pseudowire/cnpw:vccv-ability" {
    deviate not-supported;
  }
  deviation "/ncs:devices/ncs:device/ncs:live-status/pw:pseudowires/pw:pseudowire/cnpw:vccv-ability" {
    deviate not-supported;
  }
  deviation "/ncs:devices/ncs:device/ncs:config/pw:pseudowires/pw:pseudowire/cnpw:vccv-ability" {
    deviate not-supported;
  }
  deviation "/ncs:devices/ncs:template/ncs:ned-id/ncs:config/pw:pseudowires/pw:pseudowire/cnpw:vlan-tpid" {
    deviate not-supported;
  }
  deviation "/ncs:devices/ncs:device/ncs:live-status/pw:pseudowires/pw:pseudowire/cnpw:vlan-tpid" {
    deviate not-supported;
  }
  deviation "/ncs:devices/ncs:device/ncs:config/pw:pseudowires/pw:pseudowire/cnpw:vlan-tpid" {
    deviate not-supported;
  }
  deviation "/ncs:devices/ncs:template/ncs:ned-id/ncs:config/pw:pseudowires/pw:pseudowire/pw:pw-type/pw:configured-pw/pw:configured-pw/pw:transmit-label" {
    deviate replace {
      type string;
    }
    description
      "Specify the pseudowire label of transmitted packets";
  }
  deviation "/ncs:devices/ncs:device/ncs:live-status/pw:pseudowires/pw:pseudowire/pw:pw-type/pw:configured-pw/pw:configured-pw/pw:transmit-label" {
    deviate replace {
      type uint32;
    }
    description
      "Specify the pseudowire label of transmitted packets";
  }
  deviation "/ncs:devices/ncs:device/ncs:config/pw:pseudowires/pw:pseudowire/pw:pw-type/pw:configured-pw/pw:configured-pw/pw:transmit-label" {
    deviate replace {
      type uint32;
    }
    description
      "Specify the pseudowire label of transmitted packets";
  }
  deviation "/ncs:devices/ncs:template/ncs:ned-id/ncs:config/pw:pseudowires/pw:pseudowire/pw:pw-type/pw:configured-pw/pw:configured-pw/pw:receive-label" {
    deviate replace {
      type string;
    }
    description
      "Specify the pseudowire label of recevied packets";
  }
  deviation "/ncs:devices/ncs:device/ncs:live-status/pw:pseudowires/pw:pseudowire/pw:pw-type/pw:configured-pw/pw:configured-pw/pw:receive-label" {
    deviate replace {
      type uint32 {
        range "16..15999";
      }
    }
    description
      "Specify the pseudowire label of recevied packets";
  }
  deviation "/ncs:devices/ncs:device/ncs:config/pw:pseudowires/pw:pseudowire/pw:pw-type/pw:configured-pw/pw:configured-pw/pw:receive-label" {
    deviate replace {
      type uint32 {
        range "16..15999";
      }
    }
    description
      "Specify the pseudowire label of recevied packets";
  }
}
