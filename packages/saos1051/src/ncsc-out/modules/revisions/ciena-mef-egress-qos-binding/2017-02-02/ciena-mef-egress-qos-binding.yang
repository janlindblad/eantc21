module ciena-mef-egress-qos-binding {
  // Generated by yanger -t ncs
  tailf:mount-id "saos1051-nc-1.0:saos1051-nc-1.0";
  tailf:ncs-device-type "netconf";

  namespace "urn:ciena:params:xml:ns:yang:ciena-pn::ciena-mef-egress-qos-binding";
  prefix mef-egress-qos-binding;

  import ciena-mef-egress-qos {
    prefix mef-egress-qos;
  }
  import ciena-mef-logical-port {
    prefix mef-logical-port;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
                 U.S.A.
     Phone:   +1 800-921-1144
     Fax:     +1 410-694-5750";
  description
    "This YANG module defines Ciena's management data definition for the
     association of certain interfaces (e.g. mef-logical-port) to a queue-group-instance";

  revision 2017-02-02 {
    description
      "Initial Version.";
  }

  augment "/ncs:devices/ncs:device/ncs:config" {
    container interface-qos-binding {
      tailf:ncs-device-type "netconf";
      tailf:display-when "not(../../ncs:module) or ../../ncs:module[ncs:name='ciena-mef-egress-qos-binding']";
      description
        "List of egress-qos-bindings. Egress QoS Bindings configure a binding of a queue-group-instance
         to a logical port determining the default set of configurable queues for a Logical Port";
      list interface-qos-binding {
        key "name";
        leaf name {
          type string;
          description
            "This object indicates the identifier and is a
             text string that is used to identify an interface-qos-binding.
             Unique string values are chosen to uniquely identify
             interface-qos-binding.
             This object should only be used for interfaces where it is not possible
             to import ciena-mef-egress-qos module (e.g. logical-port)";
        }
        leaf queue-group-instance {
          type mef-egress-qos:queue-group-ref;
          description
            "A reference to a Queue Group Instance specific to the Interface (e.g. logical-port)";
        }
        leaf logical-port {
          type mef-logical-port:logical-port-ref;
          description
            "Reference to the logical-port that the queue-group-instance is the default
             Queue Group Instance for the logical-port and all logical-interfaces (e.g. flow-points)
             which are not specifying a specific Queue Group Instance otherwise";
        }
      }
    }
  }
  augment "/ncs:devices/ncs:device/ncs:live-status" {
    container interface-qos-binding {
      tailf:ncs-device-type "netconf";
      tailf:display-when "not(../../ncs:module) or ../../ncs:module[ncs:name='ciena-mef-egress-qos-binding'] or (../../ncs:live-status-protocol[not(ncs:capability)]) or (../../ncs:live-status-protocol/ncs:capability/ncs:module[.='ciena-mef-egress-qos-binding'])";
      description
        "List of egress-qos-bindings. Egress QoS Bindings configure a binding of a queue-group-instance
         to a logical port determining the default set of configurable queues for a Logical Port";
      list interface-qos-binding {
        key "name";
        leaf name {
          type string;
          description
            "This object indicates the identifier and is a
             text string that is used to identify an interface-qos-binding.
             Unique string values are chosen to uniquely identify
             interface-qos-binding.
             This object should only be used for interfaces where it is not possible
             to import ciena-mef-egress-qos module (e.g. logical-port)";
        }
        leaf queue-group-instance {
          type mef-egress-qos:live_ncs_queue-group-ref;
          description
            "A reference to a Queue Group Instance specific to the Interface (e.g. logical-port)";
        }
        leaf logical-port {
          type mef-logical-port:live_ncs_logical-port-ref;
          description
            "Reference to the logical-port that the queue-group-instance is the default
             Queue Group Instance for the logical-port and all logical-interfaces (e.g. flow-points)
             which are not specifying a specific Queue Group Instance otherwise";
        }
      }
    }
  }
  augment "/ncs:devices/ncs:template/ncs:ned-id/ncs:config" {
    container interface-qos-binding {
      description
        "List of egress-qos-bindings. Egress QoS Bindings configure a binding of a queue-group-instance
         to a logical port determining the default set of configurable queues for a Logical Port";
      list interface-qos-binding {
        // NCS patched for predictable order
        ordered-by user;
        key "name";
        leaf name {
          type string;
          description
            "This object indicates the identifier and is a
             text string that is used to identify an interface-qos-binding.
             Unique string values are chosen to uniquely identify
             interface-qos-binding.
             This object should only be used for interfaces where it is not possible
             to import ciena-mef-egress-qos module (e.g. logical-port)";
        }
        leaf queue-group-instance {
          type mef-egress-qos:ncs_template_queue-group-ref;
          description
            "A reference to a Queue Group Instance specific to the Interface (e.g. logical-port)";
        }
        leaf logical-port {
          type mef-logical-port:ncs_template_logical-port-ref;
          description
            "Reference to the logical-port that the queue-group-instance is the default
             Queue Group Instance for the logical-port and all logical-interfaces (e.g. flow-points)
             which are not specifying a specific Queue Group Instance otherwise";
        }
      }
    }
  }
}
