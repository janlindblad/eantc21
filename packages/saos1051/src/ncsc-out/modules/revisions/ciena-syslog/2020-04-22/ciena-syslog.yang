module ciena-syslog {
  // Generated by yanger -t ncs
  tailf:mount-id "saos1051-nc-1.0:saos1051-nc-1.0";
  tailf:ncs-device-type "netconf";

  namespace "http://www.ciena.com/ns/yang/ciena-syslog";
  prefix ciena-syslog;

  import ietf-inet-types {
    prefix inet;
  }
  import ciena-types {
    prefix ciena;
  }
  import ietf-syslog {
    prefix syslog;
  }
  import ietf-syslog-types {
    prefix syslogtypes;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's global configuration for syslog settings.

     Copyright (c) 2016 Ciena Corporation.  All rights
     reserved.

     All information contained herein is, and remains
     the property of Ciena Corporation. Dissemination of this
     information or reproduction of this material is strictly
     forbidden unless prior written permission is obtained from
     Ciena Corporation.";

  revision 2020-04-22 {
    description
      "Removed max-elements limit from leaf severity.";
    reference
      "RFC 6020: YANG - A Data Modeling Language for
       the Network Configuration Protocol (NETCONF).
       No specific reference; standard not available.";
  }
  revision 2019-01-31 {
    description
      "Added defaults to leaves.";
    reference
      "RFC 6020: YANG - A Data Modeling Language for
       the Network Configuration Protocol (NETCONF).
       No specific reference; standard not available.";
  }
  revision 2016-08-14 {
    description
      "Initial version";
    reference
      "RFC 6020: YANG - A Data Modeling Language for
       the Network Configuration Protocol (NETCONF).
       No specific reference; standard not available.";
  }

  augment "/ncs:devices/ncs:template/ncs:ned-id/ncs:config/syslog:syslog/syslog:log-actions/syslog:remote" {
    description
      "A replacement for the syslog destination in the ietf-syslog YANG model.
         SAOS only supports one facility per syslog collector and a list of severities per facility.";
    leaf admin-state {
      type ciena:ncs_template_admin-state;
      // NCS drop default statement
      description
        "The administrative state of Syslog.";
    }
    list dest {
      // NCS patched for predictable order
      ordered-by user;
      key "address";
      description
        "A replacement for the ietf-syslog destination list.";
      leaf address {
        type string;
        description
          "Syslog UDP address.";
      }
      leaf admin-state {
        type ciena:ncs_template_admin-state;
        // NCS drop default statement
        description
          "The administrative state of the Syslog server.";
      }
      leaf port {
        type string;
        // NCS drop default statement
        description
          "UDP port number.";
      }
      leaf facility {
        type string;
        // NCS drop default statement
        description
          "Describes the Syslog facility.";
      }
      leaf-list severity {
        // NCS patched for predictable order
        ordered-by user;
        type syslogtypes:ncs_template_severity;
        description
          "Set a list of severities for the facility.
           The severity will default to LOG_INFO if
           none is specified.";
      }
      leaf custom-prefix {
        type string;
        description
          "Syslog message prefix.";
      }
    }
  }
  augment "/ncs:devices/ncs:device/ncs:live-status/syslog:syslog/syslog:log-actions/syslog:remote" {
    description
      "A replacement for the syslog destination in the ietf-syslog YANG model.
         SAOS only supports one facility per syslog collector and a list of severities per facility.";
    leaf admin-state {
      tailf:ncs-device-type "netconf";
      tailf:display-when "not(../../../../../ncs:module) or ../../../../../ncs:module[ncs:name='ciena-syslog'] or (../../../../../ncs:live-status-protocol[not(ncs:capability)]) or (../../../../../ncs:live-status-protocol/ncs:capability/ncs:module[.='ciena-syslog'])";
      type ciena:live_ncs_admin-state;
      // NCS drop default statement
      description
        "The administrative state of Syslog.";
    }
    list dest {
      tailf:ncs-device-type "netconf";
      tailf:display-when "not(../../../../ncs:module) or ../../../../ncs:module[ncs:name='ciena-syslog'] or (../../../../ncs:live-status-protocol[not(ncs:capability)]) or (../../../../ncs:live-status-protocol/ncs:capability/ncs:module[.='ciena-syslog'])";
      key "address";
      description
        "A replacement for the ietf-syslog destination list.";
      leaf address {
        type inet:host;
        description
          "Syslog UDP address.";
      }
      leaf admin-state {
        type ciena:live_ncs_admin-state;
        // NCS drop default statement
        description
          "The administrative state of the Syslog server.";
      }
      leaf port {
        type inet:port-number {
          range "514..65535";
        }
        // NCS drop default statement
        description
          "UDP port number.";
      }
      leaf facility {
        type identityref {
          base syslogtypes:syslog-facility;
        }
        // NCS drop default statement
        description
          "Describes the Syslog facility.";
      }
      leaf-list severity {
        type syslogtypes:live_ncs_severity;
        description
          "Set a list of severities for the facility.
           The severity will default to LOG_INFO if
           none is specified.";
      }
      leaf custom-prefix {
        type string {
          length "0..15";
        }
        description
          "Syslog message prefix.";
      }
    }
  }
  augment "/ncs:devices/ncs:device/ncs:config/syslog:syslog/syslog:log-actions/syslog:remote" {
    description
      "A replacement for the syslog destination in the ietf-syslog YANG model.
         SAOS only supports one facility per syslog collector and a list of severities per facility.";
    leaf admin-state {
      tailf:ncs-device-type "netconf";
      tailf:display-when "not(../../../../../ncs:module) or ../../../../../ncs:module[ncs:name='ciena-syslog']";
      type ciena:admin-state;
      default "enabled";
      description
        "The administrative state of Syslog.";
    }
    list dest {
      tailf:ncs-device-type "netconf";
      tailf:display-when "not(../../../../ncs:module) or ../../../../ncs:module[ncs:name='ciena-syslog']";
      key "address";
      description
        "A replacement for the ietf-syslog destination list.";
      leaf address {
        type inet:host;
        description
          "Syslog UDP address.";
      }
      leaf admin-state {
        type ciena:admin-state;
        default "enabled";
        description
          "The administrative state of the Syslog server.";
      }
      leaf port {
        type inet:port-number {
          range "514..65535";
        }
        default "514";
        description
          "UDP port number.";
      }
      leaf facility {
        type identityref {
          base syslogtypes:syslog-facility;
        }
        default "syslogtypes:local6";
        description
          "Describes the Syslog facility.";
      }
      leaf-list severity {
        type syslogtypes:severity;
        description
          "Set a list of severities for the facility.
           The severity will default to LOG_INFO if
           none is specified.";
      }
      leaf custom-prefix {
        type string {
          length "0..15";
        }
        description
          "Syslog message prefix.";
      }
    }
  }
}
