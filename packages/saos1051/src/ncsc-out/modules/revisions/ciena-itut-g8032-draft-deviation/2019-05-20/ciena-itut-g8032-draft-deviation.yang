module ciena-itut-g8032-draft-deviation {
  // Generated by yanger -t ncs
  tailf:mount-id "saos1051-nc-1.0:saos1051-nc-1.0";
  tailf:ncs-device-type "netconf";

  namespace "http://www.ciena.com/ns/yang/ciena-itut-g8032-draft-deviation";
  prefix g8032-deviation;

  import ciena-itut-g8032-draft {
    prefix g8032;
  }
  import ciena-mef-logical-port {
    prefix mef-logical-port;
  }
  import ciena-mef-fd {
    prefix ciena-mef-fd;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's specific deviations
     to the g8032 yang model.

     Copyright (c) 2019 Ciena Corporation.  All rights
     reserved.

     All information contained herein is, and remains the
     property of Ciena Corporation. Dissemination of this
     information or reproduction of this material is strictly
     forbidden unless prior written permission is obtained
     from Ciena Corporation.";

  revision 2019-05-20 {
    description
      "This YANG model describes the deviation of ciena-itut-g8032-draft yang";
  }

  deviation "/ncs:devices/ncs:template/ncs:ned-id/ncs:config/g8032:g8032-rings/g8032:g8032-ring/g8032:ring-ports/g8032:ring-port/g8032:interface" {
    deviate replace {
      type mef-logical-port:ncs_template_logical-port-ref;
    }
  }
  deviation "/ncs:devices/ncs:device/ncs:live-status/g8032:g8032-rings/g8032:g8032-ring/g8032:ring-ports/g8032:ring-port/g8032:interface" {
    deviate replace {
      type mef-logical-port:live_ncs_logical-port-ref;
    }
  }
  deviation "/ncs:devices/ncs:device/ncs:config/g8032:g8032-rings/g8032:g8032-ring/g8032:ring-ports/g8032:ring-port/g8032:interface" {
    deviate replace {
      type mef-logical-port:logical-port-ref;
    }
  }
  deviation "/ncs:devices/ncs:template/ncs:ned-id/ncs:config/g8032:g8032-rings/g8032:g8032-ring/g8032:ring-id" {
    deviate replace {
      type string;
    }
  }
  deviation "/ncs:devices/ncs:device/ncs:live-status/g8032:g8032-rings/g8032:g8032-ring/g8032:ring-id" {
    deviate replace {
      type uint8 {
        range "1..255";
      }
    }
  }
  deviation "/ncs:devices/ncs:device/ncs:config/g8032:g8032-rings/g8032:g8032-ring/g8032:ring-id" {
    deviate replace {
      type uint8 {
        range "1..255";
      }
    }
  }
  deviation "/ncs:devices/ncs:template/ncs:ned-id/ncs:config/g8032:g8032-rings/g8032:g8032-ring/g8032:erp-instances/g8032:erp-instance/g8032:data-members" {
    deviate replace {
      // NCS drop min-elements statement
      type string;
    }
  }
  deviation "/ncs:devices/ncs:device/ncs:live-status/g8032:g8032-rings/g8032:g8032-ring/g8032:erp-instances/g8032:erp-instance/g8032:data-members" {
    deviate replace {
      // NCS drop min-elements statement
      type leafref {
        path "/ncs:devices/ncs:device/ncs:live-status/ciena-mef-fd:fds/ciena-mef-fd:fd/ciena-mef-fd:name" {
          tailf:xpath-root 3;
        }
      }
    }
  }
  deviation "/ncs:devices/ncs:device/ncs:config/g8032:g8032-rings/g8032:g8032-ring/g8032:erp-instances/g8032:erp-instance/g8032:data-members" {
    deviate replace {
      min-elements 0;
      type leafref {
        path "/ncs:devices/ncs:device/ncs:config/ciena-mef-fd:fds/ciena-mef-fd:fd/ciena-mef-fd:name" {
          tailf:xpath-root 3;
        }
      }
    }
  }
  deviation "/ncs:devices/ncs:device/ncs:live-status/g8032:g8032-rings-state/g8032:g8032-ring/g8032:erp-instances/g8032:erp-instance/g8032:ports/g8032:port/g8032:flush-logic-remote" {
    deviate not-supported;
  }
}
