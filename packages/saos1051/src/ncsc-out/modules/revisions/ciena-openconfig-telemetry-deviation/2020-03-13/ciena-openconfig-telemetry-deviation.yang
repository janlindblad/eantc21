module ciena-openconfig-telemetry-deviation {
  // Generated by yanger -t ncs
  tailf:mount-id "saos1051-nc-1.0:saos1051-nc-1.0";
  tailf:ncs-device-type "netconf";

  namespace "http://ciena.com/ns/yang/ciena-openconfig-telemetry-deviation";
  prefix ciena-oct-dev;

  import openconfig-telemetry {
    prefix oct;
  }
  import ciena-openconfig-telemetry {
    prefix ciena-oct;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This module contains the Ciena proprietary YANG modifications
     to the OpenConfig telemetry YANG model.

     Copyright (c) 2017 Ciena Corporation.  All rights reserved.

     All information contained herein is, and remains
     the property of Ciena Corporation. Dissemination of this
     information or reproduction of this material is strictly
     forbidden unless prior written permission is obtained from
     Ciena Corporation.";

  revision 2020-03-13 {
    description
      "Deviate local-source-address,originated-qos-marking
       protocol,encoding";
    reference "openconfig-telemetry.yang.";
  }
  revision 2017-02-01 {
    description
      "Initial version";
    reference "";
  }

  deviation "/ncs:devices/ncs:template/ncs:ned-id/ncs:config/oct:telemetry-system/oct:subscriptions" {
    deviate not-supported;
  }
  deviation "/ncs:devices/ncs:device/ncs:live-status/oct:telemetry-system/oct:subscriptions" {
    deviate not-supported;
  }
  deviation "/ncs:devices/ncs:device/ncs:config/oct:telemetry-system/oct:subscriptions" {
    deviate not-supported;
  }
  deviation "/ncs:devices/ncs:template/ncs:ned-id/ncs:config/oct:telemetry-system/oct:destination-groups" {
    deviate not-supported;
  }
  deviation "/ncs:devices/ncs:device/ncs:live-status/oct:telemetry-system/oct:destination-groups" {
    deviate not-supported;
  }
  deviation "/ncs:devices/ncs:device/ncs:config/oct:telemetry-system/oct:destination-groups" {
    deviate not-supported;
  }
  deviation "/ncs:devices/ncs:template/ncs:ned-id/ncs:config/oct:telemetry-system/oct:sensor-groups" {
    deviate not-supported;
  }
  deviation "/ncs:devices/ncs:device/ncs:live-status/oct:telemetry-system/oct:sensor-groups" {
    deviate not-supported;
  }
  deviation "/ncs:devices/ncs:device/ncs:config/oct:telemetry-system/oct:sensor-groups" {
    deviate not-supported;
  }
  deviation "/ncs:devices/ncs:device/ncs:live-status/ciena-oct:telemetry-client-subscriptions/ciena-oct:subscriptions/ciena-oct:subscription-state/ciena-oct:telemetry-server-port" {
    deviate not-supported;
  }
  deviation "/ncs:devices/ncs:device/ncs:live-status/ciena-oct:telemetry-client-subscriptions/ciena-oct:subscriptions/ciena-oct:subscription-state/ciena-oct:telemetry-client-ip-address" {
    deviate not-supported;
  }
}
