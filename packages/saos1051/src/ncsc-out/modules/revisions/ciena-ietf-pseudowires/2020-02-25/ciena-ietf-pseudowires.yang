module ciena-ietf-pseudowires {
  // Generated by yanger -t ncs
  tailf:mount-id "saos1051-nc-1.0:saos1051-nc-1.0";
  tailf:ncs-device-type "netconf";

  namespace "http://ciena.com/ns/yang/ciena-ietf-pseudowires";
  prefix cnpw;

  import ietf-pseudowires {
    prefix pw;
  }
  import ciena-l3-types {
    prefix cn-l3-types;
  }
  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This module contains the Ciena proprietary YANG deviations
     of the standard pseudowire YANG module.
     Copyright (c) 2016 Ciena Corporation.  All rights reserved.

     All information contained herein is, and remains
     the property of Ciena Corporation. Dissemination of this
     information or reproduction of this material is strictly
     forbidden unless prior written permission is obtained from
     Ciena Corporation.";

  revision 2020-02-25 {
    description
      "Added Tunnel name,type,source-ip
       and destination-ip for tunnels";
  }
  revision 2019-11-15 {
    description
      "Added CC Type support";
    reference "RFC 5085";
  }
  revision 2019-11-05 {
    description
      "Added fat-capability parameter to support R and T bit individually";
    reference "RFC 6391";
  }
  revision 2018-11-12 {
    description
      "Initial version";
  }

  typedef ncs_template_pw-role-type {
    type string;
    description
      "Describes the role of Pseudowire as primary or backup";
  }

  typedef ncs_template_pseudowire-cctype {
    type string;
  }

  typedef ncs_rpc_notif_pw-role-type {
    type identityref {
      base role-of-pw;
    }
    description
      "Describes the role of Pseudowire as primary or backup";
  }

  typedef ncs_rpc_notif_pseudowire-cctype {
    type bits {
      bit cctype-1 {
        position 0;
      }
      bit cctype-2 {
        position 1;
      }
      bit cctype-3 {
        position 2;
      }
      bit cctype-4 {
        position 3;
      }
    }
  }

  typedef live_ncs_pw-role-type {
    type identityref {
      base role-of-pw;
    }
    description
      "Describes the role of Pseudowire as primary or backup";
  }

  typedef live_ncs_pseudowire-cctype {
    type bits {
      bit cctype-1 {
        position 0;
      }
      bit cctype-2 {
        position 1;
      }
      bit cctype-3 {
        position 2;
      }
      bit cctype-4 {
        position 3;
      }
    }
  }

  typedef pw-role-type {
    type identityref {
      base role-of-pw;
    }
    description
      "Describes the role of Pseudowire as primary or backup";
  }

  typedef pseudowire-cctype {
    type bits {
      bit cctype-1 {
        position 0;
      }
      bit cctype-2 {
        position 1;
      }
      bit cctype-3 {
        position 2;
      }
      bit cctype-4 {
        position 3;
      }
    }
  }

  augment "/ncs:devices/ncs:template/ncs:ned-id/ncs:config/pw:pseudowires/pw:pseudowire" {
    description
      "Adding additional parameters to ietf-pseduowires yang file";
    leaf role {
      type ncs_template_pw-role-type;
      // NCS drop default statement
      description
        "Mention the pseudowire role as primary or backup";
    }
    leaf protect {
      type string;
      // NCS drop default statement
      description
        "This attribute should be enabled if there is a protection required.";
    }
    leaf primary-pw {
      // NCS drop when statement
      type string;
      description
        "Mention the primary pseudowire name";
    }
    leaf mode {
      type cn-l3-types:ncs_template_pseudowire-mode;
      // NCS drop default statement
      description
        "Specify the pseudowire mode as mesh or spoke";
    }
    leaf vccv-ability {
      type string;
      description
        "Use this attribute to set the pseudowire Virtual Circuit Connectivity Verification (VCCV)";
    }
    leaf vlan-tpid {
      type cn-l3-types:ncs_template_mpls-tpid;
      description
        "Select the vlan tag protocol identifier";
    }
    leaf stats-collection {
      type string;
      // NCS drop default statement
      description
        "turn on/off statistics collection on the pseudowires";
    }
    leaf pw-loadbalance {
      type string;
      // NCS drop default statement
      description
        "PW load-balancing";
    }
    leaf fat-capability {
      // NCS drop when statement
      type string;
      // NCS drop default statement
      description
        "FAT pseudowire capability for negotiation";
    }
    leaf cc-types {
      type ncs_template_pseudowire-cctype;
      description
        "Use this attribute to set the CC Type for pseudowire signalling
         where each bit represent the CC Type in accordance with RFC 5085";
    }
    leaf tunnel-type {
      type cn-l3-types:ncs_template_tunnel-type;
      description
        "This is an enumeration which defines different tunnel types";
    }
    leaf tunnel-name {
      type string;
      description
        "User provided tunnel name over which PW needs to be created";
    }
    leaf tunnel-source-ip {
      type string;
      description
        "User provided tunnel source-ip";
    }
    leaf tunnel-destination-ip {
      type string;
      description
        "User provided tunnel destination-ip";
    }
  }
  augment "/ncs:devices/ncs:device/ncs:live-status/pw:pseudowires/pw:pseudowire" {
    description
      "Adding additional parameters to ietf-pseduowires yang file";
    leaf role {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type live_ncs_pw-role-type;
      // NCS drop default statement
      description
        "Mention the pseudowire role as primary or backup";
    }
    leaf protect {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type boolean;
      // NCS drop default statement
      description
        "This attribute should be enabled if there is a protection required.";
    }
    leaf primary-pw {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      // NCS drop when statement
      type leafref {
        path "/ncs:devices/ncs:device/ncs:live-status/pw:pseudowires/pw:pseudowire/pw:name" {
          tailf:xpath-root 3;
        }
      }
      description
        "Mention the primary pseudowire name";
    }
    leaf mode {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type cn-l3-types:live_ncs_pseudowire-mode;
      // NCS drop default statement
      description
        "Specify the pseudowire mode as mesh or spoke";
    }
    leaf vccv-ability {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type boolean;
      description
        "Use this attribute to set the pseudowire Virtual Circuit Connectivity Verification (VCCV)";
    }
    leaf vlan-tpid {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type cn-l3-types:live_ncs_mpls-tpid;
      description
        "Select the vlan tag protocol identifier";
    }
    leaf stats-collection {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type enumeration {
        enum "off" {
          description
            "specifies counter status on pseudowire is OFF";
        }
        enum "on" {
          description
            "specifies counter status on pseudowire is ON";
        }
      }
      // NCS drop default statement
      description
        "turn on/off statistics collection on the pseudowires";
    }
    leaf pw-loadbalance {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type enumeration {
        enum "disabled" {
          value 0;
          description
            "load-balancing disabled";
        }
        enum "fat-pw" {
          value 1;
          description
            "load-balance using FAT label below PW label";
        }
        enum "entropy" {
          value 2;
          description
            "load-balance using ELI/EL above PW label";
        }
      }
      // NCS drop default statement
      description
        "PW load-balancing";
    }
    leaf fat-capability {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      // NCS drop when statement
      type enumeration {
        enum "tx-rx" {
          value 0;
          description
            "enable FAT label receiving and transmitting both capability";
        }
        enum "rx" {
          value 1;
          description
            "enable FAT label receiving capability";
        }
        enum "tx" {
          value 2;
          description
            "enable FAT label transmitting capability";
        }
      }
      // NCS drop default statement
      description
        "FAT pseudowire capability for negotiation";
    }
    leaf cc-types {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type live_ncs_pseudowire-cctype;
      description
        "Use this attribute to set the CC Type for pseudowire signalling
         where each bit represent the CC Type in accordance with RFC 5085";
    }
    leaf tunnel-type {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type cn-l3-types:live_ncs_tunnel-type;
      description
        "This is an enumeration which defines different tunnel types";
    }
    leaf tunnel-name {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type string;
      description
        "User provided tunnel name over which PW needs to be created";
    }
    leaf tunnel-source-ip {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type inet:ipv4-address;
      description
        "User provided tunnel source-ip";
    }
    leaf tunnel-destination-ip {
      tailf:ncs-device-type "netconf";
      tailf:display-when "not(../../../../ncs:module) or ../../../../ncs:module[ncs:name='ciena-ietf-pseudowires'] or (../../../../ncs:live-status-protocol[not(ncs:capability)]) or (../../../../ncs:live-status-protocol/ncs:capability/ncs:module[.='ciena-ietf-pseudowires'])";
      type inet:ipv4-address;
      description
        "User provided tunnel destination-ip";
    }
  }
  augment "/ncs:devices/ncs:device/ncs:config/pw:pseudowires/pw:pseudowire" {
    description
      "Adding additional parameters to ietf-pseduowires yang file";
    leaf role {
      tailf:ncs-device-type "netconf";
      tailf:display-when "not(../../../../ncs:module) or ../../../../ncs:module[ncs:name='ciena-ietf-pseudowires']";
      type pw-role-type;
      default "primary";
      description
        "Mention the pseudowire role as primary or backup";
    }
    leaf protect {
      tailf:ncs-device-type "netconf";
      tailf:display-when "not(../../../../ncs:module) or ../../../../ncs:module[ncs:name='ciena-ietf-pseudowires']";
      type boolean;
      default "false";
      description
        "This attribute should be enabled if there is a protection required.";
    }
    leaf primary-pw {
      tailf:ncs-device-type "netconf";
      tailf:display-when "not(../../../../ncs:module) or ../../../../ncs:module[ncs:name='ciena-ietf-pseudowires']";
      when "../role = 'cnpw:backup'" {
        tailf:xpath-root 3;
      }
      type leafref {
        path "/ncs:devices/ncs:device/ncs:config/pw:pseudowires/pw:pseudowire/pw:name" {
          tailf:xpath-root 3;
        }
      }
      description
        "Mention the primary pseudowire name";
    }
    leaf mode {
      tailf:ncs-device-type "netconf";
      tailf:display-when "not(../../../../ncs:module) or ../../../../ncs:module[ncs:name='ciena-ietf-pseudowires']";
      type cn-l3-types:pseudowire-mode;
      default "mesh";
      description
        "Specify the pseudowire mode as mesh or spoke";
    }
    leaf vccv-ability {
      tailf:ncs-device-type "netconf";
      tailf:display-when "not(../../../../ncs:module) or ../../../../ncs:module[ncs:name='ciena-ietf-pseudowires']";
      type boolean;
      description
        "Use this attribute to set the pseudowire Virtual Circuit Connectivity Verification (VCCV)";
    }
    leaf vlan-tpid {
      tailf:ncs-device-type "netconf";
      tailf:display-when "not(../../../../ncs:module) or ../../../../ncs:module[ncs:name='ciena-ietf-pseudowires']";
      type cn-l3-types:mpls-tpid;
      description
        "Select the vlan tag protocol identifier";
    }
    leaf stats-collection {
      tailf:ncs-device-type "netconf";
      tailf:display-when "not(../../../../ncs:module) or ../../../../ncs:module[ncs:name='ciena-ietf-pseudowires']";
      type enumeration {
        enum "off" {
          description
            "specifies counter status on pseudowire is OFF";
        }
        enum "on" {
          description
            "specifies counter status on pseudowire is ON";
        }
      }
      default "off";
      description
        "turn on/off statistics collection on the pseudowires";
    }
    leaf pw-loadbalance {
      tailf:ncs-device-type "netconf";
      tailf:display-when "not(../../../../ncs:module) or ../../../../ncs:module[ncs:name='ciena-ietf-pseudowires']";
      type enumeration {
        enum "disabled" {
          value 0;
          description
            "load-balancing disabled";
        }
        enum "fat-pw" {
          value 1;
          description
            "load-balance using FAT label below PW label";
        }
        enum "entropy" {
          value 2;
          description
            "load-balance using ELI/EL above PW label";
        }
      }
      default "disabled";
      description
        "PW load-balancing";
    }
    leaf fat-capability {
      tailf:ncs-device-type "netconf";
      tailf:display-when "not(../../../../ncs:module) or ../../../../ncs:module[ncs:name='ciena-ietf-pseudowires']";
      when "../pw-loadbalance = 'fat-pw'" {
        tailf:xpath-root 3;
        description
          "The fat-capability value is only applicable to the fat-pw type loadbalance";
      }
      type enumeration {
        enum "tx-rx" {
          value 0;
          description
            "enable FAT label receiving and transmitting both capability";
        }
        enum "rx" {
          value 1;
          description
            "enable FAT label receiving capability";
        }
        enum "tx" {
          value 2;
          description
            "enable FAT label transmitting capability";
        }
      }
      default "tx-rx";
      description
        "FAT pseudowire capability for negotiation";
    }
    leaf cc-types {
      tailf:ncs-device-type "netconf";
      tailf:display-when "not(../../../../ncs:module) or ../../../../ncs:module[ncs:name='ciena-ietf-pseudowires']";
      type pseudowire-cctype;
      description
        "Use this attribute to set the CC Type for pseudowire signalling
         where each bit represent the CC Type in accordance with RFC 5085";
    }
    leaf tunnel-type {
      tailf:ncs-device-type "netconf";
      tailf:display-when "not(../../../../ncs:module) or ../../../../ncs:module[ncs:name='ciena-ietf-pseudowires']";
      type cn-l3-types:tunnel-type;
      description
        "This is an enumeration which defines different tunnel types";
    }
    leaf tunnel-name {
      tailf:ncs-device-type "netconf";
      tailf:display-when "not(../../../../ncs:module) or ../../../../ncs:module[ncs:name='ciena-ietf-pseudowires']";
      type string;
      description
        "User provided tunnel name over which PW needs to be created";
    }
    leaf tunnel-source-ip {
      tailf:ncs-device-type "netconf";
      tailf:display-when "not(../../../../ncs:module) or ../../../../ncs:module[ncs:name='ciena-ietf-pseudowires']";
      type inet:ipv4-address;
      description
        "User provided tunnel source-ip";
    }
    leaf tunnel-destination-ip {
      tailf:ncs-device-type "netconf";
      tailf:display-when "not(../../../../ncs:module) or ../../../../ncs:module[ncs:name='ciena-ietf-pseudowires']";
      type inet:ipv4-address;
      description
        "User provided tunnel destination-ip";
    }
  }
  augment "/ncs:devices/ncs:template/ncs:ned-id/ncs:config/pw:pseudowires/pw:pseudowire/pw:pw-type/pw:configured-pw/pw:configured-pw" {
    description
      "Adding additional parameters to ietf-pseduowires yang file";
    leaf pw-status {
      type string;
      // NCS drop default statement
      description
        "Enables PW status for Static PW.";
    }
    leaf pw-status-refresh-timer {
      units "seconds";
      type string;
      // NCS drop default statement
      description
        "pw status refresh timer is in seconds.After which a PW status is transmitted
         periodically if an AC fault has occurred.
         The range is <0-65535>. Default is 600 seconds.";
    }
  }
  augment "/ncs:devices/ncs:device/ncs:live-status/pw:pseudowires/pw:pseudowire/pw:pw-type/pw:configured-pw/pw:configured-pw" {
    description
      "Adding additional parameters to ietf-pseduowires yang file";
    leaf pw-status {
      tailf:ncs-device-type "netconf";
      tailf:display-when "not(../../../../../../../ncs:module) or ../../../../../../../ncs:module[ncs:name='ciena-ietf-pseudowires'] or (../../../../../../../ncs:live-status-protocol[not(ncs:capability)]) or (../../../../../../../ncs:live-status-protocol/ncs:capability/ncs:module[.='ciena-ietf-pseudowires'])";
      type boolean;
      // NCS drop default statement
      description
        "Enables PW status for Static PW.";
    }
    leaf pw-status-refresh-timer {
      tailf:ncs-device-type "netconf";
      tailf:display-when "not(../../../../../../../ncs:module) or ../../../../../../../ncs:module[ncs:name='ciena-ietf-pseudowires'] or (../../../../../../../ncs:live-status-protocol[not(ncs:capability)]) or (../../../../../../../ncs:live-status-protocol/ncs:capability/ncs:module[.='ciena-ietf-pseudowires'])";
      units "seconds";
      type uint16 {
        range "0..65535";
      }
      // NCS drop default statement
      description
        "pw status refresh timer is in seconds.After which a PW status is transmitted
         periodically if an AC fault has occurred.
         The range is <0-65535>. Default is 600 seconds.";
    }
  }
  augment "/ncs:devices/ncs:device/ncs:config/pw:pseudowires/pw:pseudowire/pw:pw-type/pw:configured-pw/pw:configured-pw" {
    description
      "Adding additional parameters to ietf-pseduowires yang file";
    leaf pw-status {
      tailf:ncs-device-type "netconf";
      tailf:display-when "not(../../../../../../../ncs:module) or ../../../../../../../ncs:module[ncs:name='ciena-ietf-pseudowires']";
      type boolean;
      default "false";
      description
        "Enables PW status for Static PW.";
    }
    leaf pw-status-refresh-timer {
      tailf:ncs-device-type "netconf";
      tailf:display-when "not(../../../../../../../ncs:module) or ../../../../../../../ncs:module[ncs:name='ciena-ietf-pseudowires']";
      units "seconds";
      type uint16 {
        range "0..65535";
      }
      default "600";
      description
        "pw status refresh timer is in seconds.After which a PW status is transmitted
         periodically if an AC fault has occurred.
         The range is <0-65535>. Default is 600 seconds.";
    }
  }

  identity backup {
    base role-of-pw;
    description
      "Role of PW is backup";
  }

  identity primary {
    base role-of-pw;
    description
      "Role of PW is primary";
  }

  identity role-of-pw {
    description
      "Role of pseudowire";
  }
}
