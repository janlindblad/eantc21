module ciena-ip-neighbor {
  // Generated by yanger -t ncs
  tailf:mount-id "saos1051-nc-1.0:saos1051-nc-1.0";
  tailf:ncs-device-type "netconf";

  namespace "urn:ciena:params:xml:ns:yang:ciena-ip-neighbor";
  prefix cn-ip-nbrs;

  import ietf-inet-types {
    prefix inet;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "yang model to show binding between neighbor ip address and mac address";

  revision 2018-02-01 {
    description
      "Initial revision of the yang model to support show ip neighbor";
  }

  typedef ncs_template_neighbor-state {
    type string;
  }

  typedef ncs_rpc_notif_neighbor-state {
    type enumeration {
      enum "PERMANENT" {
        description
          "never expires; never verified";
      }
      enum "NOARP" {
        description
          "normal expiration; never verified; no-op to data path";
      }
      enum "DELAY" {
        description
          "schedule ARP request; needs verification; no-op to data path";
      }
      enum "REACHABLE" {
        description
          "normal expiration";
      }
      enum "STALE" {
        description
          "still usable; needs verification";
      }
      enum "PROBE" {
        description
          "sending ARP request; no-op to data path";
      }
      enum "INCOMPLETE" {
        description
          "first ARP request sent; no-op to data path";
      }
      enum "FAILED" {
        description
          "no response received";
      }
    }
  }

  typedef live_ncs_neighbor-state {
    type enumeration {
      enum "PERMANENT" {
        description
          "never expires; never verified";
      }
      enum "NOARP" {
        description
          "normal expiration; never verified; no-op to data path";
      }
      enum "DELAY" {
        description
          "schedule ARP request; needs verification; no-op to data path";
      }
      enum "REACHABLE" {
        description
          "normal expiration";
      }
      enum "STALE" {
        description
          "still usable; needs verification";
      }
      enum "PROBE" {
        description
          "sending ARP request; no-op to data path";
      }
      enum "INCOMPLETE" {
        description
          "first ARP request sent; no-op to data path";
      }
      enum "FAILED" {
        description
          "no response received";
      }
    }
  }

  typedef neighbor-state {
    type enumeration {
      enum "PERMANENT" {
        description
          "never expires; never verified";
      }
      enum "NOARP" {
        description
          "normal expiration; never verified; no-op to data path";
      }
      enum "DELAY" {
        description
          "schedule ARP request; needs verification; no-op to data path";
      }
      enum "REACHABLE" {
        description
          "normal expiration";
      }
      enum "STALE" {
        description
          "still usable; needs verification";
      }
      enum "PROBE" {
        description
          "sending ARP request; no-op to data path";
      }
      enum "INCOMPLETE" {
        description
          "first ARP request sent; no-op to data path";
      }
      enum "FAILED" {
        description
          "no response received";
      }
    }
  }

  augment "/ncs:devices/ncs:device/ncs:config" {
    // NCS drop config false container 'ip-neighbor-state'
  }
  augment "/ncs:devices/ncs:device/ncs:live-status" {
    container ip-neighbor-state {
      tailf:ncs-device-type "netconf";
      tailf:display-when "not(../../ncs:module) or ../../ncs:module[ncs:name='ciena-ip-neighbor'] or (../../ncs:live-status-protocol[not(ncs:capability)]) or (../../ncs:live-status-protocol/ncs:capability/ncs:module[.='ciena-ip-neighbor'])";
      list ipv4 {
        key "interface-name ip-address";
        leaf interface-name {
          type string;
          description
            "Outgoing interface name.";
        }
        leaf ip-address {
          type inet:ipv4-address;
          description
            "Next-hop IPv4 Address.";
        }
        leaf mac-address {
          type yang:mac-address;
          description
            "Mac address binding on the next hop ip address";
        }
        leaf state {
          type live_ncs_neighbor-state;
          description
            "Indicate state of the ip neighbor entry";
        }
      }
      list ipv6 {
        key "interface-name ip-address";
        leaf interface-name {
          type string;
          description
            "Outgoing interface name.";
        }
        leaf ip-address {
          type inet:ipv6-address;
          description
            "Next-hop IPv6 Address.";
        }
        leaf mac-address {
          type yang:mac-address;
          description
            "Mac address binding on the next hop ip address";
        }
        leaf state {
          type live_ncs_neighbor-state;
          description
            "Indicate state of the ip neighbor entry";
        }
      }
    }
  }
  augment "/ncs:devices/ncs:template/ncs:ned-id/ncs:config" {
    // NCS drop config false container 'ip-neighbor-state'
  }
}
