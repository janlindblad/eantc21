module ciena-vdisk-mgmt {
  // Generated by yanger -t ncs
  tailf:mount-id "saos1051-nc-1.0:saos1051-nc-1.0";
  tailf:ncs-device-type "netconf";

  namespace "urn:ciena:params:xml:ns:yang:ciena-pn::ciena-vdisk-mgmt";
  prefix vdisk-mgmt;

  import ciena-file-mgmt {
    prefix file-mgmt;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data definition for virtual disk management";

  revision 2020-03-02 {
    description
      "Adding support for downloadable vdisk";
  }
  revision 2017-06-05 {
    description
      "1.0";
  }

  augment "/ncs:devices/ncs:device/ncs:config" {
    container vdisks {
      tailf:ncs-device-type "netconf";
      tailf:display-when "not(../../ncs:module) or ../../ncs:module[ncs:name='ciena-vdisk-mgmt']";
      description
        "Image related parameters";
      list vdisk {
        key "vdisk-name";
        description
          "List of virtual disks on the device";
        leaf vdisk-name {
          type string {
            length "1..200";
          }
          description
            "Name of the virtual disk";
        }
        choice type {
          case file {
            leaf file-size {
              mandatory true;
              type uint64 {
                range "1..max";
              }
              units "MB";
              description
                "Size of the virtual disk to be created";
            }
            leaf file-extension {
              mandatory true;
              type enumeration {
                enum "qcow2";
                enum "img";
                enum "raw";
              }
              description
                "Extension of virtual disk to be created. Following extensions are supported:
                 qcow2: Create .qcow2 virtual disk
                 img  : Create .img virtual disk
                 raw  : Create .raw virtual disk";
            }
            leaf file-encoding {
              type enumeration {
                enum "qcow2";
                enum "raw";
              }
              description
                "Type of encoding for the virtual disk,
                 qcow2: The encoding will be Qemu Copy on Write v 2.0
                 raw  : The encoding will be raw encoding";
            }
            description
              "config attributes for creating new file";
          }
          case downloaded-file {
            leaf file-name {
              type leafref {
                path "/ncs:devices/ncs:device/ncs:config/file-mgmt:files/file-mgmt:file/file-mgmt:file-name" {
                  tailf:xpath-root 3;
                }
              }
              description
                "Reference to file downloaded by file-management";
            }
            description
              "config attributes for already downloaded file";
          }
        }
      }
    }
  }
  augment "/ncs:devices/ncs:device/ncs:live-status" {
    container vdisks {
      tailf:ncs-device-type "netconf";
      tailf:display-when "not(../../ncs:module) or ../../ncs:module[ncs:name='ciena-vdisk-mgmt'] or (../../ncs:live-status-protocol[not(ncs:capability)]) or (../../ncs:live-status-protocol/ncs:capability/ncs:module[.='ciena-vdisk-mgmt'])";
      description
        "Image related parameters";
      list vdisk {
        key "vdisk-name";
        description
          "List of virtual disks on the device";
        leaf vdisk-name {
          type string {
            length "1..200";
          }
          description
            "Name of the virtual disk";
        }
        choice type {
          case file {
            leaf file-size {
              // NCS drop mandatory statement
              type uint64 {
                range "1..max";
              }
              units "MB";
              description
                "Size of the virtual disk to be created";
            }
            leaf file-extension {
              // NCS drop mandatory statement
              type enumeration {
                enum "qcow2";
                enum "img";
                enum "raw";
              }
              description
                "Extension of virtual disk to be created. Following extensions are supported:
                 qcow2: Create .qcow2 virtual disk
                 img  : Create .img virtual disk
                 raw  : Create .raw virtual disk";
            }
            leaf file-encoding {
              type enumeration {
                enum "qcow2";
                enum "raw";
              }
              description
                "Type of encoding for the virtual disk,
                 qcow2: The encoding will be Qemu Copy on Write v 2.0
                 raw  : The encoding will be raw encoding";
            }
            description
              "config attributes for creating new file";
          }
          case downloaded-file {
            leaf file-name {
              type leafref {
                path "/ncs:devices/ncs:device/ncs:live-status/file-mgmt:files/file-mgmt:file/file-mgmt:file-name" {
                  tailf:xpath-root 3;
                }
              }
              description
                "Reference to file downloaded by file-management";
            }
            description
              "config attributes for already downloaded file";
          }
        }
      }
    }
  }
  augment "/ncs:devices/ncs:template/ncs:ned-id/ncs:config" {
    container vdisks {
      description
        "Image related parameters";
      list vdisk {
        // NCS patched for predictable order
        ordered-by user;
        key "vdisk-name";
        description
          "List of virtual disks on the device";
        leaf vdisk-name {
          type string;
          description
            "Name of the virtual disk";
        }
        choice type {
          case file {
            leaf file-size {
              // NCS drop mandatory statement
              type string;
              units "MB";
              description
                "Size of the virtual disk to be created";
            }
            leaf file-extension {
              // NCS drop mandatory statement
              type string;
              description
                "Extension of virtual disk to be created. Following extensions are supported:
                 qcow2: Create .qcow2 virtual disk
                 img  : Create .img virtual disk
                 raw  : Create .raw virtual disk";
            }
            leaf file-encoding {
              type string;
              description
                "Type of encoding for the virtual disk,
                 qcow2: The encoding will be Qemu Copy on Write v 2.0
                 raw  : The encoding will be raw encoding";
            }
            description
              "config attributes for creating new file";
          }
          case downloaded-file {
            leaf file-name {
              type string;
              description
                "Reference to file downloaded by file-management";
            }
            description
              "config attributes for already downloaded file";
          }
        }
      }
    }
  }
}
