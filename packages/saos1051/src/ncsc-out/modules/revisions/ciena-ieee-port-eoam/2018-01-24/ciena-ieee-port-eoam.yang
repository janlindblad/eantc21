module ciena-ieee-port-eoam {
  // Generated by yanger -t ncs
  tailf:mount-id "saos1051-nc-1.0:saos1051-nc-1.0";
  tailf:ncs-device-type "netconf";

  namespace "urn:ciena:params:xml:ns:yang:ciena-pn:ciena-ieee:ns:yang:ieee-port-eoam";
  prefix eoam;

  import ietf-yang-types {
    prefix yang;
  }
  import openconfig-interfaces {
    prefix oc-if;
  }
  import ciena-openconfig-interfaces {
    prefix cn-oc-if;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module contains the schema definition for Ethernet
     Operations, Administration and Management (EOAM) at a port level.";

  revision 2018-01-24 {
    description
      "Updated to reflect move from ietf-interfaces to
       openconfig-interfaces.";
  }
  revision 2017-12-27 {
    description
      "Modified container names to meaningful names by adding
       protocol name (eoam) as their prefix.";
  }
  revision 2015-02-25 {
    description
      "Initial Version.";
    reference
      "[802.3ah] refers to:
       IEEE Std 802.3ah-2004: 'Draft amendment to -
       Information technology - Telecommunications and
       information exchange between systems - Local and
       metropolitan are networks - Specific requirements - Part
       3: Carrier sense multiple access with collision detection
       (CSMA/CD) access method and physical layer specifications
       - Media Access Control Parameters, Physical Layers and
       Management Parameters for subscriber access networks',
       October 2004.

       [802-2001] refers to:
       'IEEE Standard for LAN/MAN (Local Area
       Network/Metropolitan Area Network): Overview and
       Architecture', IEEE 802, June 2001.";
  }

  typedef ncs_template_oui {
    type string;
    description
      "An Organizationally Unique Identifier (OUI) is a 24-bit number
       that uniquely identifies a vendor, manufacturer, or other organization
       globally or worldwide.";
  }

  typedef ncs_template_functions-supported {
    type string;
    description
      "The OAM functions supported on this Ethernet-like interface.
       OAM consists of separate functional sets beyond the basic
       discovery process that is always required.  These functional
       groups can be supported independently by any implementation.
       These values are communicated to the peer via the local
       configuration field of Information OAMPDUs.";
  }

  typedef ncs_template_event {
    type string;
    description
      "The type of event that generated this entry in the event log.
       When the OUI is the IEEE 802.3 OUI of 0x0180C2, the following
       event types are defined:
          erroredSymbolEvent(1),
          erroredFramePeriodEvent(2),
          erroredFrameEvent(3),
          erroredFrameSecondsEvent(4),
          linkFault(256),
          dyingGaspEvent(257),
          criticalLinkEvent(258)
       The first four are considered threshold crossing events as they
       are generated when a metric exceeds a given value within a specified
       window. The other three are not threshold crossing events. When the OUI is
       not 0x0180C2, then some other organization has defined the event
       space. If event subtyping is known to the implementation, it may
       be reflected here. Otherwise, this value should return all Fs
       (0xFFFFFFFF).";
    reference "[802.3ah], 30.3.6.1.10 and 57.5.3.";
  }

  typedef ncs_template_event-location {
    type string;
    description
      "Indicates whether the event occured locally or was received
       from the OAM peer.";
  }

  typedef ncs_template_oper-status {
    type string;
    description
      "At initialization and failure conditions, two OAM entities on
       the same full-duplex Ethernet link begin a discovery phase to
       determine what OAM capabilities may be used on that link. The
       progress of this initialization is controlled by the OAM sub layer.";
  }

  typedef ncs_template_peer-status {
    type string;
    description
      "This object indicates whether the information in this row should
       be considered valid.";
  }

  typedef ncs_rpc_notif_oui {
    type string;
    description
      "An Organizationally Unique Identifier (OUI) is a 24-bit number
       that uniquely identifies a vendor, manufacturer, or other organization
       globally or worldwide.";
  }

  typedef ncs_rpc_notif_functions-supported {
    type bits {
      bit unidirectional-support {
        position 0;
        description
          "Setting 'unidirectionalSupport(0)' indicates that the OAM
           entity supports the transmission of OAMPDUs on links that are
           operating in unidirectional mode (traffic flowing in one
           direction only).  ";
      }
      bit loopback-support {
        position 1;
        description
          "Setting 'loopbackSupport(1)' indicates that
           the OAM entity can initiate and respond to loopback commands.";
      }
      bit event-support {
        position 2;
        description
          "Setting 'eventSupport(2)' indicates that the OAM entity can
           send and receive Event Notification OAMPDUs. ";
      }
      bit variable-support {
        position 3;
        description
          "Setting 'variableSupport(3)' indicates that the OAM entity can send
           and receive Variable Request and Response OAMPDUs.";
      }
      bit Unknown {
        position 4;
      }
    }
    description
      "The OAM functions supported on this Ethernet-like interface.
       OAM consists of separate functional sets beyond the basic
       discovery process that is always required.  These functional
       groups can be supported independently by any implementation.
       These values are communicated to the peer via the local
       configuration field of Information OAMPDUs.";
  }

  typedef ncs_rpc_notif_event {
    type string;
    description
      "The type of event that generated this entry in the event log.
       When the OUI is the IEEE 802.3 OUI of 0x0180C2, the following
       event types are defined:
          erroredSymbolEvent(1),
          erroredFramePeriodEvent(2),
          erroredFrameEvent(3),
          erroredFrameSecondsEvent(4),
          linkFault(256),
          dyingGaspEvent(257),
          criticalLinkEvent(258)
       The first four are considered threshold crossing events as they
       are generated when a metric exceeds a given value within a specified
       window. The other three are not threshold crossing events. When the OUI is
       not 0x0180C2, then some other organization has defined the event
       space. If event subtyping is known to the implementation, it may
       be reflected here. Otherwise, this value should return all Fs
       (0xFFFFFFFF).";
    reference "[802.3ah], 30.3.6.1.10 and 57.5.3.";
  }

  typedef ncs_rpc_notif_event-location {
    type enumeration {
      enum "local" {
        description
          "This event occured locally.";
      }
      enum "remote" {
        description
          "This event was received from the OAM peer via Ethernet OAM.";
      }
    }
    description
      "Indicates whether the event occured locally or was received
       from the OAM peer.";
  }

  typedef ncs_rpc_notif_oper-status {
    type enumeration {
      enum "disabled" {
        description
          "This value indicates that OAM is disabled on this interface via
           the admin-state";
      }
      enum "link-fault" {
        description
          "If the link has detected a fault and is transmitting OAMPDUs
           with a link fault indication, the value is link-fault";
      }
      enum "passive-wait" {
        description
          "The passive-wait state is returned only by OAM entities in passive
           mode (mode) and reflects the state in which the OAM entity is
           waiting to see if the peer device is OAM capable.";
      }
      enum "active-send-local" {
        description
          "The active-send-local is used by active mode devices (mode) and
           reflects the OAM entity actively trying to discover whether the
           peer has OAM capability but has not yet made that determination.";
      }
      enum "send-local-remote" {
        description
          "The state send-local-remote indicates that the local OAM entity
           has discovered the peer but has not yet accepted or rejected the
           configuration of the peer.";
      }
      enum "send-local-remote-ok" {
        description
          "If the OAM peering is allowed by the local device, the state
           moves to send-local-remote-ok.";
      }
      enum "locally-rejected" {
        description
          "The local device can, for whatever reason, decide that the peer
           device is unacceptable and decline OAM peering. If the local OAM
           entity rejects the peer OAM entity, the state becomes locally-rejected.
           Note that both the send-local-remote and locally-rejected states
           fall within the state SEND_LOCAL_REMOTE of the Discovery state
           diagram [802.3ah, Figure 57-5], with the difference being whether
           the local OAM client has actively rejected the peering or has
           just not indicated any decision yet. Whether a peering decision
           has been made is indicated via the local flags field in the OAMPDU
           (reflected in the aOAMLocalFlagsField of 30.3.6.1.10). ";
      }
      enum "remotely-rejected" {
        description
          "If the remote OAM entity rejects the peering, the state becomes
           oamPeeringRemotelyRejected(8). Note that both the sendLocalAndRemoteOk(6)
           and oamPeeringRemotelyRejected(8) states fall within the state
           SEND_LOCAL_REMOTE_OK of the Discovery state diagram [802.3ah,
           Figure 57-5], with the difference being whether the remote OAM
           client has rejected the peering or has just not yet decided. This
           is indicated via the remote flags field in the OAM PDU (reflected
           in the aOAMRemoteFlagsField of 30.3.6.1.11).";
      }
      enum "operational" {
        description
          "When the local OAM entity learns that both it and the remote
           OAM entity have accepted the peering, the state moves to operational(9)
           corresponding to the SEND_ANY state of the Discovery state diagram
           [802.3ah, Figure 57-5].";
      }
    }
    description
      "At initialization and failure conditions, two OAM entities on
       the same full-duplex Ethernet link begin a discovery phase to
       determine what OAM capabilities may be used on that link. The
       progress of this initialization is controlled by the OAM sub layer.";
  }

  typedef ncs_rpc_notif_peer-status {
    type enumeration {
      enum "active" {
        value 1;
        description
          "When active(1), the information is valid and represents the current
           peer of the OAM entity.";
      }
      enum "inactive" {
        value 2;
        description
          "When inactive(2), the information in this row is invalid. A value
           of inactive(2) is returned if the oper-status is disabled, passive-wait,
           or active-send-local. For all other values of oper-status, a value
           of active(1) is returned.";
      }
    }
    description
      "This object indicates whether the information in this row should
       be considered valid.";
  }

  typedef live_ncs_oui {
    type string;
    description
      "An Organizationally Unique Identifier (OUI) is a 24-bit number
       that uniquely identifies a vendor, manufacturer, or other organization
       globally or worldwide.";
  }

  typedef live_ncs_functions-supported {
    type bits {
      bit unidirectional-support {
        position 0;
        description
          "Setting 'unidirectionalSupport(0)' indicates that the OAM
           entity supports the transmission of OAMPDUs on links that are
           operating in unidirectional mode (traffic flowing in one
           direction only).  ";
      }
      bit loopback-support {
        position 1;
        description
          "Setting 'loopbackSupport(1)' indicates that
           the OAM entity can initiate and respond to loopback commands.";
      }
      bit event-support {
        position 2;
        description
          "Setting 'eventSupport(2)' indicates that the OAM entity can
           send and receive Event Notification OAMPDUs. ";
      }
      bit variable-support {
        position 3;
        description
          "Setting 'variableSupport(3)' indicates that the OAM entity can send
           and receive Variable Request and Response OAMPDUs.";
      }
      bit Unknown {
        position 4;
      }
    }
    description
      "The OAM functions supported on this Ethernet-like interface.
       OAM consists of separate functional sets beyond the basic
       discovery process that is always required.  These functional
       groups can be supported independently by any implementation.
       These values are communicated to the peer via the local
       configuration field of Information OAMPDUs.";
  }

  typedef live_ncs_event {
    type string;
    description
      "The type of event that generated this entry in the event log.
       When the OUI is the IEEE 802.3 OUI of 0x0180C2, the following
       event types are defined:
          erroredSymbolEvent(1),
          erroredFramePeriodEvent(2),
          erroredFrameEvent(3),
          erroredFrameSecondsEvent(4),
          linkFault(256),
          dyingGaspEvent(257),
          criticalLinkEvent(258)
       The first four are considered threshold crossing events as they
       are generated when a metric exceeds a given value within a specified
       window. The other three are not threshold crossing events. When the OUI is
       not 0x0180C2, then some other organization has defined the event
       space. If event subtyping is known to the implementation, it may
       be reflected here. Otherwise, this value should return all Fs
       (0xFFFFFFFF).";
    reference "[802.3ah], 30.3.6.1.10 and 57.5.3.";
  }

  typedef live_ncs_event-location {
    type enumeration {
      enum "local" {
        description
          "This event occured locally.";
      }
      enum "remote" {
        description
          "This event was received from the OAM peer via Ethernet OAM.";
      }
    }
    description
      "Indicates whether the event occured locally or was received
       from the OAM peer.";
  }

  typedef live_ncs_oper-status {
    type enumeration {
      enum "disabled" {
        description
          "This value indicates that OAM is disabled on this interface via
           the admin-state";
      }
      enum "link-fault" {
        description
          "If the link has detected a fault and is transmitting OAMPDUs
           with a link fault indication, the value is link-fault";
      }
      enum "passive-wait" {
        description
          "The passive-wait state is returned only by OAM entities in passive
           mode (mode) and reflects the state in which the OAM entity is
           waiting to see if the peer device is OAM capable.";
      }
      enum "active-send-local" {
        description
          "The active-send-local is used by active mode devices (mode) and
           reflects the OAM entity actively trying to discover whether the
           peer has OAM capability but has not yet made that determination.";
      }
      enum "send-local-remote" {
        description
          "The state send-local-remote indicates that the local OAM entity
           has discovered the peer but has not yet accepted or rejected the
           configuration of the peer.";
      }
      enum "send-local-remote-ok" {
        description
          "If the OAM peering is allowed by the local device, the state
           moves to send-local-remote-ok.";
      }
      enum "locally-rejected" {
        description
          "The local device can, for whatever reason, decide that the peer
           device is unacceptable and decline OAM peering. If the local OAM
           entity rejects the peer OAM entity, the state becomes locally-rejected.
           Note that both the send-local-remote and locally-rejected states
           fall within the state SEND_LOCAL_REMOTE of the Discovery state
           diagram [802.3ah, Figure 57-5], with the difference being whether
           the local OAM client has actively rejected the peering or has
           just not indicated any decision yet. Whether a peering decision
           has been made is indicated via the local flags field in the OAMPDU
           (reflected in the aOAMLocalFlagsField of 30.3.6.1.10). ";
      }
      enum "remotely-rejected" {
        description
          "If the remote OAM entity rejects the peering, the state becomes
           oamPeeringRemotelyRejected(8). Note that both the sendLocalAndRemoteOk(6)
           and oamPeeringRemotelyRejected(8) states fall within the state
           SEND_LOCAL_REMOTE_OK of the Discovery state diagram [802.3ah,
           Figure 57-5], with the difference being whether the remote OAM
           client has rejected the peering or has just not yet decided. This
           is indicated via the remote flags field in the OAM PDU (reflected
           in the aOAMRemoteFlagsField of 30.3.6.1.11).";
      }
      enum "operational" {
        description
          "When the local OAM entity learns that both it and the remote
           OAM entity have accepted the peering, the state moves to operational(9)
           corresponding to the SEND_ANY state of the Discovery state diagram
           [802.3ah, Figure 57-5].";
      }
    }
    description
      "At initialization and failure conditions, two OAM entities on
       the same full-duplex Ethernet link begin a discovery phase to
       determine what OAM capabilities may be used on that link. The
       progress of this initialization is controlled by the OAM sub layer.";
  }

  typedef live_ncs_peer-status {
    type enumeration {
      enum "active" {
        value 1;
        description
          "When active(1), the information is valid and represents the current
           peer of the OAM entity.";
      }
      enum "inactive" {
        value 2;
        description
          "When inactive(2), the information in this row is invalid. A value
           of inactive(2) is returned if the oper-status is disabled, passive-wait,
           or active-send-local. For all other values of oper-status, a value
           of active(1) is returned.";
      }
    }
    description
      "This object indicates whether the information in this row should
       be considered valid.";
  }

  typedef oui {
    type string;
    description
      "An Organizationally Unique Identifier (OUI) is a 24-bit number
       that uniquely identifies a vendor, manufacturer, or other organization
       globally or worldwide.";
  }

  typedef functions-supported {
    type bits {
      bit unidirectional-support {
        position 0;
        description
          "Setting 'unidirectionalSupport(0)' indicates that the OAM
           entity supports the transmission of OAMPDUs on links that are
           operating in unidirectional mode (traffic flowing in one
           direction only).  ";
      }
      bit loopback-support {
        position 1;
        description
          "Setting 'loopbackSupport(1)' indicates that
           the OAM entity can initiate and respond to loopback commands.";
      }
      bit event-support {
        position 2;
        description
          "Setting 'eventSupport(2)' indicates that the OAM entity can
           send and receive Event Notification OAMPDUs. ";
      }
      bit variable-support {
        position 3;
        description
          "Setting 'variableSupport(3)' indicates that the OAM entity can send
           and receive Variable Request and Response OAMPDUs.";
      }
      bit Unknown {
        position 4;
      }
    }
    description
      "The OAM functions supported on this Ethernet-like interface.
       OAM consists of separate functional sets beyond the basic
       discovery process that is always required.  These functional
       groups can be supported independently by any implementation.
       These values are communicated to the peer via the local
       configuration field of Information OAMPDUs.";
  }

  typedef event {
    type string;
    description
      "The type of event that generated this entry in the event log.
       When the OUI is the IEEE 802.3 OUI of 0x0180C2, the following
       event types are defined:
          erroredSymbolEvent(1),
          erroredFramePeriodEvent(2),
          erroredFrameEvent(3),
          erroredFrameSecondsEvent(4),
          linkFault(256),
          dyingGaspEvent(257),
          criticalLinkEvent(258)
       The first four are considered threshold crossing events as they
       are generated when a metric exceeds a given value within a specified
       window. The other three are not threshold crossing events. When the OUI is
       not 0x0180C2, then some other organization has defined the event
       space. If event subtyping is known to the implementation, it may
       be reflected here. Otherwise, this value should return all Fs
       (0xFFFFFFFF).";
    reference "[802.3ah], 30.3.6.1.10 and 57.5.3.";
  }

  typedef event-location {
    type enumeration {
      enum "local" {
        description
          "This event occured locally.";
      }
      enum "remote" {
        description
          "This event was received from the OAM peer via Ethernet OAM.";
      }
    }
    description
      "Indicates whether the event occured locally or was received
       from the OAM peer.";
  }

  typedef oper-status {
    type enumeration {
      enum "disabled" {
        description
          "This value indicates that OAM is disabled on this interface via
           the admin-state";
      }
      enum "link-fault" {
        description
          "If the link has detected a fault and is transmitting OAMPDUs
           with a link fault indication, the value is link-fault";
      }
      enum "passive-wait" {
        description
          "The passive-wait state is returned only by OAM entities in passive
           mode (mode) and reflects the state in which the OAM entity is
           waiting to see if the peer device is OAM capable.";
      }
      enum "active-send-local" {
        description
          "The active-send-local is used by active mode devices (mode) and
           reflects the OAM entity actively trying to discover whether the
           peer has OAM capability but has not yet made that determination.";
      }
      enum "send-local-remote" {
        description
          "The state send-local-remote indicates that the local OAM entity
           has discovered the peer but has not yet accepted or rejected the
           configuration of the peer.";
      }
      enum "send-local-remote-ok" {
        description
          "If the OAM peering is allowed by the local device, the state
           moves to send-local-remote-ok.";
      }
      enum "locally-rejected" {
        description
          "The local device can, for whatever reason, decide that the peer
           device is unacceptable and decline OAM peering. If the local OAM
           entity rejects the peer OAM entity, the state becomes locally-rejected.
           Note that both the send-local-remote and locally-rejected states
           fall within the state SEND_LOCAL_REMOTE of the Discovery state
           diagram [802.3ah, Figure 57-5], with the difference being whether
           the local OAM client has actively rejected the peering or has
           just not indicated any decision yet. Whether a peering decision
           has been made is indicated via the local flags field in the OAMPDU
           (reflected in the aOAMLocalFlagsField of 30.3.6.1.10). ";
      }
      enum "remotely-rejected" {
        description
          "If the remote OAM entity rejects the peering, the state becomes
           oamPeeringRemotelyRejected(8). Note that both the sendLocalAndRemoteOk(6)
           and oamPeeringRemotelyRejected(8) states fall within the state
           SEND_LOCAL_REMOTE_OK of the Discovery state diagram [802.3ah,
           Figure 57-5], with the difference being whether the remote OAM
           client has rejected the peering or has just not yet decided. This
           is indicated via the remote flags field in the OAM PDU (reflected
           in the aOAMRemoteFlagsField of 30.3.6.1.11).";
      }
      enum "operational" {
        description
          "When the local OAM entity learns that both it and the remote
           OAM entity have accepted the peering, the state moves to operational(9)
           corresponding to the SEND_ANY state of the Discovery state diagram
           [802.3ah, Figure 57-5].";
      }
    }
    description
      "At initialization and failure conditions, two OAM entities on
       the same full-duplex Ethernet link begin a discovery phase to
       determine what OAM capabilities may be used on that link. The
       progress of this initialization is controlled by the OAM sub layer.";
  }

  typedef peer-status {
    type enumeration {
      enum "active" {
        value 1;
        description
          "When active(1), the information is valid and represents the current
           peer of the OAM entity.";
      }
      enum "inactive" {
        value 2;
        description
          "When inactive(2), the information in this row is invalid. A value
           of inactive(2) is returned if the oper-status is disabled, passive-wait,
           or active-send-local. For all other values of oper-status, a value
           of active(1) is returned.";
      }
    }
    description
      "This object indicates whether the information in this row should
       be considered valid.";
  }

  grouping ncs_template_port-config-objects {
    leaf pdu-timer {
      type string;
      description
        "The time in milliseconds between information OAMPDUs being transmitted
         via the Ethernet port";
    }
    leaf link-lost-timer {
      type string;
      description
        "The time in milliseconds to wait for an information OAMPDU to
         be received from a peer via the Ethernet port, before declaring
         the link as lost";
    }
    description
      "OAM port configuration objects.";
  }

  grouping ncs_template_loopback-statistics {
    leaf loopback-control-transmitted {
      type string;
      units "frames";
      description
        "A count of the number of Loopback Control OAMPDUs transmitted
         on this interface. A Loopback Control OAMPDU is indicated by a
         valid frame with (1) destination MAC address equal to that of
         the reserved MAC address for Slow Protocols (See 43B of [802.3ah]),
         (2) a lengthOrType field equal to the reserved type for Slow Protocols,
         (3) a Slow Protocols subtype equal to that of the subtype reserved
         for OAM, and (4) an OAMPDU code that equals the OAM Loopback Control
         code. Discontinuities of this counter can occur at re-initialization
         of the management system, and at other times as indicated by the
         value of the ifCounterDiscontinuityTime.";
      reference "[802.3ah], 30.3.6.1.26.";
    }
    leaf loopback-control-received {
      type string;
      units "frames";
      description
        "A count of the number of Loopback Control OAMPDUs received on
         this interface. A Loopback Control OAMPDU is indicated by a valid
         frame with (1) destination MAC address equal to that of the reserved
         MAC address for Slow Protocols (See 43B of [802.3ah]), (2) a lengthOrType
         field equal to the reserved type for Slow Protocols, (3) a Slow
         Protocols subtype equal to that of the subtype reserved for OAM,
         and (4) an OAMPDU code that equals the OAM Loopback Control code.
         Discontinuities of this counter can occur at re-initialization
         of the management system, and at other times as indicated by the
         value of the ifCounterDiscontinuityTime.";
      reference "[802.3ah], 30.3.6.1.27.";
    }
    description
      "Loopback transmit and receive statistics.";
  }

  grouping ncs_rpc_notif_port-config-objects {
    leaf pdu-timer {
      type uint16;
      description
        "The time in milliseconds between information OAMPDUs being transmitted
         via the Ethernet port";
    }
    leaf link-lost-timer {
      type uint16;
      description
        "The time in milliseconds to wait for an information OAMPDU to
         be received from a peer via the Ethernet port, before declaring
         the link as lost";
    }
    description
      "OAM port configuration objects.";
  }

  grouping ncs_rpc_notif_loopback-statistics {
    leaf loopback-control-transmitted {
      type yang:counter32;
      units "frames";
      description
        "A count of the number of Loopback Control OAMPDUs transmitted
         on this interface. A Loopback Control OAMPDU is indicated by a
         valid frame with (1) destination MAC address equal to that of
         the reserved MAC address for Slow Protocols (See 43B of [802.3ah]),
         (2) a lengthOrType field equal to the reserved type for Slow Protocols,
         (3) a Slow Protocols subtype equal to that of the subtype reserved
         for OAM, and (4) an OAMPDU code that equals the OAM Loopback Control
         code. Discontinuities of this counter can occur at re-initialization
         of the management system, and at other times as indicated by the
         value of the ifCounterDiscontinuityTime.";
      reference "[802.3ah], 30.3.6.1.26.";
    }
    leaf loopback-control-received {
      type yang:counter32;
      units "frames";
      description
        "A count of the number of Loopback Control OAMPDUs received on
         this interface. A Loopback Control OAMPDU is indicated by a valid
         frame with (1) destination MAC address equal to that of the reserved
         MAC address for Slow Protocols (See 43B of [802.3ah]), (2) a lengthOrType
         field equal to the reserved type for Slow Protocols, (3) a Slow
         Protocols subtype equal to that of the subtype reserved for OAM,
         and (4) an OAMPDU code that equals the OAM Loopback Control code.
         Discontinuities of this counter can occur at re-initialization
         of the management system, and at other times as indicated by the
         value of the ifCounterDiscontinuityTime.";
      reference "[802.3ah], 30.3.6.1.27.";
    }
    description
      "Loopback transmit and receive statistics.";
  }

  grouping live_ncs_port-config-objects {
    leaf pdu-timer {
      type uint16;
      description
        "The time in milliseconds between information OAMPDUs being transmitted
         via the Ethernet port";
    }
    leaf link-lost-timer {
      type uint16;
      description
        "The time in milliseconds to wait for an information OAMPDU to
         be received from a peer via the Ethernet port, before declaring
         the link as lost";
    }
    description
      "OAM port configuration objects.";
  }

  grouping live_ncs_loopback-statistics {
    leaf loopback-control-transmitted {
      type yang:counter32;
      units "frames";
      description
        "A count of the number of Loopback Control OAMPDUs transmitted
         on this interface. A Loopback Control OAMPDU is indicated by a
         valid frame with (1) destination MAC address equal to that of
         the reserved MAC address for Slow Protocols (See 43B of [802.3ah]),
         (2) a lengthOrType field equal to the reserved type for Slow Protocols,
         (3) a Slow Protocols subtype equal to that of the subtype reserved
         for OAM, and (4) an OAMPDU code that equals the OAM Loopback Control
         code. Discontinuities of this counter can occur at re-initialization
         of the management system, and at other times as indicated by the
         value of the ifCounterDiscontinuityTime.";
      reference "[802.3ah], 30.3.6.1.26.";
    }
    leaf loopback-control-received {
      type yang:counter32;
      units "frames";
      description
        "A count of the number of Loopback Control OAMPDUs received on
         this interface. A Loopback Control OAMPDU is indicated by a valid
         frame with (1) destination MAC address equal to that of the reserved
         MAC address for Slow Protocols (See 43B of [802.3ah]), (2) a lengthOrType
         field equal to the reserved type for Slow Protocols, (3) a Slow
         Protocols subtype equal to that of the subtype reserved for OAM,
         and (4) an OAMPDU code that equals the OAM Loopback Control code.
         Discontinuities of this counter can occur at re-initialization
         of the management system, and at other times as indicated by the
         value of the ifCounterDiscontinuityTime.";
      reference "[802.3ah], 30.3.6.1.27.";
    }
    description
      "Loopback transmit and receive statistics.";
  }

  grouping port-config-objects {
    leaf pdu-timer {
      type uint16;
      description
        "The time in milliseconds between information OAMPDUs being transmitted
         via the Ethernet port";
    }
    leaf link-lost-timer {
      type uint16;
      description
        "The time in milliseconds to wait for an information OAMPDU to
         be received from a peer via the Ethernet port, before declaring
         the link as lost";
    }
    description
      "OAM port configuration objects.";
  }

  grouping loopback-statistics {
    leaf loopback-control-transmitted {
      type yang:counter32;
      units "frames";
      description
        "A count of the number of Loopback Control OAMPDUs transmitted
         on this interface. A Loopback Control OAMPDU is indicated by a
         valid frame with (1) destination MAC address equal to that of
         the reserved MAC address for Slow Protocols (See 43B of [802.3ah]),
         (2) a lengthOrType field equal to the reserved type for Slow Protocols,
         (3) a Slow Protocols subtype equal to that of the subtype reserved
         for OAM, and (4) an OAMPDU code that equals the OAM Loopback Control
         code. Discontinuities of this counter can occur at re-initialization
         of the management system, and at other times as indicated by the
         value of the ifCounterDiscontinuityTime.";
      reference "[802.3ah], 30.3.6.1.26.";
    }
    leaf loopback-control-received {
      type yang:counter32;
      units "frames";
      description
        "A count of the number of Loopback Control OAMPDUs received on
         this interface. A Loopback Control OAMPDU is indicated by a valid
         frame with (1) destination MAC address equal to that of the reserved
         MAC address for Slow Protocols (See 43B of [802.3ah]), (2) a lengthOrType
         field equal to the reserved type for Slow Protocols, (3) a Slow
         Protocols subtype equal to that of the subtype reserved for OAM,
         and (4) an OAMPDU code that equals the OAM Loopback Control code.
         Discontinuities of this counter can occur at re-initialization
         of the management system, and at other times as indicated by the
         value of the ifCounterDiscontinuityTime.";
      reference "[802.3ah], 30.3.6.1.27.";
    }
    description
      "Loopback transmit and receive statistics.";
  }

  augment "/ncs:devices/ncs:device/ncs:rpc" {
    container rpc-eoam-loopback-command {
      tailf:ncs-device-type "netconf";
      tailf:display-when "not(../../ncs:module) or ../../ncs:module[ncs:name='ciena-ieee-port-eoam']";
      tailf:action eoam-loopback-command {
        tailf:actionpoint ncsproxy {
          tailf:internal;
        }
        description
          "Initiate or terminate remote loopback with an OAM peer.";
        input {
          leaf loopback-command {
            type enumeration {
              enum "start-remote-loopback" {
                description
                  "start-remote-loopback causes the local OAM client to send a loopback
                   OAMPDU to the OAM peer with the loopback enable flags set. These
                   setting only take effect is the oper-status for the Ethernet port
                   is operational.";
              }
              enum "stop-remote-loopback" {
                description
                  "stop-remote-loopback causes the local OAM client to send a loopback
                   OAMPDU to the OAM peer with the loopback enable flags cleared.
                   These setting only take effect is the oper-status for the Ethernet
                   port is operational.";
              }
            }
          }
        }
        output {
          uses ncs_rpc_notif_loopback-statistics;
        }
      }
    }
  }
  augment "/ncs:devices/ncs:device-group/ncs:ned-id/ncs:rpc" {
    container rpc-eoam-loopback-command {
      tailf:ncs-device-type "netconf";
      tailf:display-when "/ncs:devices/ncs:device[ncs:name=current()/../../../ncs:member]/ncs:module[ncs:name='ciena-ieee-port-eoam']";
      tailf:action eoam-loopback-command {
        tailf:actionpoint ncsproxy {
          tailf:internal;
        }
        description
          "Initiate or terminate remote loopback with an OAM peer.";
        input {
          leaf loopback-command {
            type enumeration {
              enum "start-remote-loopback" {
                description
                  "start-remote-loopback causes the local OAM client to send a loopback
                   OAMPDU to the OAM peer with the loopback enable flags set. These
                   setting only take effect is the oper-status for the Ethernet port
                   is operational.";
              }
              enum "stop-remote-loopback" {
                description
                  "stop-remote-loopback causes the local OAM client to send a loopback
                   OAMPDU to the OAM peer with the loopback enable flags cleared.
                   These setting only take effect is the oper-status for the Ethernet
                   port is operational.";
              }
            }
          }
        }
        output {
          container "device" {
            leaf "name" {
              type string;
            }
            leaf "info" {
              type string;
            }
            container "result" {
              uses ncs_rpc_notif_loopback-statistics;
            }
          }
        }
      }
    }
  }
  augment "/ncs:devices/ncs:device/ncs:netconf-notifications/ncs:received-notifications/ncs:notification/ncs:data" {
    container eoam-link-event {
      presence "";
      config false;
      leaf log-port {
        type string;
        description
          "An Ethernet port on the switch.";
      }
      leaf log-type {
        type ncs_rpc_notif_event;
      }
      leaf log-location {
        type ncs_rpc_notif_event-location;
      }
    }
  }
  augment "/ncs:devices/ncs:template/ncs:ned-id/ncs:config/oc-if:interfaces/oc-if:interface/oc-if:config" {
    // NCS drop when statement
    container eoam-port-config {
      leaf admin-status {
        type string;
        // NCS drop default statement
        description
          "EOAM port admin state.";
      }
      leaf mode {
        type string;
        // NCS drop default statement
        description
          "The mode of OAM opertion for this Ethernet like interface. OAM
            on Ethernet interfaces maybe in active mode or passive mode.";
      }
      uses ncs_template_port-config-objects;
      description
        "EOAM port state configuration.";
    }
    container eoam-loopback-port-config {
      leaf loopback-ignore-rx {
        type string;
        // NCS drop default statement
        description
          "Since OAM loopback is a disruptive operation (user traffic does
           not pass), this attribute provides a mechanism to provide controls
           over whether received OAM loopback commands are processed or ignored.
           The attribute has no meaning if the local OAM entity does not support
           the loopback function (as defined in functions-supported).";
      }
      description
        "EOAM port loopback confguration.";
    }
    container eoam-port-event-config {
      leaf error-frame-period-window {
        type string;
        units "frames";
        description
          "The number of frames over which the threshold is defined. The
           default value of the window is the number of minimum size Ethernet
           frames that can be received over the physical layer in one second.
           If error-frame-period-threshold frame errors occur within a window
           of error-frame-period-window frames, an Event Notification OAMPDU
           should be generated with an Errored Frame Period Event TLV indicating
           the threshold has been crossed in this window.
           +------------ Range of errd-frame-period-window values------------+
           |     10 mbps link :     1488 -     892800 |
           |    100 mbps link :    14880 -    8928000 |
           |   1000 mbps link :   148810 -   89285760 |
           |  10000 mbps link :  1488096 -  892857120 |
           | 100000 mbps link : 14880953 - 4294967295 |
           +-----------------------------------------------------------------+";
        reference "[802.3ah], 30.3.6.1.38";
      }
      leaf error-frame-period-threshold {
        type string;
        units "frames";
        // NCS drop default statement
        description
          "The number of frame errors that must occur for this event to
           be triggered. The default value is one frame error. If error-frame-period-threshold
           frame errors occur within a window of error-frame-period-window
           frames, an Event Notification OAMPDU should be generated with
           an Errored Frame Period Event TLV indicating the threshold has
           been crossed in this window.";
        reference "[802.3ah], 30.3.6.1.38";
      }
      leaf error-frame-period-event-notification {
        type string;
        // NCS drop default statement
        description
          "Indicates whether the occurrence of an Errored Frame Period Event
           should result in an Event Notification OAMPDU generated by the
           OAM layer. By default, this attribute is 'on' for Ethernet like
           interfaces that support OAM. If the OAM layer does not support
           event notifications (as indicated via the functions-supported
           attribute), this value is ignored.";
      }
      leaf error-frame-window {
        type string;
        units "tenths-of-a-second";
        // NCS drop default statement
        description
          "The amount of time (in 100ms increments) over which the threshold
           is defined. The default value is 10 (1 second). If error-frame-threshold
           frame errors occur within a window of error-frame-window seconds
           (measured in tenths of seconds), an Event Notification OAMPDU
           should be generated with an Errored Frame Event TLV indicating
           the threshold has been crossed in this window.";
        reference "[802.3ah], 30.3.6.1.38";
      }
      leaf error-frame-threshold {
        type string;
        units "frames";
        // NCS drop default statement
        description
          "The number of frame errors that must occur for this event to
           be triggered. The default value is one frame error. If error-frame-threshold
           frame errors occur within a window of error-frame-window (in tenths
           of seconds), an Event Notification OAMPDU should be generated
           with an Errored Frame Event TLV indicating the threshold has been
           crossed in this window.";
        reference "[802.3ah], 30.3.6.1.36";
      }
      leaf error-frame-event-notification {
        type string;
        // NCS drop default statement
        description
          "Indicates whether the occurrence of an Errored Frame Event should
           result in an Event Notification OAMPDU generated by the OAM layer.
           By default, this attribute should be 'on' for Ethernet like interfaces
           that support OAM. If the OAM layer does not support event notifications
           (as indicated via the functions-supported attribute), this value
           is ignored.";
      }
      leaf error-frame-seconds-summary-window {
        type string;
        // NCS drop default statement
        units "tenths-of-a-second";
        description
          "The amount of time (in 100ms intervals) over which the threshold
           is defined. The default value is 100 (10 seconds). If error-frame-seconds-summary-threshold
           frame errors occur within a window of error-frame-seconds-summary-window
           (in tenths of seconds), an Event Notification OAMPDU should be
           generated with an Errored Frame Seconds Summary Event TLV indicating
           the threshold has been crossed in this window.";
        reference "[802.3ah], 30.3.6.1.40";
      }
      leaf error-frame-seconds-summary-threshold {
        type string;
        units "errored-frame-seconds";
        // NCS drop default statement
        description
          "The number of errored frame seconds that must occur for this
           event to be triggered. The default value is one errored frame
           second. If error-frame-seconds-summary-threshold frame errors
           occur within a window of error-frame-seconds-summary-window (in
           tenths of seconds), an Event Notification OAMPDU should be generated
           with an Errored Frame Seconds Summary Event TLV indicating the
           threshold has been crossed in this window.";
        reference "[802.3ah], 30.3.6.1.40";
      }
      leaf error-frame-seconds-event-notification {
        type string;
        // NCS drop default statement
        description
          "Indicates whether the occurrence of an Errored Frame Seconds
           Summary Event should result in an Event Notification OAMPDU generated
           by the OAM layer. By default, this object should have the value
           'on' for Ethernet like interfaces that support OAM. If the OAM
           layer does not support event notifications (as indicated via the
           functions-supported attribute), this value is ignored.";
      }
      leaf dying-gasp {
        type string;
        // NCS drop default statement
        description
          "Indicates whether the local device should attempt to indicate
           a dying gasp fault via the OAMPDU flags field to its peer OAM
           entity. If the system does not support dying gasp capability,
           setting this object has no effect, and reading the object should
           always result in 'disable'. By default, this object should have
           the value enable for Ethernet like interfaces that support OAM.
           If the OAM layer does not support event notifications (as indicated
           via the functions-supported attribute), this value is ignored.";
      }
      leaf critical-event {
        type string;
        // NCS drop default statement
        description
          "Indicates whether the local device should attempt to indicate
           a critical event has occurred via the OAMPDU flags field to its
           peer OAM entity. By default, this object should have the value
           'enable' for Ethernet like interfaces that support OAM. If the
           OAM layer does not support event notifications (as indicated via
           the functions-supported attribute), this value is ignored.";
      }
      description
        "EOAM port event generation configuration.";
    }
    description
      "EOAM port configuration.";
  }
  augment "/ncs:devices/ncs:device/ncs:live-status/oc-if:interfaces/oc-if:interface/oc-if:config" {
    // NCS drop when statement
    container eoam-port-config {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf admin-status {
        type enumeration {
          enum "enable" {
            description
              "Enable OAM administratively on this port or interface";
          }
          enum "disable" {
            description
              "Disable OAM administratively on this port or interface.
               The OAM admin-status always starts in the disabled state until
               an explicit management action or configuration information is
               retained by the system and causes a transition to the enabled
               state";
          }
        }
        // NCS drop default statement
        description
          "EOAM port admin state.";
      }
      leaf mode {
        type enumeration {
          enum "active" {
            description
              "Active mode provides additional capabilities to initiate
               monitoring activities with the remote OAM peer entity.
               As an example, an active OAM entity can put the
               remote OAM entity in a loopback state, where a passive OAM entity
               cannot. The default value of mode is dependent on the type of
               system on which this Ethernet like interface resides. The default
               value should be 'active' unless it is known that this system should
               take on a subservient role to the other device connected over
               this interface. Changing this value results in incrementing the
               configuration revision field of locally generated OAMPDUs (30.3.6.1.12)
               and potentially causes re-doing of the OAM discovery process if
               the oper-status was already operational.";
          }
          enum "passive" {
            description
              "Passive mode generally waits for the peer to initiate OAM
               actions with it.";
          }
        }
        // NCS drop default statement
        description
          "The mode of OAM opertion for this Ethernet like interface. OAM
            on Ethernet interfaces maybe in active mode or passive mode.";
      }
      uses live_ncs_port-config-objects;
      description
        "EOAM port state configuration.";
    }
    container eoam-loopback-port-config {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf loopback-ignore-rx {
        type enumeration {
          enum "ignore" {
            description
              "When the value is ignore, received loopback commands are ignored.
               The default value is to ignore loopback commands (ignore).";
          }
          enum "process" {
            description
              "When the value is process, OAM loopback commands are processed.";
          }
        }
        // NCS drop default statement
        description
          "Since OAM loopback is a disruptive operation (user traffic does
           not pass), this attribute provides a mechanism to provide controls
           over whether received OAM loopback commands are processed or ignored.
           The attribute has no meaning if the local OAM entity does not support
           the loopback function (as defined in functions-supported).";
      }
      description
        "EOAM port loopback confguration.";
    }
    container eoam-port-event-config {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf error-frame-period-window {
        type uint32;
        units "frames";
        description
          "The number of frames over which the threshold is defined. The
           default value of the window is the number of minimum size Ethernet
           frames that can be received over the physical layer in one second.
           If error-frame-period-threshold frame errors occur within a window
           of error-frame-period-window frames, an Event Notification OAMPDU
           should be generated with an Errored Frame Period Event TLV indicating
           the threshold has been crossed in this window.
           +------------ Range of errd-frame-period-window values------------+
           |     10 mbps link :     1488 -     892800 |
           |    100 mbps link :    14880 -    8928000 |
           |   1000 mbps link :   148810 -   89285760 |
           |  10000 mbps link :  1488096 -  892857120 |
           | 100000 mbps link : 14880953 - 4294967295 |
           +-----------------------------------------------------------------+";
        reference "[802.3ah], 30.3.6.1.38";
      }
      leaf error-frame-period-threshold {
        type uint32;
        units "frames";
        // NCS drop default statement
        description
          "The number of frame errors that must occur for this event to
           be triggered. The default value is one frame error. If error-frame-period-threshold
           frame errors occur within a window of error-frame-period-window
           frames, an Event Notification OAMPDU should be generated with
           an Errored Frame Period Event TLV indicating the threshold has
           been crossed in this window.";
        reference "[802.3ah], 30.3.6.1.38";
      }
      leaf error-frame-period-event-notification {
        type boolean;
        // NCS drop default statement
        description
          "Indicates whether the occurrence of an Errored Frame Period Event
           should result in an Event Notification OAMPDU generated by the
           OAM layer. By default, this attribute is 'on' for Ethernet like
           interfaces that support OAM. If the OAM layer does not support
           event notifications (as indicated via the functions-supported
           attribute), this value is ignored.";
      }
      leaf error-frame-window {
        type uint32 {
          range "10..600";
        }
        units "tenths-of-a-second";
        // NCS drop default statement
        description
          "The amount of time (in 100ms increments) over which the threshold
           is defined. The default value is 10 (1 second). If error-frame-threshold
           frame errors occur within a window of error-frame-window seconds
           (measured in tenths of seconds), an Event Notification OAMPDU
           should be generated with an Errored Frame Event TLV indicating
           the threshold has been crossed in this window.";
        reference "[802.3ah], 30.3.6.1.38";
      }
      leaf error-frame-threshold {
        type uint32;
        units "frames";
        // NCS drop default statement
        description
          "The number of frame errors that must occur for this event to
           be triggered. The default value is one frame error. If error-frame-threshold
           frame errors occur within a window of error-frame-window (in tenths
           of seconds), an Event Notification OAMPDU should be generated
           with an Errored Frame Event TLV indicating the threshold has been
           crossed in this window.";
        reference "[802.3ah], 30.3.6.1.36";
      }
      leaf error-frame-event-notification {
        type boolean;
        // NCS drop default statement
        description
          "Indicates whether the occurrence of an Errored Frame Event should
           result in an Event Notification OAMPDU generated by the OAM layer.
           By default, this attribute should be 'on' for Ethernet like interfaces
           that support OAM. If the OAM layer does not support event notifications
           (as indicated via the functions-supported attribute), this value
           is ignored.";
      }
      leaf error-frame-seconds-summary-window {
        type uint16 {
          range "100..9000";
        }
        // NCS drop default statement
        units "tenths-of-a-second";
        description
          "The amount of time (in 100ms intervals) over which the threshold
           is defined. The default value is 100 (10 seconds). If error-frame-seconds-summary-threshold
           frame errors occur within a window of error-frame-seconds-summary-window
           (in tenths of seconds), an Event Notification OAMPDU should be
           generated with an Errored Frame Seconds Summary Event TLV indicating
           the threshold has been crossed in this window.";
        reference "[802.3ah], 30.3.6.1.40";
      }
      leaf error-frame-seconds-summary-threshold {
        type uint32 {
          range "1..900";
        }
        units "errored-frame-seconds";
        // NCS drop default statement
        description
          "The number of errored frame seconds that must occur for this
           event to be triggered. The default value is one errored frame
           second. If error-frame-seconds-summary-threshold frame errors
           occur within a window of error-frame-seconds-summary-window (in
           tenths of seconds), an Event Notification OAMPDU should be generated
           with an Errored Frame Seconds Summary Event TLV indicating the
           threshold has been crossed in this window.";
        reference "[802.3ah], 30.3.6.1.40";
      }
      leaf error-frame-seconds-event-notification {
        type boolean;
        // NCS drop default statement
        description
          "Indicates whether the occurrence of an Errored Frame Seconds
           Summary Event should result in an Event Notification OAMPDU generated
           by the OAM layer. By default, this object should have the value
           'on' for Ethernet like interfaces that support OAM. If the OAM
           layer does not support event notifications (as indicated via the
           functions-supported attribute), this value is ignored.";
      }
      leaf dying-gasp {
        type boolean;
        // NCS drop default statement
        description
          "Indicates whether the local device should attempt to indicate
           a dying gasp fault via the OAMPDU flags field to its peer OAM
           entity. If the system does not support dying gasp capability,
           setting this object has no effect, and reading the object should
           always result in 'disable'. By default, this object should have
           the value enable for Ethernet like interfaces that support OAM.
           If the OAM layer does not support event notifications (as indicated
           via the functions-supported attribute), this value is ignored.";
      }
      leaf critical-event {
        type boolean;
        // NCS drop default statement
        description
          "Indicates whether the local device should attempt to indicate
           a critical event has occurred via the OAMPDU flags field to its
           peer OAM entity. By default, this object should have the value
           'enable' for Ethernet like interfaces that support OAM. If the
           OAM layer does not support event notifications (as indicated via
           the functions-supported attribute), this value is ignored.";
      }
      description
        "EOAM port event generation configuration.";
    }
    description
      "EOAM port configuration.";
  }
  augment "/ncs:devices/ncs:device/ncs:config/oc-if:interfaces/oc-if:interface/oc-if:config" {
    when "cn-oc-if:type = 'ettp'" {
      tailf:xpath-root 3;
    }
    container eoam-port-config {
      tailf:ncs-device-type "netconf";
      tailf:display-when "not(../../../../../ncs:module) or ../../../../../ncs:module[ncs:name='ciena-ieee-port-eoam']";
      leaf admin-status {
        type enumeration {
          enum "enable" {
            description
              "Enable OAM administratively on this port or interface";
          }
          enum "disable" {
            description
              "Disable OAM administratively on this port or interface.
               The OAM admin-status always starts in the disabled state until
               an explicit management action or configuration information is
               retained by the system and causes a transition to the enabled
               state";
          }
        }
        default "disable";
        description
          "EOAM port admin state.";
      }
      leaf mode {
        type enumeration {
          enum "active" {
            description
              "Active mode provides additional capabilities to initiate
               monitoring activities with the remote OAM peer entity.
               As an example, an active OAM entity can put the
               remote OAM entity in a loopback state, where a passive OAM entity
               cannot. The default value of mode is dependent on the type of
               system on which this Ethernet like interface resides. The default
               value should be 'active' unless it is known that this system should
               take on a subservient role to the other device connected over
               this interface. Changing this value results in incrementing the
               configuration revision field of locally generated OAMPDUs (30.3.6.1.12)
               and potentially causes re-doing of the OAM discovery process if
               the oper-status was already operational.";
          }
          enum "passive" {
            description
              "Passive mode generally waits for the peer to initiate OAM
               actions with it.";
          }
        }
        default "active";
        description
          "The mode of OAM opertion for this Ethernet like interface. OAM
            on Ethernet interfaces maybe in active mode or passive mode.";
      }
      uses port-config-objects;
      description
        "EOAM port state configuration.";
    }
    container eoam-loopback-port-config {
      tailf:ncs-device-type "netconf";
      tailf:display-when "not(../../../../../ncs:module) or ../../../../../ncs:module[ncs:name='ciena-ieee-port-eoam']";
      leaf loopback-ignore-rx {
        type enumeration {
          enum "ignore" {
            description
              "When the value is ignore, received loopback commands are ignored.
               The default value is to ignore loopback commands (ignore).";
          }
          enum "process" {
            description
              "When the value is process, OAM loopback commands are processed.";
          }
        }
        default "ignore";
        description
          "Since OAM loopback is a disruptive operation (user traffic does
           not pass), this attribute provides a mechanism to provide controls
           over whether received OAM loopback commands are processed or ignored.
           The attribute has no meaning if the local OAM entity does not support
           the loopback function (as defined in functions-supported).";
      }
      description
        "EOAM port loopback confguration.";
    }
    container eoam-port-event-config {
      tailf:ncs-device-type "netconf";
      tailf:display-when "not(../../../../../ncs:module) or ../../../../../ncs:module[ncs:name='ciena-ieee-port-eoam']";
      leaf error-frame-period-window {
        type uint32;
        units "frames";
        description
          "The number of frames over which the threshold is defined. The
           default value of the window is the number of minimum size Ethernet
           frames that can be received over the physical layer in one second.
           If error-frame-period-threshold frame errors occur within a window
           of error-frame-period-window frames, an Event Notification OAMPDU
           should be generated with an Errored Frame Period Event TLV indicating
           the threshold has been crossed in this window.
           +------------ Range of errd-frame-period-window values------------+
           |     10 mbps link :     1488 -     892800 |
           |    100 mbps link :    14880 -    8928000 |
           |   1000 mbps link :   148810 -   89285760 |
           |  10000 mbps link :  1488096 -  892857120 |
           | 100000 mbps link : 14880953 - 4294967295 |
           +-----------------------------------------------------------------+";
        reference "[802.3ah], 30.3.6.1.38";
      }
      leaf error-frame-period-threshold {
        type uint32;
        units "frames";
        default "1";
        description
          "The number of frame errors that must occur for this event to
           be triggered. The default value is one frame error. If error-frame-period-threshold
           frame errors occur within a window of error-frame-period-window
           frames, an Event Notification OAMPDU should be generated with
           an Errored Frame Period Event TLV indicating the threshold has
           been crossed in this window.";
        reference "[802.3ah], 30.3.6.1.38";
      }
      leaf error-frame-period-event-notification {
        type boolean;
        default "false";
        description
          "Indicates whether the occurrence of an Errored Frame Period Event
           should result in an Event Notification OAMPDU generated by the
           OAM layer. By default, this attribute is 'on' for Ethernet like
           interfaces that support OAM. If the OAM layer does not support
           event notifications (as indicated via the functions-supported
           attribute), this value is ignored.";
      }
      leaf error-frame-window {
        type uint32 {
          range "10..600";
        }
        units "tenths-of-a-second";
        default "10";
        description
          "The amount of time (in 100ms increments) over which the threshold
           is defined. The default value is 10 (1 second). If error-frame-threshold
           frame errors occur within a window of error-frame-window seconds
           (measured in tenths of seconds), an Event Notification OAMPDU
           should be generated with an Errored Frame Event TLV indicating
           the threshold has been crossed in this window.";
        reference "[802.3ah], 30.3.6.1.38";
      }
      leaf error-frame-threshold {
        type uint32;
        units "frames";
        default "1";
        description
          "The number of frame errors that must occur for this event to
           be triggered. The default value is one frame error. If error-frame-threshold
           frame errors occur within a window of error-frame-window (in tenths
           of seconds), an Event Notification OAMPDU should be generated
           with an Errored Frame Event TLV indicating the threshold has been
           crossed in this window.";
        reference "[802.3ah], 30.3.6.1.36";
      }
      leaf error-frame-event-notification {
        type boolean;
        default "false";
        description
          "Indicates whether the occurrence of an Errored Frame Event should
           result in an Event Notification OAMPDU generated by the OAM layer.
           By default, this attribute should be 'on' for Ethernet like interfaces
           that support OAM. If the OAM layer does not support event notifications
           (as indicated via the functions-supported attribute), this value
           is ignored.";
      }
      leaf error-frame-seconds-summary-window {
        type uint16 {
          range "100..9000";
        }
        default "600";
        units "tenths-of-a-second";
        description
          "The amount of time (in 100ms intervals) over which the threshold
           is defined. The default value is 100 (10 seconds). If error-frame-seconds-summary-threshold
           frame errors occur within a window of error-frame-seconds-summary-window
           (in tenths of seconds), an Event Notification OAMPDU should be
           generated with an Errored Frame Seconds Summary Event TLV indicating
           the threshold has been crossed in this window.";
        reference "[802.3ah], 30.3.6.1.40";
      }
      leaf error-frame-seconds-summary-threshold {
        type uint32 {
          range "1..900";
        }
        units "errored-frame-seconds";
        default "1";
        description
          "The number of errored frame seconds that must occur for this
           event to be triggered. The default value is one errored frame
           second. If error-frame-seconds-summary-threshold frame errors
           occur within a window of error-frame-seconds-summary-window (in
           tenths of seconds), an Event Notification OAMPDU should be generated
           with an Errored Frame Seconds Summary Event TLV indicating the
           threshold has been crossed in this window.";
        reference "[802.3ah], 30.3.6.1.40";
      }
      leaf error-frame-seconds-event-notification {
        type boolean;
        default "false";
        description
          "Indicates whether the occurrence of an Errored Frame Seconds
           Summary Event should result in an Event Notification OAMPDU generated
           by the OAM layer. By default, this object should have the value
           'on' for Ethernet like interfaces that support OAM. If the OAM
           layer does not support event notifications (as indicated via the
           functions-supported attribute), this value is ignored.";
      }
      leaf dying-gasp {
        type boolean;
        default "false";
        description
          "Indicates whether the local device should attempt to indicate
           a dying gasp fault via the OAMPDU flags field to its peer OAM
           entity. If the system does not support dying gasp capability,
           setting this object has no effect, and reading the object should
           always result in 'disable'. By default, this object should have
           the value enable for Ethernet like interfaces that support OAM.
           If the OAM layer does not support event notifications (as indicated
           via the functions-supported attribute), this value is ignored.";
      }
      leaf critical-event {
        type boolean;
        default "false";
        description
          "Indicates whether the local device should attempt to indicate
           a critical event has occurred via the OAMPDU flags field to its
           peer OAM entity. By default, this object should have the value
           'enable' for Ethernet like interfaces that support OAM. If the
           OAM layer does not support event notifications (as indicated via
           the functions-supported attribute), this value is ignored.";
      }
      description
        "EOAM port event generation configuration.";
    }
    description
      "EOAM port configuration.";
  }
  augment "/ncs:devices/ncs:device/ncs:live-status/oc-if:interfaces/oc-if:interface/oc-if:state" {
    // NCS drop when statement
    container eoam-port-status {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf error-frame-period-window {
        type uint32;
        units "frames";
        description
          "The number of frames over which the threshold is defined. The
           default value of the window is the number of minimum size Ethernet
           frames that can be received over the physical layer in one second.
           If error-frame-period-threshold frame errors occur within a window
           of error-frame-period-window frames, an Event Notification OAMPDU
           should be generated with an Errored Frame Period Event TLV indicating
           the threshold has been crossed in this window.
           +------------ Range of errd-frame-period-window values------------+
           |     10 mbps link :     1488 -     892800 |
           |    100 mbps link :    14880 -    8928000 |
           |   1000 mbps link :   148810 -   89285760 |
           |  10000 mbps link :  1488096 -  892857120 |
           | 100000 mbps link : 14880953 - 4294967295 |
           +-----------------------------------------------------------------+";
        reference "[802.3ah], 30.3.6.1.38";
      }
      leaf port-oper-status {
        type live_ncs_oper-status;
        description
          "The OAM operational status for the Ethernet like interface";
      }
      leaf max-pdu-size {
        type uint32 {
          range "64..1518";
        }
        description
          "The largest OAMPDU that the OAM entity supports. OAM entities
           exchange maximum OAMPDU sizes and negotiate to use the smaller
           of the two maximum OAMPDU sizes between the peers. This value
           is determined by the local implementation.";
      }
      leaf configuration-revision {
        type uint32 {
          range "0..65535";
        }
        description
          "The configuration revision of the OAM entity as reflected in
           the latest OAMPDU sent by the OAM entity. The configuration revision
           is used by OAM entities to indicate configuration changes have
           occurred which might require the peer OAM entity to re-evaluate
           whether the peering is allowed. See local_satisfied in [802.3ah,
           57.3.1.2].";
      }
      uses live_ncs_port-config-objects;
      leaf local-functions-supported {
        type live_ncs_functions-supported;
        description
          "The OAM functions supported on this Ethernet like interface.
           OAM consists of separate functional sets beyond the basic discovery
           process which is always required. These functional groups can
           be supported independently by any implementation. These values
           are communicated to the peer via the local configuration field
           of Information OAMPDUs.";
      }
      description
        "EOAM port operational status.";
    }
    container eoam-peer-information {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf peer-status {
        type live_ncs_peer-status;
        description
          " Operational status of the peer OAM interface.";
      }
      leaf peer-mac-address {
        type yang:mac-address;
        description
          "The MAC address of the peer OAM entity. The MAC address is derived
           from the most recently received OAMPDU. This value is initialized
           to all zeros (0x000000000000). This value is invalid if the wwpLeosOamPeerStatus
           is inactive. An OAMPDU is indicated by a valid frame with (1)
           destination MAC address equal to that of the reserved MAC address
           for Slow Protocols (See 43B of [802.3ah]), (2) a lengthOrType
           field equal to the reserved type for Slow Protocols, (3) and a
           Slow Protocols subtype equal to that of the subtype reserved for
           OAM.";
      }
      leaf peer-vendor-oui {
        type live_ncs_oui;
        description
          "The OUI of the OAM peer as reflected in the latest Information
           OAMPDU received with a Local Information TLV. The OUI can be used
           to identify the vendor of the remote OAM entity. This value is
           initialized to all zeros (0x000000). This value is considered
           invalid if the peer-status is inactive. An Information OAMPDU
           is indicated by a valid frame with (1) destination MAC address
           equal to that of the reserved MAC address for Slow Protocols (See
           43B of [802.3ah]), (2) a lengthOrType field equal to the reserved
           type for Slow Protocols, (3) a Slow Protocols subtype equal to
           that of the subtype reserved for OAM, and (4) an OAM code that
           equals the code reserved for Information OAMPDUs.";
      }
      leaf vendor-info {
        type uint32;
        description
          "The Vendor Info of the OAM peer as reflected in the latest Information
           OAMPDU received with a Local Information TLV. The vendor information
           field is within the Local Information TLV, and can be used to
           determine additional information about the peer entity. The format
           of the vendor information is unspecified within the 32-bit field.
           This value is initialized to all zeros (0x00000000). This value
           is invalid if the peer-status is inactive. An Information OAMPDU
           is indicated by a valid frame with (1) destination MAC address
           equal to that of the reserved MAC address for Slow Protocols (See
           43B of [802.3ah]), (2) a lengthOrType field equal to the reserved
           type for Slow Protocols, (3) a Slow Protocols subtype equal to
           that of the subtype reserved for OAM, and (4) an OAM code that
           equals the code reserved for Information OAMPDUs. ";
      }
      leaf peer-mode {
        type enumeration {
          enum "active" {
            description
              "OAM peer is in active mode.";
          }
          enum "passive" {
            description
              "OAM peer is in passive mode.";
          }
          enum "unknown" {
            description
              "peer-mode is initialized to 'unknown' and is
               not valid if peer-status is inactive.";
          }
        }
        description
          "The mode of the OAM peer as reflected in the latest Information
           OAMPDU received with a Local Information TLV. The mode of the
           peer can be determined from the Configuration field in the Local
           Information TLV of the last Information OAMPDU received from the
           peer. This value is initialized to unknown(3), and is not valid
           if the peer-status is inactive. An Information OAMPDU
           is indicated by a valid frame with (1) destination MAC address
           equal to that of the reserved MAC address for Slow Protocols (See
           43B of [802.3ah]), (2) a lengthOrType field equal to the reserved
           type for Slow Protocols, (3) a Slow Protocols subtype equal to
           that of the subtype reserved for OAM, and (4) an OAM code that
           equals the code reserved for Information OAMPDUs.";
      }
      leaf peer-max-pdu-size {
        type uint32;
        units "bytes";
        description
          "The maximum size of OAMPDU supported by the peer as reflected
           in the latest Information OAMPDU received with a Local Information
           TLV. Ethernet OAM on this interface must not use OAMPDUs that
           exceed this size. The maximum OAMPDU size can be determined from
           the PDU Configuration field of the Local Information TLV of the
           last Information OAMPDU received from the peer. This value is
           initialized to 64, and is invalid if the peer-status is inactive.
           An Information OAMPDU is indicated by a valid frame with (1) destination
           MAC address equal to that of the reserved MAC address for Slow
           Protocols (See 43B of [802.3ah]), (2) a lengthOrType field equal
           to the reserved type for Slow Protocols, (3) a Slow Protocols
           subtype equal to that of the subtype reserved for OAM, and (4)
           an OAM code that equals the code reserved for Information OAMPDUs.";
      }
      leaf peer-configuration-revision {
        type uint32;
        description
          "The configuration revision of the OAM peer as reflected in the
           latest OAMPDU. This attribute is changed by the peer whenever
           it has a local configuration change for Ethernet OAM this interface.
           This value is initialized to all zeros (0x00000000), and is invalid
           if the peer-status is inactive. The configuration revision can
           be determined from the Revision field of the Local Information
           TLV of the most recently received Information OAMPDU with a Local
           Information TLV. An Information OAMPDU is indicated by a valid
           frame with (1) destination MAC address equal to that of the reserved
           MAC address for Slow Protocols (See 43B of [802.3ah]), (2) a lengthOrType
           field equal to the reserved type for Slow Protocols, (3) a Slow
           Protocols subtype equal to that of the subtype reserved for OAM,
           and (4) an OAM code that equals the code reserved for Information
           OAMPDUs.";
      }
      leaf peer-functions-supported {
        type live_ncs_functions-supported;
        description
          "The OAM functions supported on the peer. OAM consists of separate
           functionality sets above the basic discovery process. This value
           indicates the capabilities of the peer OAM entity with respect
           to these functions. This value is initialized so all bits are
           clear, and is invalid if the wwpLeosOamPeerStatus is inactive.
           The capbilities of the OAM peer can be determined from the configuration
           field of the Local Information TLV of the most recently received
           Information OAMPDU with a Local Information TLV. An Information
           OAMPDU is indicated by a valid frame with (1) destination MAC
           address equal to that of the reserved MAC address for Slow Protocols
           (See 43B of [802.3ah]), (2) a lengthOrType field equal to the
           reserved type for Slow Protocols, (3) a Slow Protocols subtype
           equal to that of the subtype reserved for OAM, and (4) an OAM
           code that equals the code reserved for Information OAMPDUs. ";
      }
      description
        "Operational status of the EOAM peer.";
    }
    container eoam-loopback-port-status {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf loopback-status {
        type enumeration {
          enum "no-loopback";
          enum "initiating-loopback";
          enum "remote-loopback";
          enum "terminating-loopback";
          enum "local-loopback";
          enum "unknown";
        }
        description
          "The loopback status of the OAM entity.  This status is
           determined by a combination of the local parser and
           multiplexer states, the remote parser and multiplexer states,
           as well as by the actions of the local OAM client.  When
           operating in normal mode with no loopback in progress, the
           status reads no-loopback.

           If the OAM client has sent a Loopback OAMPDU and is waiting
           for a response, where the local parser and multiplexer states
           are DISCARD (see [802.3ah, 57.2.11.1]), the status is
           'initiating-loopback'.  In this case, the local OAM entity has
           yet to receive any acknowledgement that the remote OAM entity
           has received its loopback command request.

           If the local OAM client knows that the remote OAM entity is in
           loopback mode (via the remote state information as described
           in [802.3ah, 57.2.11.1, 30.3.6.1.15]), the status is remote-loopback.
           If the local OAM client is in the process of terminating the remote
           loopback [802.3ah, 57.2.11.3, 30.3.6.1.14], with its local
           multiplexer and parser states in DISCARD, the status is
           terminating-loopback.  If the remote OAM client has put the local
           OAM entity in loopback mode as indicated by its local parser state,
           the status is local-loopback.

           The unknown status indicates the parser and multiplexer
           combination is unexpected.  This status may be returned if the
           OAM loopback is in a transition state but should not persist.

           The values of this attribute correspond to the following
           values of the local and remote parser and multiplexer states.

                                              LclPrsr   LclMux    RmtPrsr   RmtMux
            no-loopback                FWD       FWD       FWD       FWD
            initiating-loopback       DISCARD   DISCARD     FWD       FWD
            remote-loopback         DISCARD     FWD      LPBK    DISCARD
            terminating-loopback   DISCARD   DISCARD    LPBK    DISCARD
            local-loopback             LPBK    DISCARD   DISCARD     FWD
            unknown                     ***   any other combination   ***";
      }
      description
        "EOAM loopback port status.";
    }
    container eoam-port-statistics {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      leaf information-transmitted {
        type yang:counter32;
        units "frames";
        description
          "A count of the number of Information OAMPDUs transmitted on this
           interface. An Information OAMPDU is indicated by a valid frame
           with (1) destination MAC address equal to that of the reserved
           MAC address for Slow Protocols (See 43B of [802.3ah]), (2) a lengthOrType
           field equal to the reserved type for Slow Protocols, (3) a Slow
           Protocols subtype equal to that of the subtype reserved for OAM,
           and (4) an OAMPDU code that equals the OAM Information code. Discontinuities
           of this counter can occur at re-initialization of the management
           system, and at other times as indicated by the value of the
           ifCounterDiscontinuityTime.";
      }
      leaf information-received {
        type yang:counter32;
        units "frames";
        description
          "A count of the number of Information OAMPDUs received on this
           interface. An Information OAMPDU is indicated by a valid frame
           with (1) destination MAC address equal to that of the reserved
           MAC address for Slow Protocols (See 43B of [802.3ah]), (2) a lengthOrType
           field equal to the reserved type for Slow Protocols, (3) a Slow
           Protocols subtype equal to that of the subtype reserved for OAM,
           and (4) an OAMPDU code that equals the OAM Information code. Discontinuities
           of this counter can occur at re-initialization of the management
           system, and at other times as indicated by the value of the
           ifCounterDiscontinuityTime.";
      }
      leaf unique-event-notification-transmitted {
        type yang:counter32;
        units "frames";
        description
          "A count of the number of unique Event OAMPDUs transmitted on
           this interface. Event notifications may be sent in duplicate to
           increase the probability of successfully being received, given
           the possibility that a frame may be lost in transit. An Event
           Notification OAMPDU is indicated by a valid frame with (1) destination
           MAC address equal to that of the reserved MAC address for Slow
           Protocols (See 43B of [802.3ah]), (2) a lengthOrType field equal
           to the reserved type for Slow Protocols, (3) a Slow Protocols
           subtype equal to that of the subtype reserved for OAM, and (4)
           an OAMPDU code that equals the OAM Event code. A unique Event
           Notification OAMPDU is indicated as an Event Notification OAMPDU
           with a Sequence Number field that is distinct from the previously
           transmitted Event Notification OAMPDU Sequence Number. Discontinuities
           of this counter can occur at re-initialization of the management
           system, and at other times as indicated by the value of the
           ifCounterDiscontinuityTime";
      }
      leaf unique-event-notification-received {
        type yang:counter32;
        units "frames";
        description
          "A count of the number of unique Event OAMPDUs received on this
           interface. Event notification OAMPDUs may be sent in duplicate
           to increase the probability of successfully being received, given
           the possibility that a frame may be lost in transit. An Event
           Notification OAMPDU is indicated by a valid frame with (1) destination
           MAC address equal to that of the reserved MAC address for Slow
           Protocols (See 43B of [802.3ah]), (2) a lengthOrType field equal
           to the reserved type for Slow Protocols, (3) a Slow Protocols
           subtype equal to that of the subtype reserved for OAM, and (4)
           an OAMPDU code that equals the OAM Event code. A unique Event
           Notification OAMPDU is indicated as an Event Notification OAMPDU
           with a Sequence Number field that is distinct from the previously
           received Event Notification OAMPDU Sequence Number. Discontinuities
           of this counter can occur at re-initialization of the management
           system, and at other times as indicated by the value of the
           ifCounterDiscontinuityTime.";
      }
      uses live_ncs_loopback-statistics;
      leaf variable-request-transmitted {
        type yang:counter32;
        units "frames";
        description
          "A count of the number of Variable Request OAMPDUs transmitted
           on this interface. A Variable Request OAMPDU is indicated by a
           valid frame with (1) destination MAC address equal to that of
           the reserved MAC address for Slow Protocols (See 43B of [802.3ah]),
           (2) a lengthOrType field equal to the reserved type for Slow Protocols,
           (3) a Slow Protocols subtype equal to that of the subtype reserved
           for OAM, and (4) an OAMPDU code that equals the OAM Variable Request
           code. Discontinuities of this counter can occur at re-initialization
           of the management system, and at other times as indicated by the
           value of the ifCounterDiscontinuityTime.";
        reference "[802.3ah], 30.3.6.1.28.";
      }
      leaf variable-request-received {
        type yang:counter32;
        units "frames";
        description
          "A count of the number of Variable Request OAMPDUs received on
           this interface. A Variable Request OAMPDU is indicated by a valid
           frame with (1) destination MAC address equal to that of the reserved
           MAC address for Slow Protocols (See 43B of [802.3ah]), (2) a lengthOrType
           field equal to the reserved type for Slow Protocols, (3) a Slow
           Protocols subtype equal to that of the subtype reserved for OAM,
           and (4) an OAMPDU code that equals the OAM Variable Request code.
           Discontinuities of this counter can occur at re-initialization
           of the management system, and at other times as indicated by the
           value of the ifCounterDiscontinuityTime.";
      }
      leaf variable-response-transmitted {
        type yang:counter32;
        units "frames";
        description
          "A count of the number of Variable Response OAMPDUs transmitted
           on this interface. A Variable Response OAMPDU is indicated by
           a valid frame with (1) destination MAC address equal to that of
           the reserved MAC address for Slow Protocols (See 43B of [802.3ah]),
           (2) a lengthOrType field equal to the reserved type for Slow Protocols,
           (3) a Slow Protocols subtype equal to that of the subtype reserved
           for OAM, and (4) an OAMPDU code that equals the OAM Variable Response
           code. Discontinuities of this counter can occur at re-initialization
           of the management system, and at other times as indicated by the
           value of the ifCounterDiscontinuityTime.";
      }
      leaf variable-response-received {
        type yang:counter32;
        units "frames";
        description
          "A count of the number of Variable Response OAMPDUs received on
           this interface. A Variable Response OAMPDU is indicated by a valid
           frame with (1) destination MAC address equal to that of the reserved
           MAC address for Slow Protocols (See 43B of [802.3ah]), (2) a lengthOrType
           field equal to the reserved type for Slow Protocols, (3) a Slow
           Protocols subtype equal to that of the subtype reserved for OAM,
           and (4) an OAMPDU code that equals the OAM Variable Response code.
           Discontinuities of this counter can occur at re-initialization
           of the management system, and at other times as indicated by the
           value of the ifCounterDiscontinuityTime.";
      }
      leaf organization-specific-transmitted {
        type yang:counter32;
        units "frames";
        description
          "A count of the number of Organization Specific OAMPDUs transmitted
           on this interface. An Organization Specific OAMPDU is indicated
           by a valid frame with (1) destination MAC address equal to that
           of the reserved MAC address for Slow Protocols (See 43B of [802.3ah]),
           (2) a lengthOrType field equal to the reserved type for Slow Protocols,
           (3) a Slow Protocols subtype equal to that of the subtype reserved
           for OAM, and (4) an OAMPDU code that equals the OAM Organization
           Specific code. Discontinuities of this counter can occur at re-initialization
           of the management system, and at other times as indicated by the
           value of the ifCounterDiscontinuityTime.";
      }
      leaf organization-specific-received {
        type yang:counter32;
        units "frames";
        description
          "A count of the number of Organization Specific OAMPDUs received
           on this interface. An Organization Specific OAMPDU is indicated
           by a valid frame with (1) destination MAC address equal to that
           of the reserved MAC address for Slow Protocols (See 43B of [802.3ah]),
           (2) a lengthOrType field equal to the reserved type for Slow Protocols,
           (3) a Slow Protocols subtype equal to that of the subtype reserved
           for OAM, and (4) an OAMPDU code that equals the OAM Organization
           Specific code. Discontinuities of this counter can occur at re-initialization
           of the management system, and at other times as indicated by the
           value of the ifCounterDiscontinuityTime.";
      }
      leaf unsupported-codes-transmitted {
        type yang:counter32;
        units "frames";
        description
          "A count of the number of Organization Specific OAMPDUs received
           on this interface. An Organization Specific OAMPDU is indicated
           by a valid frame with (1) destination MAC address equal to that
           of the reserved MAC address for Slow Protocols (See 43B of [802.3ah]),
           (2) a lengthOrType field equal to the reserved type for Slow Protocols,
           (3) a Slow Protocols subtype equal to that of the subtype reserved
           for OAM, and (4) an OAMPDU code that equals the OAM Organization
           Specific code. Discontinuities of this counter can occur at re-initialization
           of the management system, and at other times as indicated by the
           value of the ifCounterDiscontinuityTime.";
      }
      leaf unsupported-codes-received {
        type yang:counter32;
        units "frames";
        description
          "A count of the number of OAMPDUs received on this interface with
           an unsupported op-code. An unsupported op-code OAMPDU is indicated
           by a valid frame with (1) destination MAC address equal to that
           of the reserved MAC address for Slow Protocols (See 43B of [802.3ah]),
           (2) a lengthOrType field equal to the reserved type for Slow Protocols,
           (3) a Slow Protocols subtype equal to that of the subtype reserved
           for OAM, and (4) an OAMPDU code that equals the opcode for a function
           that is not supported by the device. Discontinuities of this counter
           can occur at re-initialization of the management system, and at
           other times as indicated by the value of the ifCounterDiscontinuityTime.";
      }
      leaf frames-lost-due-to-oam {
        type yang:counter32;
        units "frames";
        description
          "A count of the number of OAMPDUs received on this interface with
           an unsupported op-code. An unsupported op-code OAMPDU is indicated
           by a valid frame with (1) destination MAC address equal to that
           of the reserved MAC address for Slow Protocols (See 43B of [802.3ah]),
           (2) a lengthOrType field equal to the reserved type for Slow Protocols,
           (3) a Slow Protocols subtype equal to that of the subtype reserved
           for OAM, and (4) an OAMPDU code that equals the opcode for a function
           that is not supported by the device. Discontinuities of this counter
           can occur at re-initialization of the management system, and at
           other times as indicated by the value of the ifCounterDiscontinuityTime.";
      }
      leaf duplicate-event-notifications-transmitted {
        type yang:counter32;
        units "frames";
        description
          "A count of the number of duplicate Event OAMPDUs transmitted
           on this interface. Event notification OAMPDUs may be sent in duplicate
           to increase the probability of successfully being received, given
           the possibility that a frame may be lost in transit. An Event
           Notification OAMPDU is indicated by a valid frame with (1) destination
           MAC address equal to that of the reserved MAC address for Slow
           Protocols (See 43B of [802.3ah]), (2) a lengthOrType field equal
           to the reserved type for Slow Protocols, (3) a Slow Protocols
           subtype equal to that of the subtype reserved for OAM, and (4)
           an OAMPDU code that equals the OAM Event code. A duplicate Event
           Notification OAMPDU is indicated as an Event Notification OAMPDU
           with a Sequence Number field that is identical to the previously
           transmitted Event Notification OAMPDU Sequence Number. Discontinuities
           of this counter can occur at re-initialization of the management
           system, and at other times as indicated by the value of the
           ifCounterDiscontinuityTime.";
      }
      leaf duplicate-event-notifications-received {
        type yang:counter32;
        units "frames";
        description
          "A count of the number of duplicate Event OAMPDUs received on
           this interface. Event notification OAMPDUs may be sent in duplicate
           to increase the probability of successfully being received, given
           the possibility that a frame may be lost in transit. An Event
           Notification OAMPDU is indicated by a valid frame with (1) destination
           MAC address equal to that of the reserved MAC address for Slow
           Protocols (See 43B of [802.3ah]), (2) a lengthOrType field equal
           to the reserved type for Slow Protocols, (3) a Slow Protocols
           subtype equal to that of the subtype reserved for OAM, and (4)
           an OAMPDU code that equals the OAM Event code. A duplicate Event
           Notification OAMPDU is indicated as an Event Notification OAMPDU
           with a Sequence Number field that is identical to the previously
           received Event Notification OAMPDU Sequence Number. Discontinuities
           of this counter can occur at re-initialization of the management
           system, and at other times as indicated by the value of the
           ifCounterDiscontinuityTime.";
      }
      description
        "EOAM port statistics.";
    }
    container eoam-port-event-log {
      tailf:ncs-device-type "netconf";
      tailf:display-when "not(../../../../../ncs:module) or ../../../../../ncs:module[ncs:name='ciena-ieee-port-eoam'] or (../../../../../ncs:live-status-protocol[not(ncs:capability)]) or (../../../../../ncs:live-status-protocol/ncs:capability/ncs:module[.='ciena-ieee-port-eoam'])";
      list event-entry {
        key "index";
        leaf index {
          type uint32 {
            range "1..4294967295";
          }
          description
            "An arbitrary integer for identifying individual events within
             the event log.";
        }
        leaf timestamp {
          type yang:timestamp;
          description
            "The value of sysUpTime at the time of the logged event. For locally
             generated events, the time of the event can be accurately retrieved
             from sysUpTime. For remotely generated events, the time of the
             event is indicated by the reception of the Event Notification
             OAMPDU indicating the event occurred on the peer. A system may
             attempt to adjust the timestamp value to more accurately reflect
             the time of the event at the peer OAM entity by using other information,
             such as that found in the timestamp found of the Event Notification
             TLVs, which provides an indication of the relative time between
             events at the peer entity.";
        }
        leaf oui {
          type live_ncs_oui;
          description
            "The OUI of the entity defining the object type. All IEEE 802.3
             defined events (as appearing in [802.3ah] except for the Organizationally
             Unique Event TLVs) use the IEEE 802.3 OUI of 0x0180C2. Organizations
             defining their own Event Notification TLVs include their OUI in
             the Event Notification TLV which gets reflected here.";
        }
        leaf event-type {
          type live_ncs_event;
        }
        leaf location {
          type live_ncs_event-location;
        }
        leaf window-hi {
          type uint32;
          description
            "If the event represents a threshold crossing event, the two objects
             window-hi and window-lo form an unsigned 64-bit integer yielding
             the window over which the value was measured for the threshold
             crossing event (e.g. 5, when 11 occurrences happened in 5 seconds
             while the threshold was 10). The two objects are combined as:
             window = ((2^32) * window-hi) + window-lo Otherwise, this value
             is returned as all Fs (0xFFFFFFFF) and adds no useful information.";
          reference "[802.3ah], 30.3.6.1.37 and 57.5.3.2.";
        }
        leaf window-lo {
          type uint32;
          description
            "If the event represents a threshold crossing event, the two objects
             window-hi and window-lo form an unsigned 64-bit integer yielding
             the window over which the value was measured for the threshold
             crossing event (e.g. 5, when 11 occurrences happened in 5 seconds
             while the threshold was 10). The two objects are combined as:
             window = ((2^32) * window-hi) + window-lo Otherwise, this value
             is returned as all Fs (0xFFFFFFFF) and adds no useful information.";
          reference "[802.3ah], 30.3.6.1.37 and 57.5.3.2.";
        }
        leaf threshold-hi {
          type uint32;
          description
            "If the event represents a threshold crossing event, the two objects
             threshold-hi and threshold-lo form an unsigned 64-bit integer
             yielding the value that was crossed for the threshold crossing
             event (e.g. 10, when 11 occurrences happened in 5 seconds while
             the threshold was 10). The two objects are combined as: threshold
             = ((2^32) * threshold-hi) + threshold-lo Otherwise, this value
             is returned as all Fs (0xFFFFFFFF) and adds no useful information.";
          reference "[802.3ah], 30.3.6.1.37 and 57.5.3.2.";
        }
        leaf threshold-lo {
          type uint32;
          description
            "If the event represents a threshold crossing event, the two objects
             threshold-hi and threshold-lo form an unsigned 64-bit integer
             yielding the value that was crossed for the threshold crossing
             event (e.g. 10, when 11 occurrences happened in 5 seconds while
             the threshold was 10). The two objects are combined as: threshold
             = ((2^32) * threshold-hi) + threshold-lo Otherwise, this value
             is returned as all Fs (0xFFFFFFFF) and adds no useful information.";
          reference "[802.3ah], 30.3.6.1.37 and 57.5.3.2.";
        }
        leaf value {
          type yang:counter64;
          description
            "If the event represents a threshold crossing event, this value
             indicates the value of the parameter within the given window that
             generated this event (e.g. 11, when 11 occurrences happened in
             5 seconds while the threshold was 10). Otherwise, this value is
             returned as all Fs (0xFFFFFFFFFFFFFFFF) and adds no useful information.";
          reference "[802.3ah], 30.3.6.1.37 and 57.5.3.2.";
        }
        leaf running-total {
          type yang:counter64;
          description
            "This value represents the total number of times this occurrence
             has happened since the last reset (e.g. 3253, when 3253 symbol
             errors have occurred since the last reset, which has resulted
             in 51 symbol error threshold crossing events since the last reset).";
          reference "[802.3ah], 30.3.6.1.37 and 57.5.3.2.";
        }
        leaf total {
          type uint32;
          description
            "This value represents the total number of times one or more of
             these occurrences have resulted in an event (e.g. 51 when 3253
             symbol errors have occurred since the last reset, which has resulted
             in 51 symbol error threshold crossing events since the last reset).";
          reference "[802.3ah], 30.3.6.1.37 and 57.5.3.2.";
        }
      }
      description
        "This table records a history of the events that have occurred
         at the Ethernet OAM level. These events can include locally detected
         events, which may result in locally generated OAMPDUs, and remotely
         detected events, which are detected by the OAM peer entity and
         signaled to the local entity via Ethernet OAM. Ethernet OAM events
         can be signaled by Event Notification OAMPDUs or by the flags
         field in any OAMPDU.";
    }
    description
      "EOAM port operational information.";
  }
}
