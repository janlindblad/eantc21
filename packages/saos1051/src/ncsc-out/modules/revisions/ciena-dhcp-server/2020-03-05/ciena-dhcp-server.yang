module ciena-dhcp-server {
  // Generated by yanger -t ncs
  tailf:mount-id "saos1051-nc-1.0:saos1051-nc-1.0";
  tailf:ncs-device-type "netconf";

  namespace "http://www.ciena.com/dhcpServer/yang/ciena-dhcp-server";
  prefix cds;

  import ietf-inet-types {
    prefix inet;
  }
  import ietf-yang-types {
    prefix yang;
  }
  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines DHCP Server Model..

     Copyright (c) 2020 Ciena Corporation.  All rights
     reserved.

     All information contained herein is, and remains
     the property of Ciena Corporation. Dissemination of this
     information or reproduction of this material is strictly
     forbidden unless prior written permission is obtained from
     Ciena Corporation.";

  revision 2020-03-05 {
    description
      "Initial version";
    reference
      "RFC 6020: YANG - A Data Modeling Language for
       the Network Configuration Protocol (NETCONF).
       DHCP server IETF YANG model reference is
       http://www.netconfcentral.org/modules/ietf-dhcp";
  }

  typedef ncs_template_allocate-type {
    type string;
    description
      "Mechanisms for IP address allocation";
  }

  typedef ncs_template_dhcp-ip-pool-name-ref {
    type string;
    description
      "Reusable type for by-name reference.
       This type may be used in cases where ability to reference
       a subinterface is not required.";
  }

  typedef ncs_rpc_notif_allocate-type {
    type enumeration {
      enum "automatic" {
        description
          "DHCP assigns a permanent IP address to a client";
      }
      enum "dynamic" {
        description
          "DHCP assigns an IP address to a client
           for a limited period of time";
      }
      enum "manual" {
        description
          "a client's IP address is assigned by the
           network administrator, and DHCP is used
           simply to convey the assigned address to the client";
      }
    }
    description
      "Mechanisms for IP address allocation";
  }

  typedef ncs_rpc_notif_dhcp-ip-pool-name-ref {
    type string;
    description
      "Reusable type for by-name reference.
       This type may be used in cases where ability to reference
       a subinterface is not required.";
  }

  typedef live_ncs_allocate-type {
    type enumeration {
      enum "automatic" {
        description
          "DHCP assigns a permanent IP address to a client";
      }
      enum "dynamic" {
        description
          "DHCP assigns an IP address to a client
           for a limited period of time";
      }
      enum "manual" {
        description
          "a client's IP address is assigned by the
           network administrator, and DHCP is used
           simply to convey the assigned address to the client";
      }
    }
    description
      "Mechanisms for IP address allocation";
  }

  typedef live_ncs_dhcp-ip-pool-name-ref {
    type leafref {
      path "/ncs:devices/ncs:device/ncs:live-status/cds:dhcp-server/cds:dhcp-ip-pool/cds:ip-pool-name" {
        tailf:xpath-root 3;
      }
    }
    description
      "Reusable type for by-name reference.
       This type may be used in cases where ability to reference
       a subinterface is not required.";
  }

  typedef allocate-type {
    type enumeration {
      enum "automatic" {
        description
          "DHCP assigns a permanent IP address to a client";
      }
      enum "dynamic" {
        description
          "DHCP assigns an IP address to a client
           for a limited period of time";
      }
      enum "manual" {
        description
          "a client's IP address is assigned by the
           network administrator, and DHCP is used
           simply to convey the assigned address to the client";
      }
    }
    description
      "Mechanisms for IP address allocation";
  }

  typedef dhcp-ip-pool-name-ref {
    type leafref {
      path "/ncs:devices/ncs:device/ncs:config/cds:dhcp-server/cds:dhcp-ip-pool/cds:ip-pool-name" {
        tailf:xpath-root 3;
      }
    }
    description
      "Reusable type for by-name reference.
       This type may be used in cases where ability to reference
       a subinterface is not required.";
  }

  grouping ncs_template_server-packet {
    description
      "The packets are sent from server ";
    // NCS drop config false leaf 'offer-packet'
    // NCS drop config false leaf 'ack-packet'
    // NCS drop config false leaf 'nack-packet'
  }

  grouping ncs_template_client-packet {
    description
      "The packets are sent from client ";
    // NCS drop config false leaf 'decline-packet'
    // NCS drop config false leaf 'discover-packet'
    // NCS drop config false leaf 'request-packet'
    // NCS drop config false leaf 'release-packet'
    // NCS drop config false leaf 'inform-packet'
  }

  grouping ncs_rpc_notif_server-packet {
    description
      "The packets are sent from server ";
    leaf offer-packet {
      type uint32;
      config false;
      description
        "Total number of DHCPOFFER packets";
    }
    leaf ack-packet {
      type uint32;
      config false;
      description
        "Total number of DHCPACK packets";
    }
    leaf nack-packet {
      type uint32;
      config false;
      description
        "Total number of DHCPNAK packets";
    }
  }

  grouping ncs_rpc_notif_client-packet {
    description
      "The packets are sent from client ";
    leaf decline-packet {
      type uint32;
      config false;
      description
        "Total number of DHCPDECLINE packets";
    }
    leaf discover-packet {
      type uint32;
      config false;
      description
        "Total number of DHCPDISCOVER packets";
    }
    leaf request-packet {
      type uint32;
      config false;
      description
        "Total number of DHCPREQUEST packets";
    }
    leaf release-packet {
      type uint32;
      config false;
      description
        "Total number of DHCPRELEASE packets";
    }
    leaf inform-packet {
      type uint32;
      config false;
      description
        "Total number of DHCPINFORM packets";
    }
  }

  grouping live_ncs_server-packet {
    description
      "The packets are sent from server ";
    leaf offer-packet {
      type uint32;
      description
        "Total number of DHCPOFFER packets";
    }
    leaf ack-packet {
      type uint32;
      description
        "Total number of DHCPACK packets";
    }
    leaf nack-packet {
      type uint32;
      description
        "Total number of DHCPNAK packets";
    }
  }

  grouping live_ncs_client-packet {
    description
      "The packets are sent from client ";
    leaf decline-packet {
      type uint32;
      description
        "Total number of DHCPDECLINE packets";
    }
    leaf discover-packet {
      type uint32;
      description
        "Total number of DHCPDISCOVER packets";
    }
    leaf request-packet {
      type uint32;
      description
        "Total number of DHCPREQUEST packets";
    }
    leaf release-packet {
      type uint32;
      description
        "Total number of DHCPRELEASE packets";
    }
    leaf inform-packet {
      type uint32;
      description
        "Total number of DHCPINFORM packets";
    }
  }

  grouping server-packet {
    description
      "The packets are sent from server ";
    // NCS drop config false leaf 'offer-packet'
    // NCS drop config false leaf 'ack-packet'
    // NCS drop config false leaf 'nack-packet'
  }

  grouping client-packet {
    description
      "The packets are sent from client ";
    // NCS drop config false leaf 'decline-packet'
    // NCS drop config false leaf 'discover-packet'
    // NCS drop config false leaf 'request-packet'
    // NCS drop config false leaf 'release-packet'
    // NCS drop config false leaf 'inform-packet'
  }

  augment "/ncs:devices/ncs:device/ncs:rpc" {
    container rpc-clean-dhcp-server-statistics {
      tailf:ncs-device-type "netconf";
      tailf:display-when "not(../../ncs:module) or ../../ncs:module[ncs:name='ciena-dhcp-server']";
      tailf:action clean-dhcp-server-statistics {
        tailf:actionpoint ncsproxy {
          tailf:internal;
        }
        description
          "Clean dhcp server packet statistics";
      }
    }
  }
  augment "/ncs:devices/ncs:device-group/ncs:ned-id/ncs:rpc" {
    container rpc-clean-dhcp-server-statistics {
      tailf:ncs-device-type "netconf";
      tailf:display-when "/ncs:devices/ncs:device[ncs:name=current()/../../../ncs:member]/ncs:module[ncs:name='ciena-dhcp-server']";
      tailf:action clean-dhcp-server-statistics {
        tailf:actionpoint ncsproxy {
          tailf:internal;
        }
        description
          "Clean dhcp server packet statistics";
      }
    }
  }
  augment "/ncs:devices/ncs:device/ncs:config" {
    container dhcp-server {
      tailf:ncs-device-type "netconf";
      tailf:display-when "not(../../ncs:module) or ../../ncs:module[ncs:name='ciena-dhcp-server']";
      description
        "DHCP server configuration";
      list dhcp-ip-pool {
        key "ip-pool-name";
        description
          "Global IP pool configuration";
        leaf ip-pool-name {
          type string {
            length "1..64";
          }
          description
            "Name of the IP pool";
        }
        leaf interface {
          type oc-if:base-interface-ref;
          description
            "Name of the interface";
        }
        leaf gateway-ip {
          type inet:ipv4-address;
          description
            "IPv4 address of the gateway";
        }
        leaf gateway-mask {
          type inet:ipv4-prefix;
          mandatory true;
          description
            "Network submask of the gateway";
        }
        leaf lease-time {
          type uint32 {
            range "180..31536000";
          }
          units "seconds";
          description
            "Default network address lease time assigned to DHCP clients";
        }
        leaf domain-name {
          type string {
            length "1..255";
          }
          description
            "Name of the domain";
        }
        list manual-allocation {
          key "mac-address ip-address";
          description
            "Mapping from MAC address to IP address";
          leaf mac-address {
            type yang:mac-address;
            description
              "MAC address of the host";
          }
          leaf ip-address {
            type inet:ipv4-address;
            description
              "IPv4 address of the host";
          }
        }
        list section {
          key "section-index";
          description
            "IPv4 address for the range";
          leaf section-index {
            type uint16 {
              range "0..255";
            }
            description
              "Index of IPv4 address range";
          }
          leaf section-start-ip {
            type inet:ipv4-address;
            mandatory true;
            description
              "Starting IPv4 Address of a section";
          }
          leaf section-end-ip {
            type inet:ipv4-address;
            description
              "Last IPv4 Address of a section";
          }
        }
        container option {
          description
            "Configuration option";
          leaf dhcp-server-identifier {
            type inet:ipv4-address;
            description
              "DHCP server identifier";
          }
          leaf domain-name {
            type string {
              length "1..255";
            }
            description
              "Name of the domain";
          }
          leaf domain-name-server {
            type inet:ipv4-address;
            description
              "IPv4 address of the domain";
          }
        }
      }
    }
    // NCS drop config false container 'dhcp-server-state'
  }
  augment "/ncs:devices/ncs:device/ncs:live-status" {
    container dhcp-server {
      tailf:ncs-device-type "netconf";
      tailf:display-when "not(../../ncs:module) or ../../ncs:module[ncs:name='ciena-dhcp-server'] or (../../ncs:live-status-protocol[not(ncs:capability)]) or (../../ncs:live-status-protocol/ncs:capability/ncs:module[.='ciena-dhcp-server'])";
      description
        "DHCP server configuration";
      list dhcp-ip-pool {
        key "ip-pool-name";
        description
          "Global IP pool configuration";
        leaf ip-pool-name {
          type string {
            length "1..64";
          }
          description
            "Name of the IP pool";
        }
        leaf interface {
          type oc-if:live_ncs_base-interface-ref;
          description
            "Name of the interface";
        }
        leaf gateway-ip {
          type inet:ipv4-address;
          description
            "IPv4 address of the gateway";
        }
        leaf gateway-mask {
          type inet:ipv4-prefix;
          // NCS drop mandatory statement
          description
            "Network submask of the gateway";
        }
        leaf lease-time {
          type uint32 {
            range "180..31536000";
          }
          units "seconds";
          description
            "Default network address lease time assigned to DHCP clients";
        }
        leaf domain-name {
          type string {
            length "1..255";
          }
          description
            "Name of the domain";
        }
        list manual-allocation {
          key "mac-address ip-address";
          description
            "Mapping from MAC address to IP address";
          leaf mac-address {
            type yang:mac-address;
            description
              "MAC address of the host";
          }
          leaf ip-address {
            type inet:ipv4-address;
            description
              "IPv4 address of the host";
          }
        }
        list section {
          key "section-index";
          description
            "IPv4 address for the range";
          leaf section-index {
            type uint16 {
              range "0..255";
            }
            description
              "Index of IPv4 address range";
          }
          leaf section-start-ip {
            type inet:ipv4-address;
            // NCS drop mandatory statement
            description
              "Starting IPv4 Address of a section";
          }
          leaf section-end-ip {
            type inet:ipv4-address;
            description
              "Last IPv4 Address of a section";
          }
        }
        container option {
          description
            "Configuration option";
          leaf dhcp-server-identifier {
            type inet:ipv4-address;
            description
              "DHCP server identifier";
          }
          leaf domain-name {
            type string {
              length "1..255";
            }
            description
              "Name of the domain";
          }
          leaf domain-name-server {
            type inet:ipv4-address;
            description
              "IPv4 address of the domain";
          }
        }
      }
    }
    container dhcp-server-state {
      tailf:ncs-device-type "netconf";
      tailf:display-when "not(../../ncs:module) or ../../ncs:module[ncs:name='ciena-dhcp-server'] or (../../ncs:live-status-protocol[not(ncs:capability)]) or (../../ncs:live-status-protocol/ncs:capability/ncs:module[.='ciena-dhcp-server'])";
      description
        "DHCP server state data";
      list dhcp-ip-pool {
        key "ip-pool-name";
        description
          "Global IP pool configuration";
        leaf ip-pool-name {
          type string;
          description
            "Name of an IP pool";
        }
        leaf gateway-ip {
          type inet:ipv4-address;
          description
            "IPv4 address of the gateway";
        }
        leaf gateway-mask {
          type inet:ipv4-prefix;
          description
            "Network submask of the gateway";
        }
        container packet-statistics {
          description
            "Packet statistics";
          container receive {
            description
              "Number of received packets";
            uses live_ncs_client-packet;
          }
          container send {
            description
              "Number of sent packets";
            uses live_ncs_server-packet;
          }
        }
        container hosts {
          description
            "Information of all the clients in the pool";
          list host {
            key "interface";
            description
              "Host status information";
            leaf interface {
              type string;
              description
                "Name of the interface";
            }
            leaf host-ip {
              type inet:ipv4-address;
              description
                "IPv4 address of the host";
            }
            leaf host-hardware-address {
              type yang:mac-address;
              description
                "MAC address of the host";
            }
            leaf lease {
              type uint32;
              description
                "Default network address lease
                 time assigned to DHCP clients";
            }
            leaf type {
              type live_ncs_allocate-type;
              description
                "Mechanisms for IP address allocation";
            }
          }
        }
      }
    }
  }
  augment "/ncs:devices/ncs:template/ncs:ned-id/ncs:config" {
    container dhcp-server {
      description
        "DHCP server configuration";
      list dhcp-ip-pool {
        // NCS patched for predictable order
        ordered-by user;
        key "ip-pool-name";
        description
          "Global IP pool configuration";
        leaf ip-pool-name {
          type string;
          description
            "Name of the IP pool";
        }
        leaf interface {
          type oc-if:ncs_template_base-interface-ref;
          description
            "Name of the interface";
        }
        leaf gateway-ip {
          type string;
          description
            "IPv4 address of the gateway";
        }
        leaf gateway-mask {
          type string;
          // NCS drop mandatory statement
          description
            "Network submask of the gateway";
        }
        leaf lease-time {
          type string;
          units "seconds";
          description
            "Default network address lease time assigned to DHCP clients";
        }
        leaf domain-name {
          type string;
          description
            "Name of the domain";
        }
        list manual-allocation {
          // NCS patched for predictable order
          ordered-by user;
          key "mac-address ip-address";
          description
            "Mapping from MAC address to IP address";
          leaf mac-address {
            type string;
            description
              "MAC address of the host";
          }
          leaf ip-address {
            type string;
            description
              "IPv4 address of the host";
          }
        }
        list section {
          // NCS patched for predictable order
          ordered-by user;
          key "section-index";
          description
            "IPv4 address for the range";
          leaf section-index {
            type string;
            description
              "Index of IPv4 address range";
          }
          leaf section-start-ip {
            type string;
            // NCS drop mandatory statement
            description
              "Starting IPv4 Address of a section";
          }
          leaf section-end-ip {
            type string;
            description
              "Last IPv4 Address of a section";
          }
        }
        container option {
          description
            "Configuration option";
          leaf dhcp-server-identifier {
            type string;
            description
              "DHCP server identifier";
          }
          leaf domain-name {
            type string;
            description
              "Name of the domain";
          }
          leaf domain-name-server {
            type string;
            description
              "IPv4 address of the domain";
          }
        }
      }
    }
    // NCS drop config false container 'dhcp-server-state'
  }
}
