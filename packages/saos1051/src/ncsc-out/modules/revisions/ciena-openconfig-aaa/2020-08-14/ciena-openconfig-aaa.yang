module ciena-openconfig-aaa {
  // Generated by yanger -t ncs
  tailf:mount-id "saos1051-nc-1.0:saos1051-nc-1.0";
  tailf:ncs-device-type "netconf";

  namespace "http://www.ciena.com/ns/yang/ciena-openconfig-aaa";
  prefix ciena-oc-aaa;

  import openconfig-aaa-types {
    prefix oc-aaa-types;
  }
  import ciena-openconfig-aaa-types {
    prefix cn-oc-aaa-types;
  }
  import openconfig-system {
    prefix oc-sys;
  }
  import ciena-types {
    prefix ciena;
  }
  import openconfig-yang-types {
    prefix oc-yang;
  }
  import ietf-yang-types {
    prefix yang;
  }
  import openconfig-inet-types {
    prefix oc-inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's augmentations to openconfig-aaa.

      Copyright (c) 2017 Ciena Corporation.  All rights
      reserved.

      All information contained herein is, and remains
      the property of Ciena Corporation. Dissemination of this
      information or reproduction of this material is strictly
      forbidden unless prior written permission is obtained from
      Ciena Corporation.";

  revision 2020-08-14 {
    description
      "Moved user identities to ciena-openconfig-aaa-types";
    reference "";
  }
  revision 2019-09-17 {
    description
      "Augmentations for server-group cached mode server search.";
    reference "";
  }
  revision 2019-06-04 {
    description
      "Added RPC to clear server statistics and radius counters.
       Added RPC to clear auth statistics.";
    reference "";
  }
  revision 2018-06-20 {
    description
      "augmentations for additional server statistics and radius counters";
    reference "";
  }
  revision 2018-04-09 {
    description
      "augmentations for authentication provider stats";
    reference "";
  }
  revision 2018-03-12 {
    description
      "Added password-policy and lockout-policy containers.
       Added the unlock user-account RPC.";
    reference "";
  }
  revision 2017-09-19 {
    description
      "Initial version";
    reference
      "RFC 6020: YANG - A Data Modeling Language for
       the Network Configuration Protocol (NETCONF).
       No specific reference; standard not available.";
  }

  typedef ncs_template_on-off-state {
    type string;
    description
      "The on / off state.";
  }

  typedef ncs_rpc_notif_on-off-state {
    type enumeration {
      enum "off" {
        description
          "The off state.";
      }
      enum "on" {
        description
          "The on state.";
      }
    }
    description
      "The on / off state.";
  }

  typedef live_ncs_on-off-state {
    type enumeration {
      enum "off" {
        description
          "The off state.";
      }
      enum "on" {
        description
          "The on state.";
      }
    }
    description
      "The on / off state.";
  }

  typedef on-off-state {
    type enumeration {
      enum "off" {
        description
          "The off state.";
      }
      enum "on" {
        description
          "The on state.";
      }
    }
    description
      "The on / off state.";
  }

  augment "/ncs:devices/ncs:device/ncs:rpc" {
    container rpc-clear-aaa-auth-stats {
      tailf:ncs-device-type "netconf";
      tailf:display-when "not(../../ncs:module) or ../../ncs:module[ncs:name='ciena-openconfig-aaa']";
      tailf:action clear-aaa-auth-stats {
        tailf:actionpoint ncsproxy {
          tailf:internal;
        }
        description
          "Clears locally-cached aaa authentication statistics.";
        input {
          leaf method {
            type string;
            description
              "Authentication method to clear stats for.";
          }
        }
      }
    }
  }
  augment "/ncs:devices/ncs:device-group/ncs:ned-id/ncs:rpc" {
    container rpc-clear-aaa-auth-stats {
      tailf:ncs-device-type "netconf";
      tailf:display-when "/ncs:devices/ncs:device[ncs:name=current()/../../../ncs:member]/ncs:module[ncs:name='ciena-openconfig-aaa']";
      tailf:action clear-aaa-auth-stats {
        tailf:actionpoint ncsproxy {
          tailf:internal;
        }
        description
          "Clears locally-cached aaa authentication statistics.";
        input {
          leaf method {
            type string;
            description
              "Authentication method to clear stats for.";
          }
        }
      }
    }
  }
  augment "/ncs:devices/ncs:device/ncs:rpc" {
    container rpc-clear-aaa-server-stats {
      tailf:ncs-device-type "netconf";
      tailf:display-when "not(../../ncs:module) or ../../ncs:module[ncs:name='ciena-openconfig-aaa']";
      tailf:action clear-aaa-server-stats {
        tailf:actionpoint ncsproxy {
          tailf:internal;
        }
        description
          "Clears locally-cached aaa server statistics.";
        input {
          leaf server-group {
            type string;
            description
              "Server-group to clear stats for.";
          }
          leaf address {
            type oc-inet:ncs_rpc_notif_ip-address;
            description
              "IP address to clear stats for.";
          }
        }
      }
    }
  }
  augment "/ncs:devices/ncs:device-group/ncs:ned-id/ncs:rpc" {
    container rpc-clear-aaa-server-stats {
      tailf:ncs-device-type "netconf";
      tailf:display-when "/ncs:devices/ncs:device[ncs:name=current()/../../../ncs:member]/ncs:module[ncs:name='ciena-openconfig-aaa']";
      tailf:action clear-aaa-server-stats {
        tailf:actionpoint ncsproxy {
          tailf:internal;
        }
        description
          "Clears locally-cached aaa server statistics.";
        input {
          leaf server-group {
            type string;
            description
              "Server-group to clear stats for.";
          }
          leaf address {
            type oc-inet:ncs_rpc_notif_ip-address;
            description
              "IP address to clear stats for.";
          }
        }
      }
    }
  }
  augment "/ncs:devices/ncs:device/ncs:rpc" {
    container rpc-unlock-user-account {
      tailf:ncs-device-type "netconf";
      tailf:display-when "not(../../ncs:module) or ../../ncs:module[ncs:name='ciena-openconfig-aaa']";
      tailf:action unlock-user-account {
        tailf:actionpoint ncsproxy {
          tailf:internal;
        }
        description
          "Unlocks the linked user account.";
        input {
          leaf user {
            type string;
            description
              "Username to unlock.";
          }
        }
      }
    }
  }
  augment "/ncs:devices/ncs:device-group/ncs:ned-id/ncs:rpc" {
    container rpc-unlock-user-account {
      tailf:ncs-device-type "netconf";
      tailf:display-when "/ncs:devices/ncs:device[ncs:name=current()/../../../ncs:member]/ncs:module[ncs:name='ciena-openconfig-aaa']";
      tailf:action unlock-user-account {
        tailf:actionpoint ncsproxy {
          tailf:internal;
        }
        description
          "Unlocks the linked user account.";
        input {
          leaf user {
            type string;
            description
              "Username to unlock.";
          }
        }
      }
    }
  }
  augment "/ncs:devices/ncs:device/ncs:netconf-notifications/ncs:received-notifications/ncs:notification/ncs:data" {
    container login-event {
      presence "";
      config false;
      description
        "Login event notification";
      leaf user-name {
        description
          "Name of user trying to access system";
        type string;
      }
      leaf login-status {
        description
          "Login success or failure indication";
        type string;
      }
      leaf ip-address {
        description
          "Remote ip that was used for login";
        type string;
      }
      leaf port {
        description
          "Port used to access";
        type string;
      }
      leaf event-type {
        description
          "Type of login event the user would like to subscribe to.";
        type enumeration {
          enum "SUCCESS" {
            description
              "Subscribe to only successful login notifications.";
          }
          enum "FAILURE" {
            description
              "Subscribe to only failed login notifications.";
          }
          enum "ANY" {
            description
              "Subscribe to any login notifications.";
          }
        }
      }
    }
  }
  augment "/ncs:devices/ncs:template/ncs:ned-id/ncs:config/oc-sys:system/oc-sys:aaa/oc-sys:authentication" {
    description
      "Authentication augmentation that supports the lockout and password policies.";
    container password-policy {
      description
        "Rules about how users are allowed to create passwords.";
      container config {
        description
          "Configurable password-policy leaves";
        leaf disallow-dict-words {
          type ncs_template_on-off-state;
          description
            "Disallow passwords containing words in the dictionary.";
        }
        leaf disallow-username {
          type ncs_template_on-off-state;
          description
            "Disallow passwords containing the user name or its reverse.";
        }
        leaf max-repeated-chars {
          type string;
          description
            "Maximum run of the same character in user account passwords.";
        }
        leaf min-length {
          type string;
          description
            "Minimum length of the user account passwords.";
        }
        leaf min-lowercase-chars {
          type string;
          description
            "Minimum number of lower case letters in the user account passwords.";
        }
        leaf min-numeric-chars {
          type string;
          description
            "Minimum number of numeric characters in the user account passwords.";
        }
        leaf min-special-chars {
          type string;
          description
            "Minimum number of special characters in the user account passwords, such as !@#$%^*().";
        }
        leaf min-uppercase-chars {
          type string;
          description
            "Minimum number of upper case letters in the user account passwords.";
        }
      }
    }
    container lockout-policy {
      description
        "Rules about when and how user passwords get locked out.";
      container config {
        description
          "Configurable lockout-policy leaves";
        leaf fail-limit {
          type string;
          description
            "Number of times a user's password can be invalid before they are locked out.";
        }
        leaf lockout-time {
          type string;
          description
            "Amount of time a user is locked out before they can retry.";
        }
      }
    }
  }
  augment "/ncs:devices/ncs:device/ncs:live-status/oc-sys:system/oc-sys:aaa/oc-sys:authentication" {
    description
      "Authentication augmentation that supports the lockout and password policies.";
    container password-policy {
      tailf:ncs-device-type "netconf";
      tailf:display-when "not(../../../../../ncs:module) or ../../../../../ncs:module[ncs:name='ciena-openconfig-aaa'] or (../../../../../ncs:live-status-protocol[not(ncs:capability)]) or (../../../../../ncs:live-status-protocol/ncs:capability/ncs:module[.='ciena-openconfig-aaa'])";
      description
        "Rules about how users are allowed to create passwords.";
      container config {
        description
          "Configurable password-policy leaves";
        leaf disallow-dict-words {
          type live_ncs_on-off-state;
          description
            "Disallow passwords containing words in the dictionary.";
        }
        leaf disallow-username {
          type live_ncs_on-off-state;
          description
            "Disallow passwords containing the user name or its reverse.";
        }
        leaf max-repeated-chars {
          type uint16 {
            range "0..128";
          }
          description
            "Maximum run of the same character in user account passwords.";
        }
        leaf min-length {
          type uint16 {
            range "0..128";
          }
          description
            "Minimum length of the user account passwords.";
        }
        leaf min-lowercase-chars {
          type uint16 {
            range "0..128";
          }
          description
            "Minimum number of lower case letters in the user account passwords.";
        }
        leaf min-numeric-chars {
          type uint16 {
            range "0..128";
          }
          description
            "Minimum number of numeric characters in the user account passwords.";
        }
        leaf min-special-chars {
          type uint16 {
            range "0..128";
          }
          description
            "Minimum number of special characters in the user account passwords, such as !@#$%^*().";
        }
        leaf min-uppercase-chars {
          type uint16 {
            range "0..128";
          }
          description
            "Minimum number of upper case letters in the user account passwords.";
        }
      }
    }
    container lockout-policy {
      tailf:ncs-device-type "netconf";
      tailf:display-when "not(../../../../../ncs:module) or ../../../../../ncs:module[ncs:name='ciena-openconfig-aaa'] or (../../../../../ncs:live-status-protocol[not(ncs:capability)]) or (../../../../../ncs:live-status-protocol/ncs:capability/ncs:module[.='ciena-openconfig-aaa'])";
      description
        "Rules about when and how user passwords get locked out.";
      container config {
        description
          "Configurable lockout-policy leaves";
        leaf fail-limit {
          type uint16 {
            range "0..5";
          }
          description
            "Number of times a user's password can be invalid before they are locked out.";
        }
        leaf lockout-time {
          type uint16;
          description
            "Amount of time a user is locked out before they can retry.";
        }
      }
    }
  }
  augment "/ncs:devices/ncs:device/ncs:config/oc-sys:system/oc-sys:aaa/oc-sys:authentication" {
    description
      "Authentication augmentation that supports the lockout and password policies.";
    container password-policy {
      tailf:ncs-device-type "netconf";
      tailf:display-when "not(../../../../../ncs:module) or ../../../../../ncs:module[ncs:name='ciena-openconfig-aaa']";
      description
        "Rules about how users are allowed to create passwords.";
      container config {
        description
          "Configurable password-policy leaves";
        leaf disallow-dict-words {
          type on-off-state;
          description
            "Disallow passwords containing words in the dictionary.";
        }
        leaf disallow-username {
          type on-off-state;
          description
            "Disallow passwords containing the user name or its reverse.";
        }
        leaf max-repeated-chars {
          type uint16 {
            range "0..128";
          }
          description
            "Maximum run of the same character in user account passwords.";
        }
        leaf min-length {
          type uint16 {
            range "0..128";
          }
          description
            "Minimum length of the user account passwords.";
        }
        leaf min-lowercase-chars {
          type uint16 {
            range "0..128";
          }
          description
            "Minimum number of lower case letters in the user account passwords.";
        }
        leaf min-numeric-chars {
          type uint16 {
            range "0..128";
          }
          description
            "Minimum number of numeric characters in the user account passwords.";
        }
        leaf min-special-chars {
          type uint16 {
            range "0..128";
          }
          description
            "Minimum number of special characters in the user account passwords, such as !@#$%^*().";
        }
        leaf min-uppercase-chars {
          type uint16 {
            range "0..128";
          }
          description
            "Minimum number of upper case letters in the user account passwords.";
        }
      }
    }
    container lockout-policy {
      tailf:ncs-device-type "netconf";
      tailf:display-when "not(../../../../../ncs:module) or ../../../../../ncs:module[ncs:name='ciena-openconfig-aaa']";
      description
        "Rules about when and how user passwords get locked out.";
      container config {
        description
          "Configurable lockout-policy leaves";
        leaf fail-limit {
          type uint16 {
            range "0..5";
          }
          description
            "Number of times a user's password can be invalid before they are locked out.";
        }
        leaf lockout-time {
          type uint16;
          description
            "Amount of time a user is locked out before they can retry.";
        }
      }
    }
  }
  augment "/ncs:devices/ncs:device/ncs:live-status/oc-sys:system/oc-sys:aaa/oc-sys:authentication/oc-sys:state" {
    description
      "Augmentation for openconfig-aaa to add authentication stats per provider";
    list authentication-provider {
      tailf:ncs-device-type "netconf";
      tailf:display-when "not(../../../../../ncs:module) or ../../../../../ncs:module[ncs:name='ciena-openconfig-aaa'] or (../../../../../ncs:live-status-protocol[not(ncs:capability)]) or (../../../../../ncs:live-status-protocol/ncs:capability/ncs:module[.='ciena-openconfig-aaa'])";
      key "name";
      description
        "List of server-groups configured to provide authentication services";
      leaf name {
        type string;
        description
          "Reference to configured name of server-group providing authentication services";
      }
      leaf type {
        type identityref {
          base AUTHEN_PVDR_TYPE;
        }
        description
          "Reference to type of authentication service provided";
      }
      leaf oper-state {
        type ciena:live_ncs_oper-state;
        description
          "the operational state of the authentication provider";
      }
      leaf called {
        type oc-yang:live_ncs_counter64;
        description
          "Number of times this authentication provider was invoked.";
      }
      leaf success {
        type oc-yang:live_ncs_counter64;
        description
          "Number of times this authentication provider returned success.";
      }
      leaf failure {
        type oc-yang:live_ncs_counter64;
        description
          "Number of times this authentication provider returned failure.";
      }
      leaf skipped {
        type oc-yang:live_ncs_counter64;
        description
          "Number of times this authentication provider was skipped.";
      }
    }
  }
  augment "/ncs:devices/ncs:template/ncs:ned-id/ncs:config/oc-sys:system/oc-sys:aaa/oc-sys:server-groups/oc-sys:server-group/oc-sys:config" {
    description
      "Augmentation for openconfig-aaa to add search-mode leaf to server-group configuration";
    leaf search-method {
      type string;
      // NCS drop default statement
      description
        "The search method for the server group to perform when trying servers in the server group.";
    }
  }
  augment "/ncs:devices/ncs:device/ncs:live-status/oc-sys:system/oc-sys:aaa/oc-sys:server-groups/oc-sys:server-group/oc-sys:config" {
    description
      "Augmentation for openconfig-aaa to add search-mode leaf to server-group configuration";
    leaf search-method {
      tailf:ncs-device-type "netconf";
      tailf:display-when "not(../../../../../../../ncs:module) or ../../../../../../../ncs:module[ncs:name='ciena-openconfig-aaa'] or (../../../../../../../ncs:live-status-protocol[not(ncs:capability)]) or (../../../../../../../ncs:live-status-protocol/ncs:capability/ncs:module[.='ciena-openconfig-aaa'])";
      type enumeration {
        enum "priority" {
          description
            "Search in order of servers listed.";
        }
        enum "cached" {
          description
            "Search starting with last known good server in server group.";
        }
      }
      // NCS drop default statement
      description
        "The search method for the server group to perform when trying servers in the server group.";
    }
  }
  augment "/ncs:devices/ncs:device/ncs:config/oc-sys:system/oc-sys:aaa/oc-sys:server-groups/oc-sys:server-group/oc-sys:config" {
    description
      "Augmentation for openconfig-aaa to add search-mode leaf to server-group configuration";
    leaf search-method {
      tailf:ncs-device-type "netconf";
      tailf:display-when "not(../../../../../../../ncs:module) or ../../../../../../../ncs:module[ncs:name='ciena-openconfig-aaa']";
      type enumeration {
        enum "priority" {
          description
            "Search in order of servers listed.";
        }
        enum "cached" {
          description
            "Search starting with last known good server in server group.";
        }
      }
      default "cached";
      description
        "The search method for the server group to perform when trying servers in the server group.";
    }
  }
  augment "/ncs:devices/ncs:template/ncs:ned-id/ncs:config/oc-sys:system/oc-sys:aaa/oc-sys:server-groups/oc-sys:server-group/oc-sys:servers/oc-sys:server/oc-sys:config" {
    description
      "Augmentation for openconfig-aaa to add admin-state leaf to server list entries";
    leaf admin-state {
      type ciena:ncs_template_admin-state;
      // NCS drop default statement
      description
        "the administrative state of the authentication server";
    }
  }
  augment "/ncs:devices/ncs:device/ncs:live-status/oc-sys:system/oc-sys:aaa/oc-sys:server-groups/oc-sys:server-group/oc-sys:servers/oc-sys:server/oc-sys:config" {
    description
      "Augmentation for openconfig-aaa to add admin-state leaf to server list entries";
    leaf admin-state {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type ciena:live_ncs_admin-state;
      // NCS drop default statement
      description
        "the administrative state of the authentication server";
    }
  }
  augment "/ncs:devices/ncs:device/ncs:config/oc-sys:system/oc-sys:aaa/oc-sys:server-groups/oc-sys:server-group/oc-sys:servers/oc-sys:server/oc-sys:config" {
    description
      "Augmentation for openconfig-aaa to add admin-state leaf to server list entries";
    leaf admin-state {
      tailf:ncs-device-type "netconf";
      tailf:display-when "not(../../../../../../../../../ncs:module) or ../../../../../../../../../ncs:module[ncs:name='ciena-openconfig-aaa']";
      type ciena:admin-state;
      default "enabled";
      description
        "the administrative state of the authentication server";
    }
  }
  augment "/ncs:devices/ncs:device/ncs:live-status/oc-sys:system/oc-sys:aaa/oc-sys:server-groups/oc-sys:server-group/oc-sys:servers/oc-sys:server/oc-sys:state" {
    description
      "Augmentation for openconfig-aaa to add oper-state and SAOS-style server statistics";
    leaf access-requests {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type oc-yang:live_ncs_counter64;
      description
        "The number of Access-Request packets sent to this server.
         This does not include retransmissions.";
    }
    leaf access-accepts {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type oc-yang:live_ncs_counter64;
      description
        "The number of Access-Accept packets received from this server.";
    }
    leaf access-rejects {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type oc-yang:live_ncs_counter64;
      description
        "The number of Access-Reject packets received from this server.";
    }
    leaf malformed-responses {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type oc-yang:live_ncs_counter64;
      description
        "The number of Malformed-Response packets received from this server.
         Malformed packets include packets with an invalid length.
         Bad authenticators or signature attributes or unknown types are not included
         as malformed access responses.";
    }
    leaf bad-authenticators {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type oc-yang:live_ncs_counter64;
      description
        "The number of packets containing invalid authenticators
         or signature attributes received from this server.";
    }
    leaf oper-state {
      tailf:ncs-device-type "netconf";
      tailf:display-when "not(../../../../../../../../../ncs:module) or ../../../../../../../../../ncs:module[ncs:name='ciena-openconfig-aaa'] or (../../../../../../../../../ncs:live-status-protocol[not(ncs:capability)]) or (../../../../../../../../../ncs:live-status-protocol/ncs:capability/ncs:module[.='ciena-openconfig-aaa'])";
      type ciena:live_ncs_oper-state;
      // NCS drop default statement
      description
        "the operational state of the AAA server.";
    }
  }
  augment "/ncs:devices/ncs:device/ncs:live-status/oc-sys:system/oc-sys:aaa/oc-sys:server-groups/oc-sys:server-group/oc-sys:servers/oc-sys:server/oc-sys:radius/oc-sys:state/oc-sys:counters" {
    description
      "Augmentation for openconfig-aaa-radius to add additional RADIUS specific counters";
    leaf access-challenges {
      tailf:ncs-device-type "netconf";
      tailf:display-when "not(../../../../../../../../../../../ncs:module) or ../../../../../../../../../../../ncs:module[ncs:name='ciena-openconfig-aaa'] or (../../../../../../../../../../../ncs:live-status-protocol[not(ncs:capability)]) or (../../../../../../../../../../../ncs:live-status-protocol/ncs:capability/ncs:module[.='ciena-openconfig-aaa'])";
      type oc-yang:live_ncs_counter64;
      description
        "The number of RADIUS Access-Challenge packets (valid or invalid) received
         from this server.";
    }
    leaf accounting-responses {
      tailf:ncs-device-type "netconf";
      tailf:display-when "not(../../../../../../../../../../../ncs:module) or ../../../../../../../../../../../ncs:module[ncs:name='ciena-openconfig-aaa'] or (../../../../../../../../../../../ncs:live-status-protocol[not(ncs:capability)]) or (../../../../../../../../../../../ncs:live-status-protocol/ncs:capability/ncs:module[.='ciena-openconfig-aaa'])";
      type oc-yang:live_ncs_counter64;
      description
        "The number of RADIUS Accounting-Response packets (valid or invalid) received
         from this server.";
    }
    leaf unknown-types {
      tailf:ncs-device-type "netconf";
      tailf:display-when "not(../../../../../../../../../../../ncs:module) or ../../../../../../../../../../../ncs:module[ncs:name='ciena-openconfig-aaa'] or (../../../../../../../../../../../ncs:live-status-protocol[not(ncs:capability)]) or (../../../../../../../../../../../ncs:live-status-protocol/ncs:capability/ncs:module[.='ciena-openconfig-aaa'])";
      type oc-yang:live_ncs_counter64;
      description
        "The number of RADIUS packets of unknown type which were received from this server
         on the authentication port.";
    }
    leaf packets-dropped {
      tailf:ncs-device-type "netconf";
      tailf:display-when "not(../../../../../../../../../../../ncs:module) or ../../../../../../../../../../../ncs:module[ncs:name='ciena-openconfig-aaa'] or (../../../../../../../../../../../ncs:live-status-protocol[not(ncs:capability)]) or (../../../../../../../../../../../ncs:live-status-protocol/ncs:capability/ncs:module[.='ciena-openconfig-aaa'])";
      type oc-yang:live_ncs_counter64;
      description
        "The number of RADIUS packets which were received from this server on the authentication
         port and dropped for some other reason.";
    }
    leaf round-trip-time {
      tailf:ncs-device-type "netconf";
      tailf:display-when "not(../../../../../../../../../../../ncs:module) or ../../../../../../../../../../../ncs:module[ncs:name='ciena-openconfig-aaa'] or (../../../../../../../../../../../ncs:live-status-protocol[not(ncs:capability)]) or (../../../../../../../../../../../ncs:live-status-protocol/ncs:capability/ncs:module[.='ciena-openconfig-aaa'])";
      type yang:timeticks;
      description
        "The time interval (in hundredths of a second) between the most
         recent Access-Reply/Access-Challenge and the Access-Request that
         matched it from this RADIUS server.";
    }
  }

  identity RADIUS {
    base AUTHEN_PVDR_TYPE;
    description
      "Built-in type for radius authentication";
    reference "";
  }

  identity TACACS {
    base AUTHEN_PVDR_TYPE;
    description
      "Built-in type for tacacs authentication";
    reference "";
  }

  identity LOCAL {
    base AUTHEN_PVDR_TYPE;
    description
      "Built-in type for local authentication";
    reference "";
  }

  identity AUTHEN_PVDR_TYPE {
    description
      "Base authentication provider type";
    reference "";
  }
}
