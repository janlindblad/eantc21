module ciena-software-mgmt-augmentation {
  // Generated by yanger -t ncs
  tailf:mount-id "saos1051-nc-1.0:saos1051-nc-1.0";
  tailf:ncs-device-type "netconf";

  namespace "http://www.ciena.com/ns/yang/ciena-software-mgmt-aug";
  prefix ciena-software-management-aug;

  import ciena-software-mgmt {
    prefix software-mgmt;
  }
  import ietf-yang-types {
    prefix yang;
  }
  import ciena-packet-xcvr {
    prefix xcvr;
  }
  import tailf-common {
    prefix tailf;
  }
  import tailf-ncs {
    prefix ncs;
  }

  revision 2020-02-17 {
    description
      "Defined swtype-id grouping and added into software download,
       activate, install, remove rpcs.
       Defined xcvr-id-leafref-type typedef.
       Added leaf-list xcvr-id into software activate and install rpcs.
       Defined software-upgrade-status typedef.
       Added software-state-cfp2-dco-firmware container to software-state.
       Added software-state-pon-ctrl-onu-firmware container to software-state.
       Added description to the package-verification-data grouping.
       Added description to the hash-algorithm leaf.";
  }
  revision 2019-09-30 {
    description
      "Initial revision.";
  }

  typedef ncs_template_software-upgrade-status {
    type string;
    description
      "Software upgrade state";
  }

  typedef ncs_template_software-type {
    type string;
    description
      "Enumerated value identifying the type of software being specified in an rpc.";
  }

  typedef ncs_template_xcvr-id-leafref-type {
    type string;
    description
      "Software xcvr-id leafref type.";
  }

  typedef ncs_rpc_notif_software-upgrade-status {
    type enumeration {
      enum "invalid" {
        description
          "Invalid";
      }
      enum "idle" {
        description
          "Idle";
      }
      enum "not-applicable" {
        description
          "Not applicable";
      }
      enum "upgrading" {
        description
          "Upgrading";
      }
      enum "verification-failure" {
        description
          "Verification failure";
      }
      enum "upgrade-successful" {
        description
          "Upgrade successful";
      }
      enum "upgrade-failure" {
        description
          "Upgrade failure";
      }
    }
    description
      "Software upgrade state";
  }

  typedef ncs_rpc_notif_software-type {
    type enumeration {
      enum "package-manifest" {
        description
          "Device software package manifest.";
      }
      enum "cfp2-dco-firmware" {
        description
          "Firmware for CFP2 DCO transceiver.";
      }
      enum "pon-ctrl-onu-firmware" {
        description
          "Firmware for PON ONU module.";
      }
    }
    description
      "Enumerated value identifying the type of software being specified in an rpc.";
  }

  typedef ncs_rpc_notif_xcvr-id-leafref-type {
    type string;
    description
      "Software xcvr-id leafref type.";
  }

  typedef live_ncs_software-upgrade-status {
    type enumeration {
      enum "invalid" {
        description
          "Invalid";
      }
      enum "idle" {
        description
          "Idle";
      }
      enum "not-applicable" {
        description
          "Not applicable";
      }
      enum "upgrading" {
        description
          "Upgrading";
      }
      enum "verification-failure" {
        description
          "Verification failure";
      }
      enum "upgrade-successful" {
        description
          "Upgrade successful";
      }
      enum "upgrade-failure" {
        description
          "Upgrade failure";
      }
    }
    description
      "Software upgrade state";
  }

  typedef live_ncs_software-type {
    type enumeration {
      enum "package-manifest" {
        description
          "Device software package manifest.";
      }
      enum "cfp2-dco-firmware" {
        description
          "Firmware for CFP2 DCO transceiver.";
      }
      enum "pon-ctrl-onu-firmware" {
        description
          "Firmware for PON ONU module.";
      }
    }
    description
      "Enumerated value identifying the type of software being specified in an rpc.";
  }

  typedef live_ncs_xcvr-id-leafref-type {
    type leafref {
      path "/ncs:devices/ncs:device/ncs:live-status/xcvr:xcvrs/xcvr:xcvr/xcvr:xcvr-id" {
        tailf:xpath-root 3;
      }
    }
    description
      "Software xcvr-id leafref type.";
  }

  typedef software-upgrade-status {
    type enumeration {
      enum "invalid" {
        description
          "Invalid";
      }
      enum "idle" {
        description
          "Idle";
      }
      enum "not-applicable" {
        description
          "Not applicable";
      }
      enum "upgrading" {
        description
          "Upgrading";
      }
      enum "verification-failure" {
        description
          "Verification failure";
      }
      enum "upgrade-successful" {
        description
          "Upgrade successful";
      }
      enum "upgrade-failure" {
        description
          "Upgrade failure";
      }
    }
    description
      "Software upgrade state";
  }

  typedef software-type {
    type enumeration {
      enum "package-manifest" {
        description
          "Device software package manifest.";
      }
      enum "cfp2-dco-firmware" {
        description
          "Firmware for CFP2 DCO transceiver.";
      }
      enum "pon-ctrl-onu-firmware" {
        description
          "Firmware for PON ONU module.";
      }
    }
    description
      "Enumerated value identifying the type of software being specified in an rpc.";
  }

  typedef xcvr-id-leafref-type {
    type leafref {
      path "/ncs:devices/ncs:device/ncs:config/xcvr:xcvrs/xcvr:xcvr/xcvr:xcvr-id" {
        tailf:xpath-root 3;
      }
    }
    description
      "Software xcvr-id leafref type.";
  }

  grouping ncs_template_package-verification-data {
    leaf hash-algorithm {
      type string;
      // NCS drop default statement
      description
        "Hash algorithm corresponding to the hash-value.";
    }
    leaf hash-value {
      type string;
      description
        "Hex-encoded hash value used to verify the the package.";
    }
    description
      "Grouping of data containing hash verification data used by s/w operations.";
  }

  grouping ncs_template_swtype-id {
    leaf sw-type {
      type ncs_template_software-type;
      // NCS drop default statement
      description
        "Type of software used by the rpc";
    }
    description
      "Grouping of software identifier information used by an rpc.";
  }

  grouping ncs_rpc_notif_package-verification-data {
    leaf hash-algorithm {
      type identityref {
        base hash-algorithm;
      }
      default "sha-256";
      description
        "Hash algorithm corresponding to the hash-value.";
    }
    leaf hash-value {
      type yang:hex-string;
      description
        "Hex-encoded hash value used to verify the the package.";
    }
    description
      "Grouping of data containing hash verification data used by s/w operations.";
  }

  grouping ncs_rpc_notif_swtype-id {
    leaf sw-type {
      type ncs_rpc_notif_software-type;
      default "package-manifest";
      description
        "Type of software used by the rpc";
    }
    description
      "Grouping of software identifier information used by an rpc.";
  }

  grouping live_ncs_package-verification-data {
    leaf hash-algorithm {
      type identityref {
        base hash-algorithm;
      }
      // NCS drop default statement
      description
        "Hash algorithm corresponding to the hash-value.";
    }
    leaf hash-value {
      type yang:hex-string;
      description
        "Hex-encoded hash value used to verify the the package.";
    }
    description
      "Grouping of data containing hash verification data used by s/w operations.";
  }

  grouping live_ncs_swtype-id {
    leaf sw-type {
      type live_ncs_software-type;
      // NCS drop default statement
      description
        "Type of software used by the rpc";
    }
    description
      "Grouping of software identifier information used by an rpc.";
  }

  grouping package-verification-data {
    leaf hash-algorithm {
      type identityref {
        base hash-algorithm;
      }
      default "sha-256";
      description
        "Hash algorithm corresponding to the hash-value.";
    }
    leaf hash-value {
      type yang:hex-string;
      description
        "Hex-encoded hash value used to verify the the package.";
    }
    description
      "Grouping of data containing hash verification data used by s/w operations.";
  }

  grouping swtype-id {
    leaf sw-type {
      type software-type;
      default "package-manifest";
      description
        "Type of software used by the rpc";
    }
    description
      "Grouping of software identifier information used by an rpc.";
  }

  augment "/ncs:devices/ncs:device/ncs:rpc/software-mgmt:rpc-software-download/software-mgmt:software-download/software-mgmt:input" {
    description
      "Augmentation of software-download to include package-verification-data
       to support validation of package file downloads.";
    uses ncs_rpc_notif_package-verification-data;
  }
  augment "/ncs:devices/ncs:device/ncs:rpc/software-mgmt:rpc-software-install/software-mgmt:software-install/software-mgmt:input" {
    description
      "Augmentation of software-install to include package-verification-data
       to support validation of package file downloads.";
    uses ncs_rpc_notif_package-verification-data;
  }
  augment "/ncs:devices/ncs:device/ncs:live-status/software-mgmt:software-state" {
    description
      "Augmentation of the software-state container to add a container
       that contains state information specific to cfp2-dco-firmware.";
    container software-state-cfp2-dco-firmware {
      tailf:ncs-device-type "netconf";
      tailf:display-when "not(../../../ncs:module) or ../../../ncs:module[ncs:name='ciena-software-mgmt-augmentation'] or (../../../ncs:live-status-protocol[not(ncs:capability)]) or (../../../ncs:live-status-protocol/ncs:capability/ncs:module[.='ciena-software-mgmt-augmentation'])";
      description
        "Software information related to the management of firmware
         associated with cfp2-dco-firmware swtype.";
      list xcvr-software-state {
        key "xcvr-id";
        leaf xcvr-id {
          type live_ncs_xcvr-id-leafref-type;
          description
            "Reference to xcvr-id.";
        }
        leaf running-image-version {
          type string;
          description
            "Version of cfp2-dco-firmware currently running on the xcvr.";
        }
        leaf upgrade-status {
          type ciena-software-management-aug:live_ncs_software-upgrade-status;
          description
            "The current status of firmware upgrade operation on the xcvr.";
        }
        leaf upgrade-image {
          type string;
          description
            "Name of cfp2-dco-firmware image corresponding to the upgrade-status of the xcvr.";
        }
        description
          "List of xcvrs providing current firmware version and upgrade status.";
      }
      leaf-list downloaded-image {
        type string;
        description
          "Name of downloaded cfp2-dco-firmware image.";
      }
      leaf-list preloaded-image {
        type string;
        description
          "Name of pre-loaded cfp2-dco-firmware image.";
      }
    }
  }
  augment "/ncs:devices/ncs:device/ncs:live-status/software-mgmt:software-state" {
    description
      "Augmentation of the software-state container to add a container
       that contains state information specific to pon-ctrl-onu-firmware.";
    container software-state-pon-ctrl-onu-firmware {
      tailf:ncs-device-type "netconf";
      tailf:display-when "not(../../../ncs:module) or ../../../ncs:module[ncs:name='ciena-software-mgmt-augmentation'] or (../../../ncs:live-status-protocol[not(ncs:capability)]) or (../../../ncs:live-status-protocol/ncs:capability/ncs:module[.='ciena-software-mgmt-augmentation'])";
      description
        "Software information related to the management of firmware
         associated with pon-ctrl-onu-firmware swtype.";
      leaf-list downloaded-image {
        type string;
        description
          "Name of downloaded pon-ctrl-onu-firmware image.";
      }
    }
  }
  augment "/ncs:devices/ncs:device/ncs:rpc/software-mgmt:rpc-software-activate/software-mgmt:software-activate/software-mgmt:input" {
    description
      "Augmentation of software-activate rpc to include additional input
       parameters that are specific to the type of software that is being
       activated.";
    uses ncs_rpc_notif_swtype-id;
    leaf-list xcvr-id {
      // NCS dropped bad when statement - YANG_ERR_XPATH_BAD_REF
      type ncs_rpc_notif_xcvr-id-leafref-type;
      description
        "Reference to xcvr-id.";
    }
  }
  augment "/ncs:devices/ncs:device/ncs:rpc/software-mgmt:rpc-software-download/software-mgmt:software-download/software-mgmt:input" {
    description
      "Augmentation of software-download rpc to include additional input
       parameters that are specific to the type of software that is being
       downloaded.";
    uses ncs_rpc_notif_swtype-id;
  }
  augment "/ncs:devices/ncs:device/ncs:rpc/software-mgmt:rpc-software-install/software-mgmt:software-install/software-mgmt:input" {
    description
      "Augmentation of software-install rpc to include additional input
       parameters that are specific to the type of software that is being
       installed.";
    uses ncs_rpc_notif_swtype-id;
    leaf-list xcvr-id {
      // NCS dropped bad when statement - YANG_ERR_XPATH_BAD_REF
      type ncs_rpc_notif_xcvr-id-leafref-type;
      description
        "Reference to xcvr-id.";
    }
  }
  augment "/ncs:devices/ncs:device/ncs:rpc/software-mgmt:rpc-software-remove/software-mgmt:software-remove/software-mgmt:input" {
    description
      "Augmentation of software-remove rpc to include additional input
       parameters that are specific to the type of software that is being
       removed.";
    uses ncs_rpc_notif_swtype-id;
  }

  identity sha-256 {
    base hash-algorithm;
    description
      "The SHA-256 algorithm.";
    reference "RFC 6234: US Secure Hash Algorithms";
  }

  identity hash-algorithm {
    description
      "A base identity for hash algorithm verification.";
  }
}
