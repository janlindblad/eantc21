module ciena-pon-ctrl {
  // Generated by yanger -t ncs
  tailf:mount-id "saos1051-nc-1.0:saos1051-nc-1.0";
  tailf:ncs-device-type "netconf";

  namespace "http://www.ciena.com/ns/yang/ciena-pon-ctrl";
  prefix pon-ctrl;

  import ciena-types {
    prefix ciena;
  }
  import ietf-yang-types {
    prefix yang;
  }
  import openconfig-interfaces {
    prefix oc-if;
  }
  import ciena-openconfig-interfaces {
    prefix cn-if;
  }
  import ciena-mef-fp {
    prefix mef-fp;
  }
  import ciena-packet-typedefs {
    prefix cntypes;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data model for the management of Passive
     Optical Network (PON) devices. This includes Optical Line Terminals (OLTs) and
     subtended Optical Network Units (ONUs).

     Copyright (c) 2019 Ciena Corporation. All rights reserved.

     All information contained herein is, and remains the property of Ciena
     Corporation. Dissemination of this information or reproduction of this
     material is strictly forbidden unless prior written permission is obtained
     from Ciena Corporation.";

  revision 2020-08-20 {
    description
      "Add ONU diagnostic data container.
       Add OLT diagnostic data container.
       Update Datalink configuration to specify 'add-ctag' PCP and VLAN-ID list.
       Add expected-firmware-version to ONU state.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-06-25 {
    description
      "Add ONU UNI port configuration and state containers.
       Add RPC for ONU admission control.
       Add default values for SLA Profile.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-05-04 {
    description
      "Add unknown state to olt-oper-state and onu-oper-state enums";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-01-20 {
    description
      "Add RPCs for OLT/ONU firmware upgrade.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2019-09-16 {
    description
      "Restructure and rename Network configuration objects.";
    reference
      "- ITU-T G.987  : 10-Gigabit-capable passive optical networks (XG-PON)
       - IEEE 802.3av : 10Gbit/s Ethernet PON (10G EPON) standard";
  }
  revision 2019-05-01 {
    description
      "Initial version.";
    reference
      "- ITU-T G.987  : 10-Gigabit-capable passive optical networks (XG-PON)
       - IEEE 802.3av : 10Gbit/s Ethernet PON (10G EPON) standard";
  }

  typedef ncs_template_name-string {
    type string;
    description
      "Name string type.";
  }

  typedef ncs_template_interface-ref {
    type oc-if:ncs_template_base-interface-ref;
    description
      "L3 Interface reference type.";
  }

  typedef ncs_template_olt-ref {
    type string;
    description
      "OLT reference leafref type.";
  }

  typedef ncs_template_onu-ref {
    type string;
    description
      "ONU reference leafref type.";
  }

  typedef ncs_template_datalink-ref {
    type string;
    description
      "Datalink reference leafref type.";
  }

  typedef ncs_template_uni-port-ref {
    type string;
    description
      "UNI port reference leafref type.";
  }

  typedef ncs_template_sla-profile-ref {
    type string;
    description
      "SLA profile reference leafref type.";
  }

  typedef ncs_template_tpid {
    type string;
    description
      "TPID type.";
  }

  typedef ncs_template_pon-mode {
    type string;
    description
      "PON-mode type.";
  }

  typedef ncs_template_encryption-mode {
    type string;
    description
      "Encryption mode type.";
  }

  typedef ncs_template_olt-oper-state {
    type string;
    description
      "OLT operational state type.";
  }

  typedef ncs_template_onu-oper-state {
    type string;
    description
      "ONU operational state type.";
  }

  typedef ncs_template_uni-port-oper-state {
    type string;
    description
      "UNI port operational state type.";
  }

  typedef ncs_template_uni-port-speed {
    type string;
    description
      "UNI port speed type.";
  }

  typedef ncs_template_uni-port-duplex {
    type string;
    description
      "UNI port duplex type.";
  }

  typedef ncs_template_tag-match-vid {
    type string;
    description
      "VLAN-ID type used for network tag match fields.
       A value of 0 matches on no VLAN tag or a priority tag.
       A value of 65535 matches on any VID value, no VLAN tag or a priority tag.";
  }

  typedef ncs_template_tag-action {
    type string;
    description
      "Tag action type.";
  }

  typedef ncs_rpc_notif_name-string {
    type string {
      length "1..64";
    }
    description
      "Name string type.";
  }

  typedef ncs_rpc_notif_interface-ref {
    type oc-if:ncs_rpc_notif_base-interface-ref;
    description
      "L3 Interface reference type.";
  }

  typedef ncs_rpc_notif_olt-ref {
    type string;
    description
      "OLT reference leafref type.";
  }

  typedef ncs_rpc_notif_onu-ref {
    type string;
    description
      "ONU reference leafref type.";
  }

  typedef ncs_rpc_notif_datalink-ref {
    type string;
    description
      "Datalink reference leafref type.";
  }

  typedef ncs_rpc_notif_uni-port-ref {
    type string;
    description
      "UNI port reference leafref type.";
  }

  typedef ncs_rpc_notif_sla-profile-ref {
    type string;
    description
      "SLA profile reference leafref type.";
  }

  typedef ncs_rpc_notif_tpid {
    type enumeration {
      enum "0x8100" {
        value 33024;
        description
          "TPID 0x8100.";
      }
      enum "0x88a8" {
        value 34984;
        description
          "TPID 0x88a8.";
      }
    }
    description
      "TPID type.";
  }

  typedef ncs_rpc_notif_pon-mode {
    type enumeration {
      enum "xgs-pon" {
        description
          "XGS-PON mode.";
      }
      enum "10g-epon" {
        description
          "10G-EPON mode.";
      }
    }
    description
      "PON-mode type.";
  }

  typedef ncs_rpc_notif_encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef ncs_rpc_notif_olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef ncs_rpc_notif_onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
    }
    description
      "ONU operational state type.";
  }

  typedef ncs_rpc_notif_uni-port-oper-state {
    type enumeration {
      enum "up" {
        description
          "UNI port link state is up.";
      }
      enum "down" {
        description
          "UNI port link state is down.";
      }
      enum "unknown" {
        description
          "UNI port link state is unknown.";
      }
    }
    description
      "UNI port operational state type.";
  }

  typedef ncs_rpc_notif_uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI port speed is unknown.";
      }
    }
    description
      "UNI port speed type.";
  }

  typedef ncs_rpc_notif_uni-port-duplex {
    type enumeration {
      enum "auto" {
        description
          "Auto-configure duplex.";
      }
      enum "full" {
        description
          "Full duplex.";
      }
      enum "half" {
        description
          "Half duplex.";
      }
      enum "unknown" {
        description
          "UNI port duplex is unknown.";
      }
    }
    description
      "UNI port duplex type.";
  }

  typedef ncs_rpc_notif_tag-match-vid {
    type uint32 {
      range "0..4094 | 65535";
    }
    description
      "VLAN-ID type used for network tag match fields.
       A value of 0 matches on no VLAN tag or a priority tag.
       A value of 65535 matches on any VID value, no VLAN tag or a priority tag.";
  }

  typedef ncs_rpc_notif_tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  typedef live_ncs_name-string {
    type string {
      length "1..64";
    }
    description
      "Name string type.";
  }

  typedef live_ncs_interface-ref {
    type oc-if:live_ncs_base-interface-ref;
    description
      "L3 Interface reference type.";
  }

  typedef live_ncs_olt-ref {
    type leafref {
      path "/ncs:devices/ncs:device/ncs:live-status/pon-ctrl:pon-ctrl/pon-ctrl:olts/pon-ctrl:olt/pon-ctrl:name" {
        tailf:xpath-root 3;
      }
    }
    description
      "OLT reference leafref type.";
  }

  typedef live_ncs_onu-ref {
    type leafref {
      path "/ncs:devices/ncs:device/ncs:live-status/pon-ctrl:pon-ctrl/pon-ctrl:onus/pon-ctrl:onu/pon-ctrl:name" {
        tailf:xpath-root 3;
      }
    }
    description
      "ONU reference leafref type.";
  }

  typedef live_ncs_datalink-ref {
    type leafref {
      path "/ncs:devices/ncs:device/ncs:live-status/pon-ctrl:pon-ctrl/pon-ctrl:onus/pon-ctrl:onu/pon-ctrl:datalinks/pon-ctrl:datalink/pon-ctrl:name" {
        tailf:xpath-root 3;
      }
    }
    description
      "Datalink reference leafref type.";
  }

  typedef live_ncs_uni-port-ref {
    type leafref {
      path "/ncs:devices/ncs:device/ncs:live-status/pon-ctrl:pon-ctrl/pon-ctrl:onus/pon-ctrl:onu/pon-ctrl:uni-ports/pon-ctrl:uni-port/pon-ctrl:name" {
        tailf:xpath-root 3;
      }
    }
    description
      "UNI port reference leafref type.";
  }

  typedef live_ncs_sla-profile-ref {
    type leafref {
      path "/ncs:devices/ncs:device/ncs:live-status/pon-ctrl:pon-ctrl/pon-ctrl:sla-profiles/pon-ctrl:sla-profile/pon-ctrl:name" {
        tailf:xpath-root 3;
      }
    }
    description
      "SLA profile reference leafref type.";
  }

  typedef live_ncs_tpid {
    type enumeration {
      enum "0x8100" {
        value 33024;
        description
          "TPID 0x8100.";
      }
      enum "0x88a8" {
        value 34984;
        description
          "TPID 0x88a8.";
      }
    }
    description
      "TPID type.";
  }

  typedef live_ncs_pon-mode {
    type enumeration {
      enum "xgs-pon" {
        description
          "XGS-PON mode.";
      }
      enum "10g-epon" {
        description
          "10G-EPON mode.";
      }
    }
    description
      "PON-mode type.";
  }

  typedef live_ncs_encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef live_ncs_olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef live_ncs_onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
    }
    description
      "ONU operational state type.";
  }

  typedef live_ncs_uni-port-oper-state {
    type enumeration {
      enum "up" {
        description
          "UNI port link state is up.";
      }
      enum "down" {
        description
          "UNI port link state is down.";
      }
      enum "unknown" {
        description
          "UNI port link state is unknown.";
      }
    }
    description
      "UNI port operational state type.";
  }

  typedef live_ncs_uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI port speed is unknown.";
      }
    }
    description
      "UNI port speed type.";
  }

  typedef live_ncs_uni-port-duplex {
    type enumeration {
      enum "auto" {
        description
          "Auto-configure duplex.";
      }
      enum "full" {
        description
          "Full duplex.";
      }
      enum "half" {
        description
          "Half duplex.";
      }
      enum "unknown" {
        description
          "UNI port duplex is unknown.";
      }
    }
    description
      "UNI port duplex type.";
  }

  typedef live_ncs_tag-match-vid {
    type uint32 {
      range "0..4094 | 65535";
    }
    description
      "VLAN-ID type used for network tag match fields.
       A value of 0 matches on no VLAN tag or a priority tag.
       A value of 65535 matches on any VID value, no VLAN tag or a priority tag.";
  }

  typedef live_ncs_tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  typedef name-string {
    type string {
      length "1..64";
    }
    description
      "Name string type.";
  }

  typedef interface-ref {
    type oc-if:base-interface-ref;
    description
      "L3 Interface reference type.";
  }

  typedef olt-ref {
    type leafref {
      path "/ncs:devices/ncs:device/ncs:config/pon-ctrl:pon-ctrl/pon-ctrl:olts/pon-ctrl:olt/pon-ctrl:name" {
        tailf:xpath-root 3;
      }
    }
    description
      "OLT reference leafref type.";
  }

  typedef onu-ref {
    type leafref {
      path "/ncs:devices/ncs:device/ncs:config/pon-ctrl:pon-ctrl/pon-ctrl:onus/pon-ctrl:onu/pon-ctrl:name" {
        tailf:xpath-root 3;
      }
    }
    description
      "ONU reference leafref type.";
  }

  typedef datalink-ref {
    type leafref {
      path "/ncs:devices/ncs:device/ncs:config/pon-ctrl:pon-ctrl/pon-ctrl:onus/pon-ctrl:onu/pon-ctrl:datalinks/pon-ctrl:datalink/pon-ctrl:name" {
        tailf:xpath-root 3;
      }
    }
    description
      "Datalink reference leafref type.";
  }

  typedef uni-port-ref {
    type leafref {
      path "/ncs:devices/ncs:device/ncs:config/pon-ctrl:pon-ctrl/pon-ctrl:onus/pon-ctrl:onu/pon-ctrl:uni-ports/pon-ctrl:uni-port/pon-ctrl:name" {
        tailf:xpath-root 3;
      }
    }
    description
      "UNI port reference leafref type.";
  }

  typedef sla-profile-ref {
    type leafref {
      path "/ncs:devices/ncs:device/ncs:config/pon-ctrl:pon-ctrl/pon-ctrl:sla-profiles/pon-ctrl:sla-profile/pon-ctrl:name" {
        tailf:xpath-root 3;
      }
    }
    description
      "SLA profile reference leafref type.";
  }

  typedef tpid {
    type enumeration {
      enum "0x8100" {
        value 33024;
        description
          "TPID 0x8100.";
      }
      enum "0x88a8" {
        value 34984;
        description
          "TPID 0x88a8.";
      }
    }
    description
      "TPID type.";
  }

  typedef pon-mode {
    type enumeration {
      enum "xgs-pon" {
        description
          "XGS-PON mode.";
      }
      enum "10g-epon" {
        description
          "10G-EPON mode.";
      }
    }
    description
      "PON-mode type.";
  }

  typedef encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
    }
    description
      "ONU operational state type.";
  }

  typedef uni-port-oper-state {
    type enumeration {
      enum "up" {
        description
          "UNI port link state is up.";
      }
      enum "down" {
        description
          "UNI port link state is down.";
      }
      enum "unknown" {
        description
          "UNI port link state is unknown.";
      }
    }
    description
      "UNI port operational state type.";
  }

  typedef uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI port speed is unknown.";
      }
    }
    description
      "UNI port speed type.";
  }

  typedef uni-port-duplex {
    type enumeration {
      enum "auto" {
        description
          "Auto-configure duplex.";
      }
      enum "full" {
        description
          "Full duplex.";
      }
      enum "half" {
        description
          "Half duplex.";
      }
      enum "unknown" {
        description
          "UNI port duplex is unknown.";
      }
    }
    description
      "UNI port duplex type.";
  }

  typedef tag-match-vid {
    type uint32 {
      range "0..4094 | 65535";
    }
    description
      "VLAN-ID type used for network tag match fields.
       A value of 0 matches on no VLAN tag or a priority tag.
       A value of 65535 matches on any VID value, no VLAN tag or a priority tag.";
  }

  typedef tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  grouping ncs_template_tag-match-grouping {
    description
      "Tag match grouping";
    leaf match-stag {
      type pon-ctrl:ncs_template_tag-match-vid;
      // NCS drop mandatory statement
      description
        "Match on an 802.1ad tag. If present, this must be the first tag on the
         frame.";
    }
    leaf match-ctag-1 {
      type pon-ctrl:ncs_template_tag-match-vid;
      // NCS drop mandatory statement
      description
        "Match on an 802.1q tag. If present, this tag will be the first tag on the
         frame, or will be the first tag after an S-Tag.";
    }
    leaf match-ctag-2 {
      type pon-ctrl:ncs_template_tag-match-vid;
      // NCS drop mandatory statement
      description
        "Match on an 802.1q tag. If present, this tag will be last tag on the
         frame and will be after the S-Tag and C-Tag 1.";
    }
  }

  grouping ncs_template_tag-options-grouping {
    description
      "Tag options grouping";
    leaf tag-action {
      type pon-ctrl:ncs_template_tag-action;
      // NCS drop mandatory statement
      description
        "Tag action to perform on the matched frame.";
    }
    leaf tag-action-pop {
      // NCS drop when statement
      type string;
      // NCS drop mandatory statement
      description
        "Number of tags to pop.";
    }
    leaf tag-action-stag {
      // NCS drop when statement
      type pon-ctrl:ncs_template_tag-match-vid;
      // NCS drop must statement
      // NCS drop mandatory statement
      description
        "The 802.1ad tag to stamp or push.";
    }
    leaf tag-action-ctag {
      // NCS drop when statement
      type pon-ctrl:ncs_template_tag-match-vid;
      // NCS drop must statement
      // NCS drop mandatory statement
      description
        "The 802.1q tag to stamp or push.";
    }
  }

  grouping ncs_template_packet-counters-grouping {
    description
      "Packet counters grouping.";
    leaf rx-frames-total {
      type string;
      description
        "Total number of packets received.";
    }
    leaf tx-frames-total {
      type string;
      description
        "Total number of packets transmitted.";
    }
    leaf rx-frames-64 {
      type string;
      description
        "Count of 64-octet packets received on the interface.";
    }
    leaf tx-frames-64 {
      type string;
      description
        "Count of 64-octet packets transmitted on the interface.";
    }
    leaf rx-frames-65-127 {
      type string;
      description
        "Count of received packets on the interface with length 65 octets to 127
         octets.";
    }
    leaf tx-frames-65-127 {
      type string;
      description
        "Count of transmitted packets on the interface with length 65 octets to 127
         octets.";
    }
    leaf rx-frames-128-255 {
      type string;
      description
        "Count of received packets on the interface with length 128 octets to 255
         octets.";
    }
    leaf tx-frames-128-255 {
      type string;
      description
        "Count of transmitted packets on the interface with length 128 octets to 255
         octets.";
    }
    leaf rx-frames-256-511 {
      type string;
      description
        "Count of received packets on the interface with length 256 octets to 511
         octets.";
    }
    leaf tx-frames-256-511 {
      type string;
      description
        "Count of transmitted packets on the interface with length 256 octets to 511
         octets.";
    }
    leaf rx-frames-512-1023 {
      type string;
      description
        "Count of received packets on the interface with length 512 octets to 1023
         octets.";
    }
    leaf tx-frames-512-1023 {
      type string;
      description
        "Count of transmitted packets on the interface with length 512 octets to 1023
         octets.";
    }
    leaf rx-frames-1024-1518 {
      type string;
      description
        "Count of received packets on the interface with length 1024 octets to 1518
         octets.";
    }
    leaf tx-frames-1024-1518 {
      type string;
      description
        "Count of transmitted packets on the interface with length 1024 octets to 1518
         octets.";
    }
    leaf rx-frames-1519-plus {
      type string;
      description
        "Count of received packets on the interface with length 1519 octets up to the
         maximum size supported by the interface.";
    }
    leaf tx-frames-1519-plus {
      type string;
      description
        "Count of transmitted packets on the interface with length 1519 octets up to the
         maximum size supported by the interface.";
    }
  }

  grouping ncs_template_phy-counters-grouping {
    description
      "PHY/MAC counters grouping.";
    leaf rx-octets-total {
      type string;
      description
        "Total count of the number of octets that have been received.";
    }
    leaf tx-octets-total {
      type string;
      description
        "Total count of the number of octets that have been transmitted.";
    }
    leaf rx-encrypted-segments {
      type string;
      description
        "Count of encrypted segments received that were decrypted.";
    }
    leaf tx-encrypted-segments {
      type string;
      description
        "Count of encrypted segments transmitted.";
    }
    leaf rx-plain-segments {
      type string;
      description
        "Count of unencrypted segments received.";
    }
    leaf tx-plain-segments {
      type string;
      description
        "Count of unencrypted segments transmitted.";
    }
    leaf rx-bandwidth-reqs {
      type string;
      description
        "Number of bandwidth requests received.";
    }
    leaf tx-bandwidth-reqs {
      type string;
      description
        "Number of bandwidth requests transmitted.";
    }
    leaf rx-mpcp-ploam {
      type string;
      description
        "Number of PLOAM cells received.";
    }
    leaf tx-mpcp-ploam {
      type string;
      description
        "Number of PLOAM cells transmitted.";
    }
    leaf tx-upstream-slots {
      type string;
      description
        "Number of upstream slot grants issued (Allocations).";
    }
    leaf rx-filtered-frames {
      type string;
      description
        "Count of frames received but filtered (not forwarded).";
    }
    leaf rx-empty-slots {
      type string;
      description
        "Count of upstream slots in which data was not present.";
    }
    leaf rx-good-bip-blocks {
      type string;
      description
        "Count of BIP blocks received without error.";
    }
    leaf rx-errored-bip-blocks {
      type string;
      description
        "Count of BIP blocks received with error.";
    }
    leaf rx-errored-bip-bits {
      type string;
      description
        "Count of BIP bits received with error.";
    }
    leaf rx-hec-errors {
      type string;
      description
        "Number of errored Header Error Checksums in the XGEM header and GPON
         Framing.";
    }
    leaf rx-crc32-drops {
      type string;
      description
        "Count of segments dropped due to CRC-32 error.";
    }
    leaf rx-crc8-errors {
      type string;
      description
        "Count of received CRC-8 errors in XGS-PON Allocations/Bandwidth Requests.";
    }
    leaf rx-overflow-drops {
      type string;
      description
        "Count of segments dropped due to queue overlfow.";
    }
    leaf rx-too-short-drops {
      type string;
      description
        "Count of segments dropped due to being too short.";
    }
    leaf rx-too-long-drops {
      type string;
      description
        "Count of segments dropped due to being too long.";
    }
  }

  grouping ncs_rpc_notif_tag-match-grouping {
    description
      "Tag match grouping";
    leaf match-stag {
      type pon-ctrl:ncs_rpc_notif_tag-match-vid;
      mandatory true;
      description
        "Match on an 802.1ad tag. If present, this must be the first tag on the
         frame.";
    }
    leaf match-ctag-1 {
      type pon-ctrl:ncs_rpc_notif_tag-match-vid;
      mandatory true;
      description
        "Match on an 802.1q tag. If present, this tag will be the first tag on the
         frame, or will be the first tag after an S-Tag.";
    }
    leaf match-ctag-2 {
      type pon-ctrl:ncs_rpc_notif_tag-match-vid;
      mandatory true;
      description
        "Match on an 802.1q tag. If present, this tag will be last tag on the
         frame and will be after the S-Tag and C-Tag 1.";
    }
  }

  grouping ncs_rpc_notif_tag-options-grouping {
    description
      "Tag options grouping";
    leaf tag-action {
      type pon-ctrl:ncs_rpc_notif_tag-action;
      mandatory true;
      description
        "Tag action to perform on the matched frame.";
    }
    leaf tag-action-pop {
      when "../tag-action = 'pop'" {
        tailf:xpath-root 3;
      }
      type uint8 {
        range "1..3";
      }
      mandatory true;
      description
        "Number of tags to pop.";
    }
    leaf tag-action-stag {
      when "(../tag-action = 'stamp' or ../tag-action = 'push')
and not(../tag-action-ctag)" {
        tailf:xpath-root 3;
      }
      type pon-ctrl:ncs_rpc_notif_tag-match-vid;
      must '. != 65535' {
        tailf:xpath-root 3;
        error-message "Illegal value for stag.";
      }
      mandatory true;
      description
        "The 802.1ad tag to stamp or push.";
    }
    leaf tag-action-ctag {
      when "(../tag-action = 'stamp' or ../tag-action = 'push')
and not(../tag-action-stag)" {
        tailf:xpath-root 3;
      }
      type pon-ctrl:ncs_rpc_notif_tag-match-vid;
      must '. != 65535' {
        tailf:xpath-root 3;
        error-message "Illegal value for ctag.";
      }
      mandatory true;
      description
        "The 802.1q tag to stamp or push.";
    }
  }

  grouping ncs_rpc_notif_packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping ncs_rpc_notif_phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping live_ncs_tag-match-grouping {
    description
      "Tag match grouping";
    leaf match-stag {
      type pon-ctrl:live_ncs_tag-match-vid;
      // NCS drop mandatory statement
      description
        "Match on an 802.1ad tag. If present, this must be the first tag on the
         frame.";
    }
    leaf match-ctag-1 {
      type pon-ctrl:live_ncs_tag-match-vid;
      // NCS drop mandatory statement
      description
        "Match on an 802.1q tag. If present, this tag will be the first tag on the
         frame, or will be the first tag after an S-Tag.";
    }
    leaf match-ctag-2 {
      type pon-ctrl:live_ncs_tag-match-vid;
      // NCS drop mandatory statement
      description
        "Match on an 802.1q tag. If present, this tag will be last tag on the
         frame and will be after the S-Tag and C-Tag 1.";
    }
  }

  grouping live_ncs_tag-options-grouping {
    description
      "Tag options grouping";
    leaf tag-action {
      type pon-ctrl:live_ncs_tag-action;
      // NCS drop mandatory statement
      description
        "Tag action to perform on the matched frame.";
    }
    leaf tag-action-pop {
      // NCS drop when statement
      type uint8 {
        range "1..3";
      }
      // NCS drop mandatory statement
      description
        "Number of tags to pop.";
    }
    leaf tag-action-stag {
      // NCS drop when statement
      type pon-ctrl:live_ncs_tag-match-vid;
      // NCS drop must statement
      // NCS drop mandatory statement
      description
        "The 802.1ad tag to stamp or push.";
    }
    leaf tag-action-ctag {
      // NCS drop when statement
      type pon-ctrl:live_ncs_tag-match-vid;
      // NCS drop must statement
      // NCS drop mandatory statement
      description
        "The 802.1q tag to stamp or push.";
    }
  }

  grouping live_ncs_packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping live_ncs_phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping tag-match-grouping {
    description
      "Tag match grouping";
    leaf match-stag {
      type pon-ctrl:tag-match-vid;
      mandatory true;
      description
        "Match on an 802.1ad tag. If present, this must be the first tag on the
         frame.";
    }
    leaf match-ctag-1 {
      type pon-ctrl:tag-match-vid;
      mandatory true;
      description
        "Match on an 802.1q tag. If present, this tag will be the first tag on the
         frame, or will be the first tag after an S-Tag.";
    }
    leaf match-ctag-2 {
      type pon-ctrl:tag-match-vid;
      mandatory true;
      description
        "Match on an 802.1q tag. If present, this tag will be last tag on the
         frame and will be after the S-Tag and C-Tag 1.";
    }
  }

  grouping tag-options-grouping {
    description
      "Tag options grouping";
    leaf tag-action {
      type pon-ctrl:tag-action;
      mandatory true;
      description
        "Tag action to perform on the matched frame.";
    }
    leaf tag-action-pop {
      when "../tag-action = 'pop'" {
        tailf:xpath-root 3;
      }
      type uint8 {
        range "1..3";
      }
      mandatory true;
      description
        "Number of tags to pop.";
    }
    leaf tag-action-stag {
      when "(../tag-action = 'stamp' or ../tag-action = 'push')
and not(../tag-action-ctag)" {
        tailf:xpath-root 3;
      }
      type pon-ctrl:tag-match-vid;
      must '. != 65535' {
        tailf:xpath-root 3;
        error-message "Illegal value for stag.";
      }
      mandatory true;
      description
        "The 802.1ad tag to stamp or push.";
    }
    leaf tag-action-ctag {
      when "(../tag-action = 'stamp' or ../tag-action = 'push')
and not(../tag-action-stag)" {
        tailf:xpath-root 3;
      }
      type pon-ctrl:tag-match-vid;
      must '. != 65535' {
        tailf:xpath-root 3;
        error-message "Illegal value for ctag.";
      }
      mandatory true;
      description
        "The 802.1q tag to stamp or push.";
    }
  }

  grouping packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  augment "/ncs:devices/ncs:device/ncs:rpc" {
    container rpc-pon-ctrl-onu-admission-control {
      tailf:ncs-device-type "netconf";
      tailf:display-when "not(../../ncs:module) or ../../ncs:module[ncs:name='ciena-pon-ctrl']";
      tailf:action pon-ctrl-onu-admission-control {
        tailf:actionpoint ncsproxy {
          tailf:internal;
        }
        description
          "Control whether an ONU is allowed to register or disallowed
           from registering on an OLT.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf registration-allowed {
            type boolean;
            mandatory true;
            description
              "When true, an ONU is allowed to register. When false,
               an ONU is disallowed from registering. An ONU that is
               disallowed from registering on the OLT will show up in
               a 'Deregistered' state with a deregister-reason of
               'Disallowed'. Note that disallowing an ONU from being
               admitted to the OLT does not persist over OLT
               reboots.";
          }
        }
        output {
          leaf status {
            type string;
            description
              "Status of the ONU admission control operation.";
          }
        }
      }
    }
  }
  augment "/ncs:devices/ncs:device-group/ncs:ned-id/ncs:rpc" {
    container rpc-pon-ctrl-onu-admission-control {
      tailf:ncs-device-type "netconf";
      tailf:display-when "/ncs:devices/ncs:device[ncs:name=current()/../../../ncs:member]/ncs:module[ncs:name='ciena-pon-ctrl']";
      tailf:action pon-ctrl-onu-admission-control {
        tailf:actionpoint ncsproxy {
          tailf:internal;
        }
        description
          "Control whether an ONU is allowed to register or disallowed
           from registering on an OLT.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf registration-allowed {
            type boolean;
            mandatory true;
            description
              "When true, an ONU is allowed to register. When false,
               an ONU is disallowed from registering. An ONU that is
               disallowed from registering on the OLT will show up in
               a 'Deregistered' state with a deregister-reason of
               'Disallowed'. Note that disallowing an ONU from being
               admitted to the OLT does not persist over OLT
               reboots.";
          }
        }
        output {
          container "device" {
            leaf "name" {
              type string;
            }
            leaf "info" {
              type string;
            }
            container "result" {
              leaf status {
                type string;
                description
                  "Status of the ONU admission control operation.";
              }
            }
          }
        }
      }
    }
  }
  augment "/ncs:devices/ncs:device/ncs:rpc" {
    container rpc-pon-ctrl-onu-firmware-activate {
      tailf:ncs-device-type "netconf";
      tailf:display-when "not(../../ncs:module) or ../../ncs:module[ncs:name='ciena-pon-ctrl']";
      tailf:action pon-ctrl-onu-firmware-activate {
        tailf:actionpoint ncsproxy {
          tailf:internal;
        }
        description
          "Activate the specified firmware version on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-version {
            type string;
            mandatory true;
            description
              "Version of firmware to activate on this ONU.
               Firmware must already be installed.";
          }
        }
        output {
          leaf status {
            type string;
            description
              "Status of the ONU firmware activate operation.";
          }
        }
      }
    }
  }
  augment "/ncs:devices/ncs:device-group/ncs:ned-id/ncs:rpc" {
    container rpc-pon-ctrl-onu-firmware-activate {
      tailf:ncs-device-type "netconf";
      tailf:display-when "/ncs:devices/ncs:device[ncs:name=current()/../../../ncs:member]/ncs:module[ncs:name='ciena-pon-ctrl']";
      tailf:action pon-ctrl-onu-firmware-activate {
        tailf:actionpoint ncsproxy {
          tailf:internal;
        }
        description
          "Activate the specified firmware version on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-version {
            type string;
            mandatory true;
            description
              "Version of firmware to activate on this ONU.
               Firmware must already be installed.";
          }
        }
        output {
          container "device" {
            leaf "name" {
              type string;
            }
            leaf "info" {
              type string;
            }
            container "result" {
              leaf status {
                type string;
                description
                  "Status of the ONU firmware activate operation.";
              }
            }
          }
        }
      }
    }
  }
  augment "/ncs:devices/ncs:device/ncs:rpc" {
    container rpc-pon-ctrl-onu-firmware-install {
      tailf:ncs-device-type "netconf";
      tailf:display-when "not(../../ncs:module) or ../../ncs:module[ncs:name='ciena-pon-ctrl']";
      tailf:action pon-ctrl-onu-firmware-install {
        tailf:actionpoint ncsproxy {
          tailf:internal;
        }
        description
          "Install new firmware on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-file-name {
            type string;
            description
              "Name of the firmware file to install on this ONU.";
          }
          leaf defer-activation {
            type boolean;
            description
              "When true, ONU firmware activation is deferred until explicitly invoked.";
          }
        }
        output {
          leaf status {
            type string;
            description
              "Status of the ONU firmware install operation.";
          }
        }
      }
    }
  }
  augment "/ncs:devices/ncs:device-group/ncs:ned-id/ncs:rpc" {
    container rpc-pon-ctrl-onu-firmware-install {
      tailf:ncs-device-type "netconf";
      tailf:display-when "/ncs:devices/ncs:device[ncs:name=current()/../../../ncs:member]/ncs:module[ncs:name='ciena-pon-ctrl']";
      tailf:action pon-ctrl-onu-firmware-install {
        tailf:actionpoint ncsproxy {
          tailf:internal;
        }
        description
          "Install new firmware on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-file-name {
            type string;
            description
              "Name of the firmware file to install on this ONU.";
          }
          leaf defer-activation {
            type boolean;
            description
              "When true, ONU firmware activation is deferred until explicitly invoked.";
          }
        }
        output {
          container "device" {
            leaf "name" {
              type string;
            }
            leaf "info" {
              type string;
            }
            container "result" {
              leaf status {
                type string;
                description
                  "Status of the ONU firmware install operation.";
              }
            }
          }
        }
      }
    }
  }
  augment "/ncs:devices/ncs:device/ncs:rpc" {
    container rpc-pon-ctrl-olt-firmware-activate {
      tailf:ncs-device-type "netconf";
      tailf:display-when "not(../../ncs:module) or ../../ncs:module[ncs:name='ciena-pon-ctrl']";
      tailf:action pon-ctrl-olt-firmware-activate {
        tailf:actionpoint ncsproxy {
          tailf:internal;
        }
        description
          "Activate the specified firmware version on an OLT.";
        input {
          leaf olt {
            type pon-ctrl:ncs_rpc_notif_olt-ref;
            mandatory true;
            description
              "Name of the OLT.";
          }
          leaf firmware-version {
            type string;
            mandatory true;
            description
              "Version of firmware to activate on this OLT.
               Firmware must already be installed.";
          }
        }
        output {
          leaf status {
            type string;
            description
              "Status of the OLT firmware activate operation.";
          }
        }
      }
    }
  }
  augment "/ncs:devices/ncs:device-group/ncs:ned-id/ncs:rpc" {
    container rpc-pon-ctrl-olt-firmware-activate {
      tailf:ncs-device-type "netconf";
      tailf:display-when "/ncs:devices/ncs:device[ncs:name=current()/../../../ncs:member]/ncs:module[ncs:name='ciena-pon-ctrl']";
      tailf:action pon-ctrl-olt-firmware-activate {
        tailf:actionpoint ncsproxy {
          tailf:internal;
        }
        description
          "Activate the specified firmware version on an OLT.";
        input {
          leaf olt {
            type pon-ctrl:ncs_rpc_notif_olt-ref;
            mandatory true;
            description
              "Name of the OLT.";
          }
          leaf firmware-version {
            type string;
            mandatory true;
            description
              "Version of firmware to activate on this OLT.
               Firmware must already be installed.";
          }
        }
        output {
          container "device" {
            leaf "name" {
              type string;
            }
            leaf "info" {
              type string;
            }
            container "result" {
              leaf status {
                type string;
                description
                  "Status of the OLT firmware activate operation.";
              }
            }
          }
        }
      }
    }
  }
  augment "/ncs:devices/ncs:device/ncs:rpc" {
    container rpc-pon-ctrl-olt-firmware-install {
      tailf:ncs-device-type "netconf";
      tailf:display-when "not(../../ncs:module) or ../../ncs:module[ncs:name='ciena-pon-ctrl']";
      tailf:action pon-ctrl-olt-firmware-install {
        tailf:actionpoint ncsproxy {
          tailf:internal;
        }
        description
          "Install new firmware on an OLT.";
        input {
          leaf olt {
            type pon-ctrl:ncs_rpc_notif_olt-ref;
            mandatory true;
            description
              "Name of the OLT.";
          }
          leaf defer-activation {
            type boolean;
            description
              "When true, OLT firmware activation is deferred until explicitly invoked.";
          }
        }
        output {
          leaf status {
            type string;
            description
              "Status of the OLT firmware install operation.";
          }
        }
      }
    }
  }
  augment "/ncs:devices/ncs:device-group/ncs:ned-id/ncs:rpc" {
    container rpc-pon-ctrl-olt-firmware-install {
      tailf:ncs-device-type "netconf";
      tailf:display-when "/ncs:devices/ncs:device[ncs:name=current()/../../../ncs:member]/ncs:module[ncs:name='ciena-pon-ctrl']";
      tailf:action pon-ctrl-olt-firmware-install {
        tailf:actionpoint ncsproxy {
          tailf:internal;
        }
        description
          "Install new firmware on an OLT.";
        input {
          leaf olt {
            type pon-ctrl:ncs_rpc_notif_olt-ref;
            mandatory true;
            description
              "Name of the OLT.";
          }
          leaf defer-activation {
            type boolean;
            description
              "When true, OLT firmware activation is deferred until explicitly invoked.";
          }
        }
        output {
          container "device" {
            leaf "name" {
              type string;
            }
            leaf "info" {
              type string;
            }
            container "result" {
              leaf status {
                type string;
                description
                  "Status of the OLT firmware install operation.";
              }
            }
          }
        }
      }
    }
  }
  augment "/ncs:devices/ncs:device/ncs:rpc" {
    container rpc-pon-ctrl-onu-statistics-clear {
      tailf:ncs-device-type "netconf";
      tailf:display-when "not(../../ncs:module) or ../../ncs:module[ncs:name='ciena-pon-ctrl']";
      tailf:action pon-ctrl-onu-statistics-clear {
        tailf:actionpoint ncsproxy {
          tailf:internal;
        }
        description
          "Clear the statistics of an ONU, or the statistics
           of a Datalink on the ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            description
              "Name of the Datalink on the ONU.";
          }
        }
        output {
          leaf status {
            type string;
            description
              "Status of the statistics clear operation.";
          }
        }
      }
    }
  }
  augment "/ncs:devices/ncs:device-group/ncs:ned-id/ncs:rpc" {
    container rpc-pon-ctrl-onu-statistics-clear {
      tailf:ncs-device-type "netconf";
      tailf:display-when "/ncs:devices/ncs:device[ncs:name=current()/../../../ncs:member]/ncs:module[ncs:name='ciena-pon-ctrl']";
      tailf:action pon-ctrl-onu-statistics-clear {
        tailf:actionpoint ncsproxy {
          tailf:internal;
        }
        description
          "Clear the statistics of an ONU, or the statistics
           of a Datalink on the ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            description
              "Name of the Datalink on the ONU.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-olt-statistics-clear {
      tailf:ncs-device-type "netconf";
      tailf:display-when "not(../../ncs:module) or ../../ncs:module[ncs:name='ciena-pon-ctrl']";
      tailf:action pon-ctrl-olt-statistics-clear {
        tailf:actionpoint ncsproxy {
          tailf:internal;
        }
        description
          "Clear the statistics of an OLT.";
        input {
          leaf olt {
            type pon-ctrl:ncs_rpc_notif_olt-ref;
            mandatory true;
            description
              "Name of the OLT.";
          }
        }
        output {
          leaf status {
            type string;
            description
              "Status of the statistics clear operation.";
          }
        }
      }
    }
  }
  augment "/ncs:devices/ncs:device-group/ncs:ned-id/ncs:rpc" {
    container rpc-pon-ctrl-olt-statistics-clear {
      tailf:ncs-device-type "netconf";
      tailf:display-when "/ncs:devices/ncs:device[ncs:name=current()/../../../ncs:member]/ncs:module[ncs:name='ciena-pon-ctrl']";
      tailf:action pon-ctrl-olt-statistics-clear {
        tailf:actionpoint ncsproxy {
          tailf:internal;
        }
        description
          "Clear the statistics of an OLT.";
        input {
          leaf olt {
            type pon-ctrl:ncs_rpc_notif_olt-ref;
            mandatory true;
            description
              "Name of the OLT.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-onu-reset {
      tailf:ncs-device-type "netconf";
      tailf:display-when "not(../../ncs:module) or ../../ncs:module[ncs:name='ciena-pon-ctrl']";
      tailf:action pon-ctrl-onu-reset {
        tailf:actionpoint ncsproxy {
          tailf:internal;
        }
        description
          "Reset an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
        }
        output {
          leaf status {
            type string;
            description
              "Status of the ONU reset operation.";
          }
        }
      }
    }
  }
  augment "/ncs:devices/ncs:device-group/ncs:ned-id/ncs:rpc" {
    container rpc-pon-ctrl-onu-reset {
      tailf:ncs-device-type "netconf";
      tailf:display-when "/ncs:devices/ncs:device[ncs:name=current()/../../../ncs:member]/ncs:module[ncs:name='ciena-pon-ctrl']";
      tailf:action pon-ctrl-onu-reset {
        tailf:actionpoint ncsproxy {
          tailf:internal;
        }
        description
          "Reset an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
        }
        output {
          container "device" {
            leaf "name" {
              type string;
            }
            leaf "info" {
              type string;
            }
            container "result" {
              leaf status {
                type string;
                description
                  "Status of the ONU reset operation.";
              }
            }
          }
        }
      }
    }
  }
  augment "/ncs:devices/ncs:device/ncs:rpc" {
    container rpc-pon-ctrl-olt-reset {
      tailf:ncs-device-type "netconf";
      tailf:display-when "not(../../ncs:module) or ../../ncs:module[ncs:name='ciena-pon-ctrl']";
      tailf:action pon-ctrl-olt-reset {
        tailf:actionpoint ncsproxy {
          tailf:internal;
        }
        description
          "Reset an OLT.";
        input {
          leaf olt {
            type pon-ctrl:ncs_rpc_notif_olt-ref;
            mandatory true;
            description
              "Name of the OLT.";
          }
        }
        output {
          leaf status {
            type string;
            description
              "Status of the OLT reset operation.";
          }
        }
      }
    }
  }
  augment "/ncs:devices/ncs:device-group/ncs:ned-id/ncs:rpc" {
    container rpc-pon-ctrl-olt-reset {
      tailf:ncs-device-type "netconf";
      tailf:display-when "/ncs:devices/ncs:device[ncs:name=current()/../../../ncs:member]/ncs:module[ncs:name='ciena-pon-ctrl']";
      tailf:action pon-ctrl-olt-reset {
        tailf:actionpoint ncsproxy {
          tailf:internal;
        }
        description
          "Reset an OLT.";
        input {
          leaf olt {
            type pon-ctrl:ncs_rpc_notif_olt-ref;
            mandatory true;
            description
              "Name of the OLT.";
          }
        }
        output {
          container "device" {
            leaf "name" {
              type string;
            }
            leaf "info" {
              type string;
            }
            container "result" {
              leaf status {
                type string;
                description
                  "Status of the OLT reset operation.";
              }
            }
          }
        }
      }
    }
  }
  augment "/ncs:devices/ncs:device/ncs:netconf-notifications/ncs:received-notifications/ncs:notification/ncs:data" {
    container uni-port-oper-state-change {
      presence "";
      config false;
      description
        "Generated when the operational state of an ONU UNI port changes.";
      leaf olt {
        type pon-ctrl:ncs_rpc_notif_olt-ref;
        description
          "Name of the OLT.";
      }
      leaf onu {
        type pon-ctrl:ncs_rpc_notif_onu-ref;
        description
          "Name of the ONU.";
      }
      leaf uni-port {
        type pon-ctrl:ncs_rpc_notif_uni-port-ref;
        description
          "ID of the UNI port whose operational state has changed.";
      }
      leaf oper-state {
        type pon-ctrl:ncs_rpc_notif_uni-port-oper-state;
        description
          "Operational state of the UNI port.";
      }
      leaf speed {
        type pon-ctrl:ncs_rpc_notif_uni-port-speed;
        description
          "Operational speed of the UNI port
           Set when the oper-state of the ONU is 'up'.";
      }
      leaf duplex {
        type pon-ctrl:ncs_rpc_notif_uni-port-duplex;
        description
          "Operational duplex of the UNI port.
           Set when the oper-state of the ONU is 'up'.";
      }
    }
  }
  augment "/ncs:devices/ncs:device/ncs:netconf-notifications/ncs:received-notifications/ncs:notification/ncs:data" {
    container onu-oper-state-change {
      presence "";
      config false;
      description
        "Generated when the operational state of an ONU changes.";
      leaf olt {
        type pon-ctrl:ncs_rpc_notif_olt-ref;
        description
          "Name of the OLT.";
      }
      leaf onu {
        type pon-ctrl:ncs_rpc_notif_onu-ref;
        description
          "Name of the ONU whose operational state has changed.";
      }
      leaf oper-state {
        type pon-ctrl:ncs_rpc_notif_onu-oper-state;
        description
          "Operational state of the ONU.";
      }
      leaf deregister-reason {
        type string;
        description
          "The reason for the last ONU deregistration.
           Set when the oper-state of the ONU is 'deregistered'.";
      }
    }
  }
  augment "/ncs:devices/ncs:device/ncs:netconf-notifications/ncs:received-notifications/ncs:notification/ncs:data" {
    container olt-oper-state-change {
      presence "";
      config false;
      description
        "Generated when the operational state of an OLT changes.";
      leaf olt {
        type pon-ctrl:ncs_rpc_notif_olt-ref;
        description
          "Name of the OLT whose operational state has changed.";
      }
      leaf oper-state {
        type pon-ctrl:ncs_rpc_notif_olt-oper-state;
        description
          "Operational state of the OLT.";
      }
    }
  }
  augment "/ncs:devices/ncs:device/ncs:netconf-notifications/ncs:received-notifications/ncs:notification/ncs:data" {
    container onu-discovered {
      presence "";
      config false;
      description
        "Generated when a new ONU is discovered on an OLT and has not yet been configured.";
      leaf olt {
        type pon-ctrl:ncs_rpc_notif_olt-ref;
        description
          "Name of the OLT on which this ONU was discovered.";
      }
      leaf onu-serial-number {
        type string {
          pattern '[a-zA-Z]{4}[0-9a-fA-F]{8}';
        }
        description
          "The serial number of the discovered ONU.";
      }
    }
  }
  augment "/ncs:devices/ncs:device/ncs:netconf-notifications/ncs:received-notifications/ncs:notification/ncs:data" {
    container olt-discovered {
      presence "";
      config false;
      description
        "Generated when a new OLT is discovered on an interface and has not yet been configured.";
      leaf l3-interface {
        type pon-ctrl:ncs_rpc_notif_interface-ref;
        description
          "Name of the L3 interface on which this OLT was discovered.";
      }
      leaf olt-mac-address {
        type yang:mac-address;
        description
          "The MAC address of the discovered OLT.";
      }
    }
  }
  augment "/ncs:devices/ncs:device/ncs:config" {
    container pon-ctrl {
      tailf:ncs-device-type "netconf";
      tailf:display-when "not(../../ncs:module) or ../../ncs:module[ncs:name='ciena-pon-ctrl']";
      description
        "PON configuration data.";
      container olts {
        description
          "The configuration data for all OLTs.";
        list olt {
          key "name";
          description
            "List of OLTs.";
          leaf name {
            type pon-ctrl:name-string;
            description
              "Name of the OLT.";
          }
          leaf admin-state {
            type ciena:admin-state;
            default "enabled";
            description
              "Enable or disable the OLT.";
          }
          leaf mac-address {
            type yang:mac-address;
            mandatory true;
            description
              "The MAC address of the OLT.";
          }
          leaf management-interface {
            type pon-ctrl:interface-ref;
            // NCS dropped bad must statement - YANG_ERR_XPATH_BAD_REF
            mandatory true;
            description
              "Reference to the L3 interface on which this OLT is to be
               managed.";
          }
          leaf pon-mode {
            type pon-ctrl:pon-mode;
            default "xgs-pon";
            description
              "The PON mode this OLT will operate in.";
          }
          leaf auto-boot-mode {
            type ciena:admin-state;
            default "disabled";
            description
              "Enable or disable autonomous boot mode on the OLT.";
          }
          leaf upstream-fec-0 {
            when "../pon-mode = 'xgs-pon'" {
              tailf:xpath-root 3;
            }
            type ciena:admin-state;
            default "enabled";
            description
              "Enable or disable upstream FEC (Forward Error Correction)
               for burst profile 0 on the OLT in XGS-PON mode.";
          }
          leaf upstream-preamble-0 {
            when "../pon-mode = 'xgs-pon'" {
              tailf:xpath-root 3;
            }
            type uint16 {
              range "16..1000";
            }
            default "64";
            description
              "The amount of preamble at the start of burst for profile 0
               on the OLT in XGS-PON mode; measured in units of upstream slots (12.8ns).";
          }
          leaf downstream-fec {
            type ciena:admin-state;
            default "enabled";
            description
              "Enable or disable downstream FEC (Forward Error Correction) on the OLT.";
          }
          leaf encryption-mode {
            type pon-ctrl:encryption-mode;
            default "disabled";
            description
              "The encryption mode on the OLT.";
          }
          leaf guard-time {
            when "../pon-mode = 'xgs-pon'" {
              tailf:xpath-root 3;
            }
            type uint16 {
              range "16..1000";
            }
            default "16";
            description
              "The guard time used by the OLT in XGS-PON mode.
               This is the amount of dead time between upstream burst slots
               measured in units of upstream slots (12.8ns).";
          }
          leaf max-nni-frame-size {
            type uint16 {
              range "512..12500";
            }
            default "9600";
            description
              "The NNI port's MTU on the OLT.
               Maximum supported MTU is 9600 in XGS-PON mode and
               12500 in 10G-EPON mode.";
          }
          leaf max-pon-frame-size {
            type uint16 {
              range "512..12500";
            }
            default "9600";
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              key "name";
              description
                "List of NNI Networks.";
              leaf name {
                type pon-ctrl:name-string;
                description
                  "Name of the NNI Network.";
              }
              uses pon-ctrl:tag-match-grouping;
              uses pon-ctrl:tag-options-grouping;
            }
          }
        }
      }
      container onus {
        description
          "The configuration data for all ONUs.";
        list onu {
          key "name olt";
          description
            "List of ONUs.";
          leaf name {
            type pon-ctrl:name-string;
            description
              "Name of the ONU.";
          }
          leaf olt {
            type pon-ctrl:olt-ref;
            mandatory true;
            description
              "Name of the OLT this ONU is subtended from.";
          }
          leaf serial-number {
            type string {
              pattern '[a-zA-Z]{4}[0-9a-fA-F]{8}';
            }
            mandatory true;
            description
              "The serial number the OLT expects to retrieve from the ONU.";
          }
          container datalinks {
            description
              "The configuration data for all Datalinks.
               A datalink is an LLID in 10G-EPON mode or an XGEM port in XGS-PON mode.";
            list datalink {
              key "name";
              description
                "List of Datalinks.";
              leaf name {
                type pon-ctrl:name-string;
                description
                  "Name of the datalink.";
              }
              leaf admin-state {
                type ciena:admin-state;
                default "enabled";
                description
                  "Enable or disable traffic on this datalink.";
              }
              leaf-list uni-ports {
                type uint8 {
                  range "1..5";
                }
                min-elements 1;
                max-elements 5;
                description
                  "List of ONU UNI ports to apply the datalink on.";
              }
              leaf-list vlan-ids {
                type pon-ctrl:tag-match-vid;
                max-elements 12;
                description
                  "List of VLAN IDs to be forwarded on this datalink.
                   Traffic will only be allowed on this datalink if it matches
                   one of the values specified. Not specifying this field or
                   specifying a value of 65535 will match on any VID value,
                   no VLAN tag or a priority tag. Values specified must be unique
                   across all datalinks on the same UNI port.";
              }
              leaf sla-profile {
                type pon-ctrl:sla-profile-ref;
                mandatory true;
                description
                  "Name of the SLA profile this datalink implements.";
              }
              leaf add-ctag {
                type mef-fp:vlan-id;
                description
                  "Add an optional C-Tag at the ONU for all upstream traffic on this datalink.
                   This tag is popped (removed) in the downstream direction.";
              }
              leaf add-ctag-pcp {
                when '../add-ctag' {
                  tailf:xpath-root 3;
                }
                type uint8 {
                  range "0..7";
                }
                description
                  "Specify the 802.1p priority of the added C-Tag on this datalink.
                   This is only valid when the add-ctag parameter is specified.
                   When this field is not specified, a PCP value of 0 is assumed for
                   untagged frames. For tagged frames the PCP value of the added C-Tag
                   is copied from the existing VLAN.";
              }
            }
          }
          container pon-connections {
            description
              "The configuration data for all PON Connections.
               PON Connections are the configuration construct that links a Datalink on the ONU to
               an NNI Network on the OLT.";
            list pon-connection {
              key "name";
              description
                "List of PON Connections.";
              leaf name {
                type pon-ctrl:name-string;
                description
                  "Name of the PON Connection.";
              }
              leaf datalink {
                type leafref {
                  path "../../../datalinks/datalink/name";
                }
                mandatory true;
                description
                  "Reference to the datalink on the ONU.
                   Datalink must be configured on the same ONU as this PON Connection.";
              }
              leaf nni-network {
                type leafref {
                  path "/ncs:devices/ncs:device/ncs:config/pon-ctrl:pon-ctrl/pon-ctrl:olts/pon-ctrl:olt[name=current()/../../../olt]/pon-ctrl:nni-networks/pon-ctrl:nni-network/pon-ctrl:name" {
                    tailf:xpath-root 3;
                  }
                }
                mandatory true;
                description
                  "Reference to the NNI Network on the OLT.
                   NNI Network must be configured on the same OLT as the ONU where this PON Connection exists.";
              }
              uses pon-ctrl:tag-match-grouping;
              uses pon-ctrl:tag-options-grouping;
            }
          }
          container uni-ports {
            description
              "The configuration data for all UNI ports.
               This configuration construct is optional and can be used to modify specific UNI port parameters
               under this ONU.";
            list uni-port {
              key "name";
              max-elements 5;
              description
                "List of UNI ports.";
              leaf name {
                type pon-ctrl:name-string;
                description
                  "The numerical identifier of this UNI port.
                   Must be a numercical value between 1 and 5.";
              }
              leaf description {
                type pon-ctrl:name-string;
                description
                  "A string description of this UNI port.";
              }
              leaf admin-state {
                type ciena:admin-state;
                default "enabled";
                description
                  "Enable or disable the UNI port.";
              }
              leaf max-frame-size {
                type uint16 {
                  range "64..9216";
                }
                default "9216";
                description
                  "The UNI port's configured MTU.";
              }
              leaf speed {
                type pon-ctrl:uni-port-speed;
                must ". != 'unknown'" {
                  tailf:xpath-root 3;
                  error-message "Illegal value for speed.";
                }
                default "auto";
                description
                  "The UNI port's configured speed.";
              }
              leaf duplex {
                type pon-ctrl:uni-port-duplex;
                must ". != 'unknown'" {
                  tailf:xpath-root 3;
                  error-message "Illegal value for duplex.";
                }
                default "auto";
                description
                  "The UNI port's configured duplex.";
              }
            }
          }
        }
      }
      container sla-profiles {
        description
          "The configuration data for all SLA Profiles.";
        list sla-profile {
          key "name";
          description
            "List of SLA profiles.";
          leaf name {
            type pon-ctrl:name-string;
            description
              "Name of the SLA profile.";
          }
          leaf up-fixed-rate {
            type uint32 {
              range "0 | 128..8000000";
            }
            units "Kbps";
            default "0";
            description
              "Fixed grant rate in Kbps. This is an unsolicited
               grant by the DBA regardless of need.";
          }
          leaf up-guaranteed-rate {
            type uint32 {
              range "128..10000000";
            }
            units "Kbps";
            default "128";
            description
              "Guaranteed (high priority) upstream rate in Kbps.";
          }
          leaf up-guaranteed-max-burst {
            type uint32 {
              range "0..1000000";
            }
            units "Bytes";
            default "409600";
            description
              "Maximum upstream burst size in Bytes. The
               guaranteed rate is enforced at this burst size.";
          }
          leaf up-best-effort-rate {
            type uint32 {
              range "0..10000000";
            }
            units "Kbps";
            default "10000000";
            description
              "Best Effort (low priority) upstream rate in Kbps.";
          }
          leaf up-best-effort-max-burst {
            type uint32 {
              range "0..1000000";
            }
            units "Bytes";
            default "409600";
            description
              "Maximum upstream burst size in Bytes. The best
               effort rate is enforced at this burst size.";
          }
          leaf up-priority {
            type uint8 {
              range "1..8";
            }
            default "1";
            description
              "Priority level for the Guaranteed portion of the SLA.";
          }
          leaf up-service-limit {
            type uint16 {
              range "2..256";
            }
            units "kBytes";
            default "128";
            description
              "Maximum grant size for an upstream slot in Kilobytes.";
          }
          leaf up-min-grant-period {
            type uint16 {
              range "0..1000";
            }
            default "0";
            description
              "The minimum allowed spacing between grants on this service.";
          }
          leaf up-max-grant-period {
            type uint16 {
              range "3..1000";
            }
            default "10";
            description
              "The maximum allowed time between grants on
               this service. This field will cause a polling grant
               when the ONU is idle.";
          }
          leaf down-guaranteed-rate {
            type uint32 {
              range "128..10000000";
            }
            units "Kbps";
            default "128";
            description
              "Guaranteed (high priority) downstream rate in Kbps.";
          }
          leaf down-guaranteed-max-burst {
            type uint32 {
              range "0..1000000";
            }
            units "Bytes";
            default "409600";
            description
              "Maximum downstream burst size in Bytes. The
               guaranteed rate is enforced at this burst size.";
          }
          leaf down-best-effort-rate {
            type uint32 {
              range "0..10000000";
            }
            units "Kbps";
            default "10000000";
            description
              "Best Effort (low priority) downstream rate in Kbps.";
          }
          leaf down-best-effort-max-burst {
            type uint32 {
              range "0..1000000";
            }
            units "Bytes";
            default "409600";
            description
              "Maximum downstream burst size in Bytes. The best
               effort rate is enforced at this burst size.";
          }
        }
      }
    }
    // NCS drop config false container 'pon-ctrl-state'
  }
  augment "/ncs:devices/ncs:device/ncs:live-status" {
    container pon-ctrl {
      tailf:ncs-device-type "netconf";
      tailf:display-when "not(../../ncs:module) or ../../ncs:module[ncs:name='ciena-pon-ctrl'] or (../../ncs:live-status-protocol[not(ncs:capability)]) or (../../ncs:live-status-protocol/ncs:capability/ncs:module[.='ciena-pon-ctrl'])";
      description
        "PON configuration data.";
      container olts {
        description
          "The configuration data for all OLTs.";
        list olt {
          key "name";
          description
            "List of OLTs.";
          leaf name {
            type pon-ctrl:live_ncs_name-string;
            description
              "Name of the OLT.";
          }
          leaf admin-state {
            type ciena:live_ncs_admin-state;
            // NCS drop default statement
            description
              "Enable or disable the OLT.";
          }
          leaf mac-address {
            type yang:mac-address;
            // NCS drop mandatory statement
            description
              "The MAC address of the OLT.";
          }
          leaf management-interface {
            type pon-ctrl:live_ncs_interface-ref;
            // NCS drop must statement
            // NCS drop mandatory statement
            description
              "Reference to the L3 interface on which this OLT is to be
               managed.";
          }
          leaf pon-mode {
            type pon-ctrl:live_ncs_pon-mode;
            // NCS drop default statement
            description
              "The PON mode this OLT will operate in.";
          }
          leaf auto-boot-mode {
            type ciena:live_ncs_admin-state;
            // NCS drop default statement
            description
              "Enable or disable autonomous boot mode on the OLT.";
          }
          leaf upstream-fec-0 {
            // NCS drop when statement
            type ciena:live_ncs_admin-state;
            // NCS drop default statement
            description
              "Enable or disable upstream FEC (Forward Error Correction)
               for burst profile 0 on the OLT in XGS-PON mode.";
          }
          leaf upstream-preamble-0 {
            // NCS drop when statement
            type uint16 {
              range "16..1000";
            }
            // NCS drop default statement
            description
              "The amount of preamble at the start of burst for profile 0
               on the OLT in XGS-PON mode; measured in units of upstream slots (12.8ns).";
          }
          leaf downstream-fec {
            type ciena:live_ncs_admin-state;
            // NCS drop default statement
            description
              "Enable or disable downstream FEC (Forward Error Correction) on the OLT.";
          }
          leaf encryption-mode {
            type pon-ctrl:live_ncs_encryption-mode;
            // NCS drop default statement
            description
              "The encryption mode on the OLT.";
          }
          leaf guard-time {
            // NCS drop when statement
            type uint16 {
              range "16..1000";
            }
            // NCS drop default statement
            description
              "The guard time used by the OLT in XGS-PON mode.
               This is the amount of dead time between upstream burst slots
               measured in units of upstream slots (12.8ns).";
          }
          leaf max-nni-frame-size {
            type uint16 {
              range "512..12500";
            }
            // NCS drop default statement
            description
              "The NNI port's MTU on the OLT.
               Maximum supported MTU is 9600 in XGS-PON mode and
               12500 in 10G-EPON mode.";
          }
          leaf max-pon-frame-size {
            type uint16 {
              range "512..12500";
            }
            // NCS drop default statement
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              key "name";
              description
                "List of NNI Networks.";
              leaf name {
                type pon-ctrl:live_ncs_name-string;
                description
                  "Name of the NNI Network.";
              }
              uses pon-ctrl:live_ncs_tag-match-grouping;
              uses pon-ctrl:live_ncs_tag-options-grouping;
            }
          }
        }
      }
      container onus {
        description
          "The configuration data for all ONUs.";
        list onu {
          key "name olt";
          description
            "List of ONUs.";
          leaf name {
            type pon-ctrl:live_ncs_name-string;
            description
              "Name of the ONU.";
          }
          leaf olt {
            type pon-ctrl:live_ncs_olt-ref;
            // NCS drop mandatory statement
            description
              "Name of the OLT this ONU is subtended from.";
          }
          leaf serial-number {
            type string {
              pattern '[a-zA-Z]{4}[0-9a-fA-F]{8}';
            }
            // NCS drop mandatory statement
            description
              "The serial number the OLT expects to retrieve from the ONU.";
          }
          container datalinks {
            description
              "The configuration data for all Datalinks.
               A datalink is an LLID in 10G-EPON mode or an XGEM port in XGS-PON mode.";
            list datalink {
              key "name";
              description
                "List of Datalinks.";
              leaf name {
                type pon-ctrl:live_ncs_name-string;
                description
                  "Name of the datalink.";
              }
              leaf admin-state {
                type ciena:live_ncs_admin-state;
                // NCS drop default statement
                description
                  "Enable or disable traffic on this datalink.";
              }
              leaf-list uni-ports {
                type uint8 {
                  range "1..5";
                }
                // NCS drop min-elements statement
                // NCS drop max-elements statement
                description
                  "List of ONU UNI ports to apply the datalink on.";
              }
              leaf-list vlan-ids {
                type pon-ctrl:live_ncs_tag-match-vid;
                // NCS drop max-elements statement
                description
                  "List of VLAN IDs to be forwarded on this datalink.
                   Traffic will only be allowed on this datalink if it matches
                   one of the values specified. Not specifying this field or
                   specifying a value of 65535 will match on any VID value,
                   no VLAN tag or a priority tag. Values specified must be unique
                   across all datalinks on the same UNI port.";
              }
              leaf sla-profile {
                type pon-ctrl:live_ncs_sla-profile-ref;
                // NCS drop mandatory statement
                description
                  "Name of the SLA profile this datalink implements.";
              }
              leaf add-ctag {
                type mef-fp:live_ncs_vlan-id;
                description
                  "Add an optional C-Tag at the ONU for all upstream traffic on this datalink.
                   This tag is popped (removed) in the downstream direction.";
              }
              leaf add-ctag-pcp {
                // NCS drop when statement
                type uint8 {
                  range "0..7";
                }
                description
                  "Specify the 802.1p priority of the added C-Tag on this datalink.
                   This is only valid when the add-ctag parameter is specified.
                   When this field is not specified, a PCP value of 0 is assumed for
                   untagged frames. For tagged frames the PCP value of the added C-Tag
                   is copied from the existing VLAN.";
              }
            }
          }
          container pon-connections {
            description
              "The configuration data for all PON Connections.
               PON Connections are the configuration construct that links a Datalink on the ONU to
               an NNI Network on the OLT.";
            list pon-connection {
              key "name";
              description
                "List of PON Connections.";
              leaf name {
                type pon-ctrl:live_ncs_name-string;
                description
                  "Name of the PON Connection.";
              }
              leaf datalink {
                type leafref {
                  path "../../../datalinks/datalink/name";
                }
                // NCS drop mandatory statement
                description
                  "Reference to the datalink on the ONU.
                   Datalink must be configured on the same ONU as this PON Connection.";
              }
              leaf nni-network {
                type leafref {
                  path "/ncs:devices/ncs:device/ncs:live-status/pon-ctrl:pon-ctrl/pon-ctrl:olts/pon-ctrl:olt[name=current()/../../../olt]/pon-ctrl:nni-networks/pon-ctrl:nni-network/pon-ctrl:name" {
                    tailf:xpath-root 3;
                  }
                }
                // NCS drop mandatory statement
                description
                  "Reference to the NNI Network on the OLT.
                   NNI Network must be configured on the same OLT as the ONU where this PON Connection exists.";
              }
              uses pon-ctrl:live_ncs_tag-match-grouping;
              uses pon-ctrl:live_ncs_tag-options-grouping;
            }
          }
          container uni-ports {
            description
              "The configuration data for all UNI ports.
               This configuration construct is optional and can be used to modify specific UNI port parameters
               under this ONU.";
            list uni-port {
              key "name";
              // NCS drop max-elements statement
              description
                "List of UNI ports.";
              leaf name {
                type pon-ctrl:live_ncs_name-string;
                description
                  "The numerical identifier of this UNI port.
                   Must be a numercical value between 1 and 5.";
              }
              leaf description {
                type pon-ctrl:live_ncs_name-string;
                description
                  "A string description of this UNI port.";
              }
              leaf admin-state {
                type ciena:live_ncs_admin-state;
                // NCS drop default statement
                description
                  "Enable or disable the UNI port.";
              }
              leaf max-frame-size {
                type uint16 {
                  range "64..9216";
                }
                // NCS drop default statement
                description
                  "The UNI port's configured MTU.";
              }
              leaf speed {
                type pon-ctrl:live_ncs_uni-port-speed;
                // NCS drop must statement
                // NCS drop default statement
                description
                  "The UNI port's configured speed.";
              }
              leaf duplex {
                type pon-ctrl:live_ncs_uni-port-duplex;
                // NCS drop must statement
                // NCS drop default statement
                description
                  "The UNI port's configured duplex.";
              }
            }
          }
        }
      }
      container sla-profiles {
        description
          "The configuration data for all SLA Profiles.";
        list sla-profile {
          key "name";
          description
            "List of SLA profiles.";
          leaf name {
            type pon-ctrl:live_ncs_name-string;
            description
              "Name of the SLA profile.";
          }
          leaf up-fixed-rate {
            type uint32 {
              range "0 | 128..8000000";
            }
            units "Kbps";
            // NCS drop default statement
            description
              "Fixed grant rate in Kbps. This is an unsolicited
               grant by the DBA regardless of need.";
          }
          leaf up-guaranteed-rate {
            type uint32 {
              range "128..10000000";
            }
            units "Kbps";
            // NCS drop default statement
            description
              "Guaranteed (high priority) upstream rate in Kbps.";
          }
          leaf up-guaranteed-max-burst {
            type uint32 {
              range "0..1000000";
            }
            units "Bytes";
            // NCS drop default statement
            description
              "Maximum upstream burst size in Bytes. The
               guaranteed rate is enforced at this burst size.";
          }
          leaf up-best-effort-rate {
            type uint32 {
              range "0..10000000";
            }
            units "Kbps";
            // NCS drop default statement
            description
              "Best Effort (low priority) upstream rate in Kbps.";
          }
          leaf up-best-effort-max-burst {
            type uint32 {
              range "0..1000000";
            }
            units "Bytes";
            // NCS drop default statement
            description
              "Maximum upstream burst size in Bytes. The best
               effort rate is enforced at this burst size.";
          }
          leaf up-priority {
            type uint8 {
              range "1..8";
            }
            // NCS drop default statement
            description
              "Priority level for the Guaranteed portion of the SLA.";
          }
          leaf up-service-limit {
            type uint16 {
              range "2..256";
            }
            units "kBytes";
            // NCS drop default statement
            description
              "Maximum grant size for an upstream slot in Kilobytes.";
          }
          leaf up-min-grant-period {
            type uint16 {
              range "0..1000";
            }
            // NCS drop default statement
            description
              "The minimum allowed spacing between grants on this service.";
          }
          leaf up-max-grant-period {
            type uint16 {
              range "3..1000";
            }
            // NCS drop default statement
            description
              "The maximum allowed time between grants on
               this service. This field will cause a polling grant
               when the ONU is idle.";
          }
          leaf down-guaranteed-rate {
            type uint32 {
              range "128..10000000";
            }
            units "Kbps";
            // NCS drop default statement
            description
              "Guaranteed (high priority) downstream rate in Kbps.";
          }
          leaf down-guaranteed-max-burst {
            type uint32 {
              range "0..1000000";
            }
            units "Bytes";
            // NCS drop default statement
            description
              "Maximum downstream burst size in Bytes. The
               guaranteed rate is enforced at this burst size.";
          }
          leaf down-best-effort-rate {
            type uint32 {
              range "0..10000000";
            }
            units "Kbps";
            // NCS drop default statement
            description
              "Best Effort (low priority) downstream rate in Kbps.";
          }
          leaf down-best-effort-max-burst {
            type uint32 {
              range "0..1000000";
            }
            units "Bytes";
            // NCS drop default statement
            description
              "Maximum downstream burst size in Bytes. The best
               effort rate is enforced at this burst size.";
          }
        }
      }
    }
    container pon-ctrl-state {
      tailf:ncs-device-type "netconf";
      tailf:display-when "not(../../ncs:module) or ../../ncs:module[ncs:name='ciena-pon-ctrl'] or (../../ncs:live-status-protocol[not(ncs:capability)]) or (../../ncs:live-status-protocol/ncs:capability/ncs:module[.='ciena-pon-ctrl'])";
      description
        "PON state data.";
      container olts {
        description
          "The state data for all OLTs.";
        list olt {
          key "name";
          description
            "List of OLTs.";
          leaf name {
            type pon-ctrl:live_ncs_name-string;
            description
              "Name of the OLT.";
          }
          leaf oper-state {
            type pon-ctrl:live_ncs_olt-oper-state;
            description
              "Operational state of the OLT.";
          }
          leaf physical-interface {
            type string;
            description
              "The physical port on the device that hosts this OLT.";
          }
          leaf host-management-address {
            type string;
            description
              "The management address of the device hosting this OLT.";
          }
          leaf host-system-name {
            type string;
            description
              "The system name of the device hosting this OLT.";
          }
          leaf management-tpid {
            type pon-ctrl:live_ncs_tpid;
            description
              "TPID used for in-band management of this OLT.";
          }
          leaf management-vid {
            type mef-fp:live_ncs_vlan-id;
            description
              "VID used for in-band management of this OLT.";
          }
          leaf firmware-version {
            type string;
            description
              "Version of the firmware running on this OLT.";
          }
          leaf standby-firmware-version {
            type string;
            description
              "Version of the firmware in the standby bank on this OLT.";
          }
          leaf firmware-status {
            type string;
            description
              "Status of the firmware running on this OLT.";
          }
          leaf hardware-version {
            type string;
            description
              "Version of the OLT's hardware.";
          }
          leaf model {
            type string;
            description
              "Model of this OLT.";
          }
          leaf model-number {
            type string;
            description
              "Model number of this OLT.";
          }
          leaf serial-number {
            type string;
            description
              "Serial number of this OLT.";
          }
          leaf num-configured-onus {
            type uint16;
            description
              "Number of configured ONUs under this OLT.";
          }
          leaf num-registered-onus {
            type uint16;
            description
              "Number of registered ONUs under this OLT.";
          }
          leaf num-deregistered-onus {
            type uint16;
            description
              "Number of deregistered ONUs under this OLT.";
          }
          leaf num-unconfigured-onus {
            type uint16;
            description
              "Number of unconfigured ONUs under this OLT.";
          }
          leaf-list unconfigured-onu {
            type string;
            description
              "The list of ONU serial numbers which have been discovered
               but not configured.";
          }
          leaf num-links {
            type uint16;
            description
              "Number of Datalinks under this OLT.";
          }
          container statistics {
            description
              "OLT statistics.";
            container nni {
              description
                "OLT NNI statistics";
              uses pon-ctrl:live_ncs_packet-counters-grouping;
              leaf rx-oam {
                type yang:counter64;
                description
                  "Count of OAM frames received on the interface.";
              }
              leaf tx-oam {
                type yang:counter64;
                description
                  "Count of OAM frames transmitted on the interface.";
              }
              leaf rx-mac-control-frames {
                type yang:counter64;
                description
                  "Count of MAC Control frames received on the interface.";
              }
              leaf rx-filtered-frames {
                type yang:counter64;
                description
                  "Count of frames received on the interface but filtered (not forwarded).";
              }
              leaf rx-crc32-drops {
                type yang:counter64;
                description
                  "Count of frames received on the interface and dropped due to invalid CRC32.";
              }
              leaf rx-overflow-drops {
                type yang:counter64;
                description
                  "Count of frames received on the interface and dropped due to input queues being full.";
              }
              leaf rx-too-short-drops {
                type yang:counter64;
                description
                  "Count of frames received on the interface and dropped due to the frame being too short.";
              }
              leaf rx-too-long-drops {
                type yang:counter64;
                description
                  "Count of frames received on the interface and dropped due to the frame being too long.";
              }
            }
            container pon {
              description
                "OLT PON statistics";
              uses pon-ctrl:live_ncs_packet-counters-grouping;
              uses pon-ctrl:live_ncs_phy-counters-grouping;
            }
          }
          container diagnostic-data {
            description
              "The diagnostic data for this OLT.";
            leaf asic-temperature {
              type int16;
              units "C";
              description
                "The OLT's ASIC temperature in degrees C.";
            }
            leaf xcvr-temperature {
              type int16;
              units "C";
              description
                "The OLT's transceiver temperature in degrees C.";
            }
            leaf laser-temperature {
              type int16;
              units "C";
              description
                "The OLT's laser temperature in degrees C.";
            }
            leaf vcc {
              type cntypes:live_ncs_decimal-2-dig;
              units "mV";
              description
                "The OLT's VCC in mV.";
            }
            leaf tec-current {
              type cntypes:live_ncs_decimal-2-dig;
              units "uA";
              description
                "The OLT's TEC current in uA.";
            }
            leaf transmit-bias {
              type cntypes:live_ncs_decimal-2-dig;
              units "uA";
              description
                "The OLT's transmit bias current in uA.";
            }
            leaf idle-receive-power {
              type cntypes:live_ncs_decimal-2-dig;
              units "dBm";
              description
                "The OLT's idle receive power in dBm.";
            }
            leaf transmit-power {
              type cntypes:live_ncs_decimal-2-dig;
              units "dBm";
              description
                "The OLT's transmit power in dBm.";
            }
            leaf last-shutdown-reason {
              type string;
              description
                "The reason for the latest shutdown of the OLT's laser.";
            }
            leaf is-laser-shutdown {
              type boolean;
              description
                "When true, indicates that the OLT's laser is currently shutdown.
                 When false, indicates that the OLT's laser is currently active.";
            }
          }
        }
      }
      container onus {
        description
          "The state data for all ONUs.";
        list onu {
          key "name olt";
          description
            "List of ONUs.";
          leaf name {
            type pon-ctrl:live_ncs_name-string;
            description
              "Name of the ONU.";
          }
          leaf olt {
            type pon-ctrl:live_ncs_olt-ref;
            description
              "Name of the OLT this ONU is subtended from.";
          }
          leaf oper-state {
            type pon-ctrl:live_ncs_onu-oper-state;
            description
              "Operational state of the ONU.";
          }
          leaf onu-id {
            type uint16;
            description
              "The ONU-ID of this ONU as assigned by the OLT.";
          }
          leaf deregister-reason {
            type string;
            description
              "The reason for the last ONU deregistration.
               Set when the oper-state of the ONU is 'deregistered'.";
          }
          leaf firmware-version {
            type string;
            description
              "Version of the firmware running on this ONU.";
          }
          leaf standby-firmware-version {
            type string;
            description
              "Version of the firmware in the standby bank on this ONU.";
          }
          leaf expected-firmware-version {
            type string;
            description
              "Version of the firmware that is expected to be running
               on this ONU based on the model number.
               Set when the ONU firmware status is 'Upgrade Required'.";
          }
          leaf firmware-status {
            type string;
            description
              "Status of the firmware running on this ONU.";
          }
          leaf firmware-upgrade-progress {
            type uint16;
            description
              "Percentage completion of the ONU firmware upgrade operation.
               Set when the ONU firmware status is 'Upgrading'.";
          }
          leaf firmware-upgrade-fail-reason {
            type string;
            description
              "The reason for the last ONU firmware upgrade failure.
               Set when the ONU firmware status is 'Upgrade Failed'.";
          }
          leaf model {
            type string;
            description
              "Model number of this ONU.";
          }
          leaf mode {
            type string;
            description
              "Mode that this ONU is operating in.";
          }
          leaf num-links {
            type uint16;
            description
              "Number of Datalinks under this ONU.";
          }
          leaf num-uni-ports {
            type uint8;
            description
              "Number of UNI ports on this ONU.";
          }
          container datalinks {
            description
              "The state data for all datalinks.";
            list datalink {
              key "name";
              description
                "List of datalinks.";
              leaf name {
                type pon-ctrl:live_ncs_name-string;
                description
                  "Name of the datalink.";
              }
              leaf alloc-id {
                type uint16;
                description
                  "The ALLOC-ID of this datalink as assigned by the OLT/ONU.
                   Only valid in XGS-PON mode.";
              }
              leaf llid {
                type uint16;
                description
                  "The LLID of this datalink as assigned by the OLT/ONU.
                   Only valid in 10G-EPON mode.";
              }
              container statistics {
                description
                  "Datalink statistics as viewed by the OLT.";
                uses pon-ctrl:live_ncs_packet-counters-grouping;
                uses pon-ctrl:live_ncs_phy-counters-grouping;
                leaf rx-fec-good-blocks {
                  type yang:counter64;
                  description
                    "Count of FEC blocks received without errors.";
                }
                leaf rx-fec-corrected-blocks {
                  type yang:counter64;
                  description
                    "Count of FEC blocks received with errors that were correctable.";
                }
                leaf rx-fec-uncorrectable-blocks {
                  type yang:counter64;
                  description
                    "Count of FEC blocks received with errors that were not correctable.";
                }
                leaf rx-fec-corrections {
                  type yang:counter64;
                  description
                    "Count of FEC blocks received with correctable errors that were corrected.";
                }
              }
            }
          }
          container uni-ports {
            description
              "The state data for all UNI ports.";
            list uni-port {
              key "name";
              description
                "List of UNI ports.";
              leaf name {
                type pon-ctrl:live_ncs_name-string;
                description
                  "The numerical identifier of this UNI port.";
              }
              leaf oper-state {
                type pon-ctrl:live_ncs_uni-port-oper-state;
                description
                  "Operational state of the UNI port.";
              }
              leaf speed {
                type pon-ctrl:live_ncs_uni-port-speed;
                description
                  "Operational speed of the UNI port.";
              }
              leaf duplex {
                type pon-ctrl:live_ncs_uni-port-duplex;
                description
                  "Operational duplex of the UNI port.";
              }
            }
          }
          container diagnostic-data {
            description
              "The diagnostic data for this ONU.";
            leaf olt-rx-power {
              type cntypes:live_ncs_decimal-2-dig;
              units "dBm";
              description
                "The OLT's Rx optical power for this ONU in dBm.";
            }
            leaf olt-tx-power {
              type cntypes:live_ncs_decimal-2-dig;
              units "dBm";
              description
                "The OLT's Tx optical power in dBm.";
            }
            leaf onu-rx-power {
              type cntypes:live_ncs_decimal-2-dig;
              units "dBm";
              description
                "The ONU's Rx optical power in dBm.";
            }
            leaf onu-tx-power {
              type cntypes:live_ncs_decimal-2-dig;
              units "dBm";
              description
                "The ONU's Tx optical power in dBm.";
            }
            leaf laser-bias-current {
              type cntypes:live_ncs_decimal-2-dig;
              units "mA";
              description
                "The ONU's laser bias current in mA.";
            }
            leaf power-feed-voltage {
              type cntypes:live_ncs_decimal-2-dig;
              units "V";
              description
                "The ONU's power feed voltage in V.";
            }
            leaf temperature {
              type int16;
              units "C";
              description
                "The ONU's temperature in degrees C.";
            }
          }
        }
      }
    }
  }
  augment "/ncs:devices/ncs:template/ncs:ned-id/ncs:config" {
    container pon-ctrl {
      description
        "PON configuration data.";
      container olts {
        description
          "The configuration data for all OLTs.";
        list olt {
          // NCS patched for predictable order
          ordered-by user;
          key "name";
          description
            "List of OLTs.";
          leaf name {
            type pon-ctrl:ncs_template_name-string;
            description
              "Name of the OLT.";
          }
          leaf admin-state {
            type ciena:ncs_template_admin-state;
            // NCS drop default statement
            description
              "Enable or disable the OLT.";
          }
          leaf mac-address {
            type string;
            // NCS drop mandatory statement
            description
              "The MAC address of the OLT.";
          }
          leaf management-interface {
            type pon-ctrl:ncs_template_interface-ref;
            // NCS drop must statement
            // NCS drop mandatory statement
            description
              "Reference to the L3 interface on which this OLT is to be
               managed.";
          }
          leaf pon-mode {
            type pon-ctrl:ncs_template_pon-mode;
            // NCS drop default statement
            description
              "The PON mode this OLT will operate in.";
          }
          leaf auto-boot-mode {
            type ciena:ncs_template_admin-state;
            // NCS drop default statement
            description
              "Enable or disable autonomous boot mode on the OLT.";
          }
          leaf upstream-fec-0 {
            // NCS drop when statement
            type ciena:ncs_template_admin-state;
            // NCS drop default statement
            description
              "Enable or disable upstream FEC (Forward Error Correction)
               for burst profile 0 on the OLT in XGS-PON mode.";
          }
          leaf upstream-preamble-0 {
            // NCS drop when statement
            type string;
            // NCS drop default statement
            description
              "The amount of preamble at the start of burst for profile 0
               on the OLT in XGS-PON mode; measured in units of upstream slots (12.8ns).";
          }
          leaf downstream-fec {
            type ciena:ncs_template_admin-state;
            // NCS drop default statement
            description
              "Enable or disable downstream FEC (Forward Error Correction) on the OLT.";
          }
          leaf encryption-mode {
            type pon-ctrl:ncs_template_encryption-mode;
            // NCS drop default statement
            description
              "The encryption mode on the OLT.";
          }
          leaf guard-time {
            // NCS drop when statement
            type string;
            // NCS drop default statement
            description
              "The guard time used by the OLT in XGS-PON mode.
               This is the amount of dead time between upstream burst slots
               measured in units of upstream slots (12.8ns).";
          }
          leaf max-nni-frame-size {
            type string;
            // NCS drop default statement
            description
              "The NNI port's MTU on the OLT.
               Maximum supported MTU is 9600 in XGS-PON mode and
               12500 in 10G-EPON mode.";
          }
          leaf max-pon-frame-size {
            type string;
            // NCS drop default statement
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              // NCS patched for predictable order
              ordered-by user;
              key "name";
              description
                "List of NNI Networks.";
              leaf name {
                type pon-ctrl:ncs_template_name-string;
                description
                  "Name of the NNI Network.";
              }
              uses pon-ctrl:ncs_template_tag-match-grouping;
              uses pon-ctrl:ncs_template_tag-options-grouping;
            }
          }
        }
      }
      container onus {
        description
          "The configuration data for all ONUs.";
        list onu {
          // NCS patched for predictable order
          ordered-by user;
          key "name olt";
          description
            "List of ONUs.";
          leaf name {
            type pon-ctrl:ncs_template_name-string;
            description
              "Name of the ONU.";
          }
          leaf olt {
            type pon-ctrl:ncs_template_olt-ref;
            // NCS drop mandatory statement
            description
              "Name of the OLT this ONU is subtended from.";
          }
          leaf serial-number {
            type string;
            // NCS drop mandatory statement
            description
              "The serial number the OLT expects to retrieve from the ONU.";
          }
          container datalinks {
            description
              "The configuration data for all Datalinks.
               A datalink is an LLID in 10G-EPON mode or an XGEM port in XGS-PON mode.";
            list datalink {
              // NCS patched for predictable order
              ordered-by user;
              key "name";
              description
                "List of Datalinks.";
              leaf name {
                type pon-ctrl:ncs_template_name-string;
                description
                  "Name of the datalink.";
              }
              leaf admin-state {
                type ciena:ncs_template_admin-state;
                // NCS drop default statement
                description
                  "Enable or disable traffic on this datalink.";
              }
              leaf-list uni-ports {
                // NCS patched for predictable order
                ordered-by user;
                type string;
                // NCS drop min-elements statement
                // NCS drop max-elements statement
                description
                  "List of ONU UNI ports to apply the datalink on.";
              }
              leaf-list vlan-ids {
                // NCS patched for predictable order
                ordered-by user;
                type pon-ctrl:ncs_template_tag-match-vid;
                // NCS drop max-elements statement
                description
                  "List of VLAN IDs to be forwarded on this datalink.
                   Traffic will only be allowed on this datalink if it matches
                   one of the values specified. Not specifying this field or
                   specifying a value of 65535 will match on any VID value,
                   no VLAN tag or a priority tag. Values specified must be unique
                   across all datalinks on the same UNI port.";
              }
              leaf sla-profile {
                type pon-ctrl:ncs_template_sla-profile-ref;
                // NCS drop mandatory statement
                description
                  "Name of the SLA profile this datalink implements.";
              }
              leaf add-ctag {
                type mef-fp:ncs_template_vlan-id;
                description
                  "Add an optional C-Tag at the ONU for all upstream traffic on this datalink.
                   This tag is popped (removed) in the downstream direction.";
              }
              leaf add-ctag-pcp {
                // NCS drop when statement
                type string;
                description
                  "Specify the 802.1p priority of the added C-Tag on this datalink.
                   This is only valid when the add-ctag parameter is specified.
                   When this field is not specified, a PCP value of 0 is assumed for
                   untagged frames. For tagged frames the PCP value of the added C-Tag
                   is copied from the existing VLAN.";
              }
            }
          }
          container pon-connections {
            description
              "The configuration data for all PON Connections.
               PON Connections are the configuration construct that links a Datalink on the ONU to
               an NNI Network on the OLT.";
            list pon-connection {
              // NCS patched for predictable order
              ordered-by user;
              key "name";
              description
                "List of PON Connections.";
              leaf name {
                type pon-ctrl:ncs_template_name-string;
                description
                  "Name of the PON Connection.";
              }
              leaf datalink {
                type string;
                // NCS drop mandatory statement
                description
                  "Reference to the datalink on the ONU.
                   Datalink must be configured on the same ONU as this PON Connection.";
              }
              leaf nni-network {
                type string;
                // NCS drop mandatory statement
                description
                  "Reference to the NNI Network on the OLT.
                   NNI Network must be configured on the same OLT as the ONU where this PON Connection exists.";
              }
              uses pon-ctrl:ncs_template_tag-match-grouping;
              uses pon-ctrl:ncs_template_tag-options-grouping;
            }
          }
          container uni-ports {
            description
              "The configuration data for all UNI ports.
               This configuration construct is optional and can be used to modify specific UNI port parameters
               under this ONU.";
            list uni-port {
              // NCS patched for predictable order
              ordered-by user;
              key "name";
              // NCS drop max-elements statement
              description
                "List of UNI ports.";
              leaf name {
                type pon-ctrl:ncs_template_name-string;
                description
                  "The numerical identifier of this UNI port.
                   Must be a numercical value between 1 and 5.";
              }
              leaf description {
                type pon-ctrl:ncs_template_name-string;
                description
                  "A string description of this UNI port.";
              }
              leaf admin-state {
                type ciena:ncs_template_admin-state;
                // NCS drop default statement
                description
                  "Enable or disable the UNI port.";
              }
              leaf max-frame-size {
                type string;
                // NCS drop default statement
                description
                  "The UNI port's configured MTU.";
              }
              leaf speed {
                type pon-ctrl:ncs_template_uni-port-speed;
                // NCS drop must statement
                // NCS drop default statement
                description
                  "The UNI port's configured speed.";
              }
              leaf duplex {
                type pon-ctrl:ncs_template_uni-port-duplex;
                // NCS drop must statement
                // NCS drop default statement
                description
                  "The UNI port's configured duplex.";
              }
            }
          }
        }
      }
      container sla-profiles {
        description
          "The configuration data for all SLA Profiles.";
        list sla-profile {
          // NCS patched for predictable order
          ordered-by user;
          key "name";
          description
            "List of SLA profiles.";
          leaf name {
            type pon-ctrl:ncs_template_name-string;
            description
              "Name of the SLA profile.";
          }
          leaf up-fixed-rate {
            type string;
            units "Kbps";
            // NCS drop default statement
            description
              "Fixed grant rate in Kbps. This is an unsolicited
               grant by the DBA regardless of need.";
          }
          leaf up-guaranteed-rate {
            type string;
            units "Kbps";
            // NCS drop default statement
            description
              "Guaranteed (high priority) upstream rate in Kbps.";
          }
          leaf up-guaranteed-max-burst {
            type string;
            units "Bytes";
            // NCS drop default statement
            description
              "Maximum upstream burst size in Bytes. The
               guaranteed rate is enforced at this burst size.";
          }
          leaf up-best-effort-rate {
            type string;
            units "Kbps";
            // NCS drop default statement
            description
              "Best Effort (low priority) upstream rate in Kbps.";
          }
          leaf up-best-effort-max-burst {
            type string;
            units "Bytes";
            // NCS drop default statement
            description
              "Maximum upstream burst size in Bytes. The best
               effort rate is enforced at this burst size.";
          }
          leaf up-priority {
            type string;
            // NCS drop default statement
            description
              "Priority level for the Guaranteed portion of the SLA.";
          }
          leaf up-service-limit {
            type string;
            units "kBytes";
            // NCS drop default statement
            description
              "Maximum grant size for an upstream slot in Kilobytes.";
          }
          leaf up-min-grant-period {
            type string;
            // NCS drop default statement
            description
              "The minimum allowed spacing between grants on this service.";
          }
          leaf up-max-grant-period {
            type string;
            // NCS drop default statement
            description
              "The maximum allowed time between grants on
               this service. This field will cause a polling grant
               when the ONU is idle.";
          }
          leaf down-guaranteed-rate {
            type string;
            units "Kbps";
            // NCS drop default statement
            description
              "Guaranteed (high priority) downstream rate in Kbps.";
          }
          leaf down-guaranteed-max-burst {
            type string;
            units "Bytes";
            // NCS drop default statement
            description
              "Maximum downstream burst size in Bytes. The
               guaranteed rate is enforced at this burst size.";
          }
          leaf down-best-effort-rate {
            type string;
            units "Kbps";
            // NCS drop default statement
            description
              "Best Effort (low priority) downstream rate in Kbps.";
          }
          leaf down-best-effort-max-burst {
            type string;
            units "Bytes";
            // NCS drop default statement
            description
              "Maximum downstream burst size in Bytes. The best
               effort rate is enforced at this burst size.";
          }
        }
      }
    }
    // NCS drop config false container 'pon-ctrl-state'
  }
}
