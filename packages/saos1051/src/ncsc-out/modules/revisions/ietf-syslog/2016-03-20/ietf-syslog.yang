module ietf-syslog {
  // Generated by yanger -t ncs
  tailf:mount-id "saos1051-nc-1.0:saos1051-nc-1.0";
  tailf:ncs-device-type "netconf";

  namespace "urn:ietf:params:xml:ns:yang:ietf-syslog";
  prefix syslog;

  import ietf-inet-types {
    prefix inet;
  }
  import ietf-interfaces {
    prefix if;
  }
  import ietf-syslog-types {
    prefix syslogtypes;
  }
  import tailf-common {
    prefix tailf;
  }
  import tailf-ncs {
    prefix ncs;
  }

  organization
    "IETF NETMOD (NETCONF Data Modeling Language)
     Working Group";
  contact
    "WG Web:   <http://tools.ietf.org/wg/netmod/>
     WG List:  <mailto:netmod@ietf.org>

     WG Chair: Lou Berger
               <mailto:lberger@labn.net>

     WG Chair: Jurgen Schonwalder
               <mailto:j.schoenwaelder@jacobs-university.de>

     WG Chair: Kent Watsen
               <mailto:kwatsen@juniper.net>

     Editor:   Kiran Agrahara Sreenivasa
               <mailto:kkoushik@cisco.com>

     Editor:   Clyde Wildes
               <mailto:cwildes@cisco.com>";
  description
    "This module contains a collection of YANG definitions
     for Syslog configuration.

     Copyright (c) 2015 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119 (http://tools.ietf.org/html/rfc2119).

     This version of this YANG module is part of RFC XXXX
     (http://tools.ietf.org/html/rfcXXXX); see the RFC itself for
     full legal notices.";
  reference
    "RFC 5424: The Syslog Protocol
     RFC 5848: Signed Syslog Messages";

  revision 2016-03-20 {
    description
      "Initial Revision";
    reference "RFC XXXX: SYSLOG YANG Model";
  }

  grouping ncs_template_syslog-severity {
    description
      "This grouping defines the Syslog severity which is used to
       select log messages.";
    leaf severity {
      type string;
      // NCS drop mandatory statement
      description
        "This leaf specifies the Syslog message severity. When
         severity is specified, the default severity comparison
         is all messages of the specified severity and greater are
         selected. 'all' is a special case which means all severities
         are selected. 'none' is a special case which means that
         no selection should occur or disable this filter.";
    }
    leaf severity-operator {
      // NCS drop when statement
      // NCS drop if-feature statement
      type string;
      // NCS drop default statement
      description
        "This leaf describes the option to specify how the
         severity comparison is performed.";
    }
  }

  grouping ncs_template_syslog-selector {
    description
      "This grouping defines a Syslog selector which is used to
       select log messages for the log-action (buffer, file,
       etc). Choose one of the following:
         no-log-facility
         log-facility [<facility> <severity>...]";
    container log-selector {
      description
        "This container describes the log selector parameters
         for Syslog.";
      choice selector-facility {
        // NCS drop mandatory statement
        description
          "This choice describes the option to specify no
           facilities, or a specific facility which can be
           all for all facilities.";
        case no-log-facility {
          description
            "This case specifies no facilities will match when
             comparing the Syslog message facility. This is a
             method that can be used to effectively disable a
             particular log-action (buffer, file, etc).";
          leaf no-facilities {
            type empty;
            description
              "This leaf specifies that no facilities are selected
               for this log-action.";
          }
        }
        case log-facility {
          description
            "This case specifies one or more specified facilities
             will match when comparing the Syslog message facility.";
          list log-facility {
            // NCS patched for predictable order
            ordered-by user;
            key "facility";
            description
              "This list describes a collection of Syslog
               facilities and severities.";
            leaf facility {
              type string;
              description
                "The leaf uniquely identifies a Syslog facility.";
            }
            uses ncs_template_syslog-severity;
          }
        }
      }
      leaf pattern-match {
        // NCS drop if-feature statement
        type string;
        description
          "This leaf desribes a Posix 1003.2 regular expression
           string that can be used to select a Syslog message for
           logging. The match is performed on the RFC 5424
           SYSLOG-MSG field.";
      }
    }
  }

  grouping ncs_template_syslog-structured-data {
    description
      "This grouping defines the Syslog structured data option
       which is used to select the format used to write log
       messages.";
    leaf structured-data {
      // NCS drop if-feature statement
      type string;
      // NCS drop default statement
      description
        "This leaf describes how log messages are written to
         the log file. If true, messages will be written
         with one or more STRUCTURED-DATA elements as per
         RFC5424; if false, messages will be written with
         STRUCTURED-DATA = NILVALUE.";
    }
  }

  grouping ncs_rpc_notif_syslog-severity {
    description
      "This grouping defines the Syslog severity which is used to
       select log messages.";
    leaf severity {
      type union {
        type enumeration {
          enum "none" {
            value -2;
            description
              "This enum describes the case where no severities
               are selected.";
          }
          enum "all" {
            value -1;
            description
              "This enum describes the case where all severities
               are selected.";
          }
        }
        type syslogtypes:ncs_rpc_notif_severity;
      }
      mandatory true;
      description
        "This leaf specifies the Syslog message severity. When
         severity is specified, the default severity comparison
         is all messages of the specified severity and greater are
         selected. 'all' is a special case which means all severities
         are selected. 'none' is a special case which means that
         no selection should occur or disable this filter.";
    }
    leaf severity-operator {
      when '../severity != "all" and
           ../severity != "none"' {
        tailf:xpath-root 3;
        description
          "The severity-operator is not applicable for severity 'all' or
           severity 'none'";
      }
      tailf:display-when "not(../ncs:module) or boolean(/ncs:devices/ncs:device[ncs:name=current()/../ncs:name]/capability/feature='selector-sevop-config')";
      type enumeration {
        enum "equals-or-higher" {
          description
            "This enum specifies all messages of the specified
             severity and higher are logged according to the
             given log-action";
        }
        enum "equals" {
          description
            "This enum specifies all messages that are for
             the specified severity are logged according to the
             given log-action";
        }
        enum "not-equals" {
          description
            "This enum specifies all messages that are not for
             the specified severity are logged according to the
             given log-action";
        }
      }
      default "equals-or-higher";
      description
        "This leaf describes the option to specify how the
         severity comparison is performed.";
    }
  }

  grouping ncs_rpc_notif_syslog-selector {
    description
      "This grouping defines a Syslog selector which is used to
       select log messages for the log-action (buffer, file,
       etc). Choose one of the following:
         no-log-facility
         log-facility [<facility> <severity>...]";
    container log-selector {
      description
        "This container describes the log selector parameters
         for Syslog.";
      choice selector-facility {
        mandatory true;
        description
          "This choice describes the option to specify no
           facilities, or a specific facility which can be
           all for all facilities.";
        case no-log-facility {
          description
            "This case specifies no facilities will match when
             comparing the Syslog message facility. This is a
             method that can be used to effectively disable a
             particular log-action (buffer, file, etc).";
          leaf no-facilities {
            type empty;
            description
              "This leaf specifies that no facilities are selected
               for this log-action.";
          }
        }
        case log-facility {
          description
            "This case specifies one or more specified facilities
             will match when comparing the Syslog message facility.";
          list log-facility {
            key "facility";
            description
              "This list describes a collection of Syslog
               facilities and severities.";
            leaf facility {
              type union {
                type identityref {
                  base syslogtypes:syslog-facility;
                }
                type enumeration {
                  enum "all" {
                    description
                      "This enum describes the case where all
                       facilities are requested.";
                  }
                }
              }
              description
                "The leaf uniquely identifies a Syslog facility.";
            }
            uses ncs_rpc_notif_syslog-severity;
          }
        }
      }
      leaf pattern-match {
        tailf:display-when "not(../../ncs:module) or boolean(/ncs:devices/ncs:device[ncs:name=current()/../../ncs:name]/capability/feature='selector-match-config')";
        type string;
        description
          "This leaf desribes a Posix 1003.2 regular expression
           string that can be used to select a Syslog message for
           logging. The match is performed on the RFC 5424
           SYSLOG-MSG field.";
      }
    }
  }

  grouping ncs_rpc_notif_syslog-structured-data {
    description
      "This grouping defines the Syslog structured data option
       which is used to select the format used to write log
       messages.";
    leaf structured-data {
      tailf:display-when "not(../ncs:module) or boolean(/ncs:devices/ncs:device[ncs:name=current()/../ncs:name]/capability/feature='structured-data-config')";
      type boolean;
      default "false";
      description
        "This leaf describes how log messages are written to
         the log file. If true, messages will be written
         with one or more STRUCTURED-DATA elements as per
         RFC5424; if false, messages will be written with
         STRUCTURED-DATA = NILVALUE.";
    }
  }

  grouping live_ncs_syslog-severity {
    description
      "This grouping defines the Syslog severity which is used to
       select log messages.";
    leaf severity {
      type union {
        type enumeration {
          enum "none" {
            value -2;
            description
              "This enum describes the case where no severities
               are selected.";
          }
          enum "all" {
            value -1;
            description
              "This enum describes the case where all severities
               are selected.";
          }
        }
        type syslogtypes:live_ncs_severity;
      }
      // NCS drop mandatory statement
      description
        "This leaf specifies the Syslog message severity. When
         severity is specified, the default severity comparison
         is all messages of the specified severity and greater are
         selected. 'all' is a special case which means all severities
         are selected. 'none' is a special case which means that
         no selection should occur or disable this filter.";
    }
    leaf severity-operator {
      // NCS drop when statement
      // NCS drop if-feature statement
      type enumeration {
        enum "equals-or-higher" {
          description
            "This enum specifies all messages of the specified
             severity and higher are logged according to the
             given log-action";
        }
        enum "equals" {
          description
            "This enum specifies all messages that are for
             the specified severity are logged according to the
             given log-action";
        }
        enum "not-equals" {
          description
            "This enum specifies all messages that are not for
             the specified severity are logged according to the
             given log-action";
        }
      }
      // NCS drop default statement
      description
        "This leaf describes the option to specify how the
         severity comparison is performed.";
    }
  }

  grouping live_ncs_syslog-selector {
    description
      "This grouping defines a Syslog selector which is used to
       select log messages for the log-action (buffer, file,
       etc). Choose one of the following:
         no-log-facility
         log-facility [<facility> <severity>...]";
    container log-selector {
      description
        "This container describes the log selector parameters
         for Syslog.";
      choice selector-facility {
        // NCS drop mandatory statement
        description
          "This choice describes the option to specify no
           facilities, or a specific facility which can be
           all for all facilities.";
        case no-log-facility {
          description
            "This case specifies no facilities will match when
             comparing the Syslog message facility. This is a
             method that can be used to effectively disable a
             particular log-action (buffer, file, etc).";
          leaf no-facilities {
            type empty;
            description
              "This leaf specifies that no facilities are selected
               for this log-action.";
          }
        }
        case log-facility {
          description
            "This case specifies one or more specified facilities
             will match when comparing the Syslog message facility.";
          list log-facility {
            key "facility";
            description
              "This list describes a collection of Syslog
               facilities and severities.";
            leaf facility {
              type union {
                type identityref {
                  base syslogtypes:syslog-facility;
                }
                type enumeration {
                  enum "all" {
                    description
                      "This enum describes the case where all
                       facilities are requested.";
                  }
                }
              }
              description
                "The leaf uniquely identifies a Syslog facility.";
            }
            uses live_ncs_syslog-severity;
          }
        }
      }
      leaf pattern-match {
        // NCS drop if-feature statement
        type string;
        description
          "This leaf desribes a Posix 1003.2 regular expression
           string that can be used to select a Syslog message for
           logging. The match is performed on the RFC 5424
           SYSLOG-MSG field.";
      }
    }
  }

  grouping live_ncs_syslog-structured-data {
    description
      "This grouping defines the Syslog structured data option
       which is used to select the format used to write log
       messages.";
    leaf structured-data {
      // NCS drop if-feature statement
      type boolean;
      // NCS drop default statement
      description
        "This leaf describes how log messages are written to
         the log file. If true, messages will be written
         with one or more STRUCTURED-DATA elements as per
         RFC5424; if false, messages will be written with
         STRUCTURED-DATA = NILVALUE.";
    }
  }

  grouping syslog-severity {
    description
      "This grouping defines the Syslog severity which is used to
       select log messages.";
    leaf severity {
      type union {
        type enumeration {
          enum "none" {
            value -2;
            description
              "This enum describes the case where no severities
               are selected.";
          }
          enum "all" {
            value -1;
            description
              "This enum describes the case where all severities
               are selected.";
          }
        }
        type syslogtypes:severity;
      }
      mandatory true;
      description
        "This leaf specifies the Syslog message severity. When
         severity is specified, the default severity comparison
         is all messages of the specified severity and greater are
         selected. 'all' is a special case which means all severities
         are selected. 'none' is a special case which means that
         no selection should occur or disable this filter.";
    }
    leaf severity-operator {
      when '../severity != "all" and
           ../severity != "none"' {
        tailf:xpath-root 3;
        description
          "The severity-operator is not applicable for severity 'all' or
           severity 'none'";
      }
      tailf:display-when "not(../ncs:module) or boolean(/ncs:devices/ncs:device[ncs:name=current()/../ncs:name]/capability/feature='selector-sevop-config')";
      type enumeration {
        enum "equals-or-higher" {
          description
            "This enum specifies all messages of the specified
             severity and higher are logged according to the
             given log-action";
        }
        enum "equals" {
          description
            "This enum specifies all messages that are for
             the specified severity are logged according to the
             given log-action";
        }
        enum "not-equals" {
          description
            "This enum specifies all messages that are not for
             the specified severity are logged according to the
             given log-action";
        }
      }
      default "equals-or-higher";
      description
        "This leaf describes the option to specify how the
         severity comparison is performed.";
    }
  }

  grouping syslog-selector {
    description
      "This grouping defines a Syslog selector which is used to
       select log messages for the log-action (buffer, file,
       etc). Choose one of the following:
         no-log-facility
         log-facility [<facility> <severity>...]";
    container log-selector {
      description
        "This container describes the log selector parameters
         for Syslog.";
      choice selector-facility {
        mandatory true;
        description
          "This choice describes the option to specify no
           facilities, or a specific facility which can be
           all for all facilities.";
        case no-log-facility {
          description
            "This case specifies no facilities will match when
             comparing the Syslog message facility. This is a
             method that can be used to effectively disable a
             particular log-action (buffer, file, etc).";
          leaf no-facilities {
            type empty;
            description
              "This leaf specifies that no facilities are selected
               for this log-action.";
          }
        }
        case log-facility {
          description
            "This case specifies one or more specified facilities
             will match when comparing the Syslog message facility.";
          list log-facility {
            key "facility";
            description
              "This list describes a collection of Syslog
               facilities and severities.";
            leaf facility {
              type union {
                type identityref {
                  base syslogtypes:syslog-facility;
                }
                type enumeration {
                  enum "all" {
                    description
                      "This enum describes the case where all
                       facilities are requested.";
                  }
                }
              }
              description
                "The leaf uniquely identifies a Syslog facility.";
            }
            uses syslog-severity;
          }
        }
      }
      leaf pattern-match {
        tailf:display-when "not(../../ncs:module) or boolean(/ncs:devices/ncs:device[ncs:name=current()/../../ncs:name]/capability/feature='selector-match-config')";
        type string;
        description
          "This leaf desribes a Posix 1003.2 regular expression
           string that can be used to select a Syslog message for
           logging. The match is performed on the RFC 5424
           SYSLOG-MSG field.";
      }
    }
  }

  grouping syslog-structured-data {
    description
      "This grouping defines the Syslog structured data option
       which is used to select the format used to write log
       messages.";
    leaf structured-data {
      tailf:display-when "not(../ncs:module) or boolean(/ncs:devices/ncs:device[ncs:name=current()/../ncs:name]/capability/feature='structured-data-config')";
      type boolean;
      default "false";
      description
        "This leaf describes how log messages are written to
         the log file. If true, messages will be written
         with one or more STRUCTURED-DATA elements as per
         RFC5424; if false, messages will be written with
         STRUCTURED-DATA = NILVALUE.";
    }
  }

  augment "/ncs:devices/ncs:device/ncs:config" {
    container syslog {
      tailf:ncs-device-type "netconf";
      tailf:display-when "not(../../ncs:module) or ../../ncs:module[ncs:name='ietf-syslog']";
      description
        "This container describes the configuration parameters for
         Syslog.";
      container log-actions {
        description
          "This container describes the log-action parameters
           for Syslog.";
        container console {
          tailf:display-when "not(../../../ncs:module) or boolean(/ncs:devices/ncs:device[ncs:name=current()/../../../ncs:name]/capability/feature='console-action')";
          presence "Enables logging console configuration";
          description
            "This container describes the configuration parameters for
             console logging.";
          uses syslog-selector;
        }
        container buffer {
          tailf:display-when "not(../../../ncs:module) or boolean(/ncs:devices/ncs:device[ncs:name=current()/../../../ncs:name]/capability/feature='buffer-action')";
          description
            "This container describes the configuration parameters for
             local memory buffer logging. The buffer is circular in
             nature, so newer messages overwrite older messages after
             the buffer is filled. The method used to read syslog messages
             from the buffer is supplied by the local implementation.";
          list log-buffer {
            key "name";
            description
              "This list describes a collection of local logging
               memory buffers. If buffer size limits are not supplied, it
               is assumed that the local implementation defined
               limits will be used.";
            leaf name {
              type string;
              description
                "This leaf specifies the name of the log buffer.";
            }
            uses syslog-selector;
            leaf buffer-size-bytes {
              tailf:display-when "not(../../../../../ncs:module) or boolean(/ncs:devices/ncs:device[ncs:name=current()/../../../../../ncs:name]/capability/feature='buffer-limit-bytes')";
              type uint64;
              units "bytes";
              description
                "This leaf configures the amount of memory (in bytes) that
                 will be dedicated to the local memory logging buffer.
                 The default value varies by implementation.";
            }
            leaf buffer-size-messages {
              tailf:display-when "not(../../../../../ncs:module) or boolean(/ncs:devices/ncs:device[ncs:name=current()/../../../../../ncs:name]/capability/feature='buffer-limit-messages')";
              type uint64;
              units "log messages";
              description
                "This leaf configures the amount number of log messages that
                 can be stored in the local memory logging buffer. The
                 default value varies by implementation.";
            }
            uses syslog-structured-data;
          }
        }
        container file {
          description
            "This container describes the configuration parameters for
             file logging. If file-archive limits are not supplied, it
             is assumed that the local implementation defined limits will
             be used.";
          list log-file {
            key "name";
            description
              "This list describes a collection of local logging
               files.";
            leaf name {
              type inet:uri {
                pattern 'file:.*';
              }
              description
                "This leaf specifies the name of the log file which
                 MUST use the uri scheme file:.";
            }
            uses syslog-selector;
            uses syslog-structured-data;
            container file-archive {
              description
                "This container describes the configuration
                 parameters for log file archiving.";
              leaf number-of-files {
                tailf:display-when "not(../../../../../../ncs:module) or boolean(/ncs:devices/ncs:device[ncs:name=current()/../../../../../../ncs:name]/capability/feature='file-limit-size')";
                type uint32;
                description
                  "This leaf specifies the maximum number of log
                   files retained. Specify 1 for implementations
                   that only support one log file.";
              }
              leaf max-file-size {
                tailf:display-when "not(../../../../../../ncs:module) or boolean(/ncs:devices/ncs:device[ncs:name=current()/../../../../../../ncs:name]/capability/feature='file-limit-size')";
                type uint64;
                units "megabytes";
                description
                  "This leaf specifies the maximum log file size.";
              }
              leaf rollover {
                tailf:display-when "not(../../../../../../ncs:module) or boolean(/ncs:devices/ncs:device[ncs:name=current()/../../../../../../ncs:name]/capability/feature='file-limit-duration')";
                type uint32;
                units "minutes";
                description
                  "This leaf specifies the length of time that log
                   events should be written to a specific log file.
                   Log events that arrive after the rollover period
                   cause the current log file to be closed and a new
                   log file to be opened.";
              }
              leaf retention {
                tailf:display-when "not(../../../../../../ncs:module) or boolean(/ncs:devices/ncs:device[ncs:name=current()/../../../../../../ncs:name]/capability/feature='file-limit-duration')";
                type uint16;
                units "hours";
                description
                  "This leaf specifies the length of time that
                   completed/closed log event files should be stored
                   in the file system before they are deleted.";
              }
            }
          }
        }
        container remote {
          description
            "This container describes the configuration parameters for
             remote logging.";
          list destination {
            key "name";
            description
              "This list describes a collection of remote logging
               destinations.";
            leaf name {
              type string;
              description
                "An arbitrary name for the endpoint to connect to.";
            }
            choice transport {
              mandatory true;
              description
                "This choice describes the transport option.";
              case tcp {
                container tcp {
                  description
                    "This container describes the TCP transport
                     options.";
                  reference "RFC 6587: Transmission of Syslog Messages over TCP";
                  leaf address {
                    type inet:host;
                    description
                      "The leaf uniquely specifies the address of
                       the remote host. One of the following must
                       be specified: an ipv4 address, an ipv6
                       address, or a host name.";
                  }
                  leaf port {
                    type inet:port-number;
                    default "514";
                    description
                      "This leaf specifies the port number used to
                       deliver messages to the remote server.";
                  }
                }
              }
              case udp {
                container udp {
                  description
                    "This container describes the UDP transport
                     options.";
                  reference "RFC 5426: Transmission of Syslog Messages over UDP";
                  leaf address {
                    type inet:host;
                    description
                      "The leaf uniquely specifies the address of
                       the remote host. One of the following must be
                       specified: an ipv4 address, an ipv6 address,
                       or a host name.";
                  }
                  leaf port {
                    type inet:port-number;
                    default "514";
                    description
                      "This leaf specifies the port number used to
                       deliver messages to the remote server.";
                  }
                }
              }
              case tls {
                container tls {
                  description
                    "This container describes the TLS transport options.";
                  reference
                    "RFC 5425: Transport Layer Security (TLS) Transport
                     Mapping for Syslog ";
                  leaf address {
                    type inet:host;
                    description
                      "The leaf uniquely specifies the address of
                       the remote host. One of the following must be
                       specified: an ipv4 address, an ipv6 address,
                       or a host name.";
                  }
                  leaf port {
                    type inet:port-number;
                    default "6514";
                    description
                      "This leaf specifies the port number used to
                       deliver messages to the remote server.";
                  }
                }
              }
            }
            uses syslog-selector;
            leaf destination-facility {
              type identityref {
                base syslogtypes:syslog-facility;
              }
              default "syslogtypes:local7";
              description
                "This leaf specifies the facility used in messages
                 delivered to the remote server.";
            }
            leaf source-interface {
              type if:interface-ref;
              description
                "This leaf sets the source interface for the remote
                 Syslog server. Either the interface name or the
                 interface IP address can be specified. If not set,
                 messages sent to a remote syslog server will
                 contain the IP address of the interface the syslog
                 message uses to exit the network element";
            }
            uses syslog-structured-data;
            container syslog-sign {
              tailf:display-when "not(../../../../../ncs:module) or boolean(/ncs:devices/ncs:device[ncs:name=current()/../../../../../ncs:name]/capability/feature='signed-messages-config')";
              presence "If present, syslog-sign is activated.";
              description
                "This container describes the configuration
                 parameters for signed syslog messages as described
                 by RFC 5848.";
              reference "RFC 5848: Signed Syslog Messages";
              leaf cert-initial-repeat {
                type uint16;
                mandatory true;
                description
                  "This leaf specifies the number of times each
                   Certificate Block should be sent before the first
                   message is sent.";
              }
              leaf cert-resend-delay {
                type uint16;
                mandatory true;
                description
                  "This leaf specifies the maximum time delay in
                   seconds until resending the Certificate Block.";
              }
              leaf cert-resend-count {
                type uint16;
                mandatory true;
                description
                  "This leaf specifies the maximum number of other
                   syslog messages to send until resending the
                   Certificate Block.";
              }
              leaf sig-max-delay {
                type uint16;
                mandatory true;
                description
                  "This leaf specifies when to generate a new
                   Signature Block. If this many seconds have
                   elapsed since the message with the first message
                   number of the Signature Block was sent, a new
                   Signature Block should be generated.";
              }
              leaf sig-number-resends {
                type uint16;
                mandatory true;
                description
                  "This leaf specifies the number of times a
                   Signature Block is resent. (It is recommended to
                   select a value of greater than 0 in particular
                   when the UDP transport [RFC5426] is used.).";
              }
              leaf sig-resend-delay {
                type uint16;
                mandatory true;
                description
                  "This leaf specifies when to send the next
                   Signature Block transmission based on time. If
                   this many seconds have elapsed since the previous
                   sending of this Signature Block, resend it.";
              }
              leaf sig-resend-count {
                type uint16;
                mandatory true;
                description
                  "This leaf specifies when to send the next
                   Signature Block transmission based on a count.
                   If this many other syslog messages have been sent
                   since the previous sending of this Signature
                   Block, resend it.";
              }
            }
          }
        }
        container terminal {
          tailf:display-when "not(../../../ncs:module) or boolean(/ncs:devices/ncs:device[ncs:name=current()/../../../ncs:name]/capability/feature='terminal-action')";
          description
            "This container describes the configuration parameters for
             the terminal logging configuration.";
          container all-terminals {
            presence "Enables logging to all terminals.";
            description
              "This container describes the configuration
               parameters for all terminals.";
            uses syslog-selector;
          }
          list terminal {
            tailf:display-when "not(../../../ncs:module) or boolean(/ncs:devices/ncs:device[ncs:name=current()/../../../ncs:name]/capability/feature='terminal-facility-user-logging-config')";
            key "name";
            description
              "This list describes a collection of ";
            leaf name {
              type string;
              description
                "This leaf uniquely describes a terminal which
                 will receive log messages.";
            }
            uses syslog-selector;
          }
        }
        container session {
          tailf:display-when "not(../../../ncs:module) or boolean(/ncs:devices/ncs:device[ncs:name=current()/../../../ncs:name]/capability/feature='session-action')";
          description
            "This container describes the configuration parameters for
             user CLI session logging configuration.";
          container all-users {
            presence "Enables logging to all user sessions.";
            description
              "This container describes the configuration
               parameters for all users.";
            uses syslog-selector;
          }
          list user {
            tailf:display-when "not(../../../ncs:module) or boolean(/ncs:devices/ncs:device[ncs:name=current()/../../../ncs:name]/capability/feature='session-facility-user-logging-config')";
            key "name";
            description
              "This list describes a collection of user names.";
            leaf name {
              type string;
              description
                "This leaf uniquely describes a user name which
                 is the login name of the user whose session
                 is to receive log messages.";
            }
            uses syslog-selector;
          }
        }
      }
    }
  }
  augment "/ncs:devices/ncs:device/ncs:live-status" {
    container syslog {
      tailf:ncs-device-type "netconf";
      tailf:display-when "not(../../ncs:module) or ../../ncs:module[ncs:name='ietf-syslog'] or (../../ncs:live-status-protocol[not(ncs:capability)]) or (../../ncs:live-status-protocol/ncs:capability/ncs:module[.='ietf-syslog'])";
      description
        "This container describes the configuration parameters for
         Syslog.";
      container log-actions {
        description
          "This container describes the log-action parameters
           for Syslog.";
        container console {
          // NCS drop if-feature statement
          presence "Enables logging console configuration";
          description
            "This container describes the configuration parameters for
             console logging.";
          uses live_ncs_syslog-selector;
        }
        container buffer {
          // NCS drop if-feature statement
          description
            "This container describes the configuration parameters for
             local memory buffer logging. The buffer is circular in
             nature, so newer messages overwrite older messages after
             the buffer is filled. The method used to read syslog messages
             from the buffer is supplied by the local implementation.";
          list log-buffer {
            key "name";
            description
              "This list describes a collection of local logging
               memory buffers. If buffer size limits are not supplied, it
               is assumed that the local implementation defined
               limits will be used.";
            leaf name {
              type string;
              description
                "This leaf specifies the name of the log buffer.";
            }
            uses live_ncs_syslog-selector;
            leaf buffer-size-bytes {
              // NCS drop if-feature statement
              type uint64;
              units "bytes";
              description
                "This leaf configures the amount of memory (in bytes) that
                 will be dedicated to the local memory logging buffer.
                 The default value varies by implementation.";
            }
            leaf buffer-size-messages {
              // NCS drop if-feature statement
              type uint64;
              units "log messages";
              description
                "This leaf configures the amount number of log messages that
                 can be stored in the local memory logging buffer. The
                 default value varies by implementation.";
            }
            uses live_ncs_syslog-structured-data;
          }
        }
        container file {
          description
            "This container describes the configuration parameters for
             file logging. If file-archive limits are not supplied, it
             is assumed that the local implementation defined limits will
             be used.";
          list log-file {
            key "name";
            description
              "This list describes a collection of local logging
               files.";
            leaf name {
              type inet:uri {
                pattern 'file:.*';
              }
              description
                "This leaf specifies the name of the log file which
                 MUST use the uri scheme file:.";
            }
            uses live_ncs_syslog-selector;
            uses live_ncs_syslog-structured-data;
            container file-archive {
              description
                "This container describes the configuration
                 parameters for log file archiving.";
              leaf number-of-files {
                // NCS drop if-feature statement
                type uint32;
                description
                  "This leaf specifies the maximum number of log
                   files retained. Specify 1 for implementations
                   that only support one log file.";
              }
              leaf max-file-size {
                // NCS drop if-feature statement
                type uint64;
                units "megabytes";
                description
                  "This leaf specifies the maximum log file size.";
              }
              leaf rollover {
                // NCS drop if-feature statement
                type uint32;
                units "minutes";
                description
                  "This leaf specifies the length of time that log
                   events should be written to a specific log file.
                   Log events that arrive after the rollover period
                   cause the current log file to be closed and a new
                   log file to be opened.";
              }
              leaf retention {
                // NCS drop if-feature statement
                type uint16;
                units "hours";
                description
                  "This leaf specifies the length of time that
                   completed/closed log event files should be stored
                   in the file system before they are deleted.";
              }
            }
          }
        }
        container remote {
          description
            "This container describes the configuration parameters for
             remote logging.";
          list destination {
            key "name";
            description
              "This list describes a collection of remote logging
               destinations.";
            leaf name {
              type string;
              description
                "An arbitrary name for the endpoint to connect to.";
            }
            choice transport {
              // NCS drop mandatory statement
              description
                "This choice describes the transport option.";
              case tcp {
                container tcp {
                  description
                    "This container describes the TCP transport
                     options.";
                  reference "RFC 6587: Transmission of Syslog Messages over TCP";
                  leaf address {
                    type inet:host;
                    description
                      "The leaf uniquely specifies the address of
                       the remote host. One of the following must
                       be specified: an ipv4 address, an ipv6
                       address, or a host name.";
                  }
                  leaf port {
                    type inet:port-number;
                    // NCS drop default statement
                    description
                      "This leaf specifies the port number used to
                       deliver messages to the remote server.";
                  }
                }
              }
              case udp {
                container udp {
                  description
                    "This container describes the UDP transport
                     options.";
                  reference "RFC 5426: Transmission of Syslog Messages over UDP";
                  leaf address {
                    type inet:host;
                    description
                      "The leaf uniquely specifies the address of
                       the remote host. One of the following must be
                       specified: an ipv4 address, an ipv6 address,
                       or a host name.";
                  }
                  leaf port {
                    type inet:port-number;
                    // NCS drop default statement
                    description
                      "This leaf specifies the port number used to
                       deliver messages to the remote server.";
                  }
                }
              }
              case tls {
                container tls {
                  description
                    "This container describes the TLS transport options.";
                  reference
                    "RFC 5425: Transport Layer Security (TLS) Transport
                     Mapping for Syslog ";
                  leaf address {
                    type inet:host;
                    description
                      "The leaf uniquely specifies the address of
                       the remote host. One of the following must be
                       specified: an ipv4 address, an ipv6 address,
                       or a host name.";
                  }
                  leaf port {
                    type inet:port-number;
                    // NCS drop default statement
                    description
                      "This leaf specifies the port number used to
                       deliver messages to the remote server.";
                  }
                }
              }
            }
            uses live_ncs_syslog-selector;
            leaf destination-facility {
              type identityref {
                base syslogtypes:syslog-facility;
              }
              // NCS drop default statement
              description
                "This leaf specifies the facility used in messages
                 delivered to the remote server.";
            }
            leaf source-interface {
              type if:live_ncs_interface-ref;
              description
                "This leaf sets the source interface for the remote
                 Syslog server. Either the interface name or the
                 interface IP address can be specified. If not set,
                 messages sent to a remote syslog server will
                 contain the IP address of the interface the syslog
                 message uses to exit the network element";
            }
            uses live_ncs_syslog-structured-data;
            container syslog-sign {
              // NCS drop if-feature statement
              presence "If present, syslog-sign is activated.";
              description
                "This container describes the configuration
                 parameters for signed syslog messages as described
                 by RFC 5848.";
              reference "RFC 5848: Signed Syslog Messages";
              leaf cert-initial-repeat {
                type uint16;
                // NCS drop mandatory statement
                description
                  "This leaf specifies the number of times each
                   Certificate Block should be sent before the first
                   message is sent.";
              }
              leaf cert-resend-delay {
                type uint16;
                // NCS drop mandatory statement
                description
                  "This leaf specifies the maximum time delay in
                   seconds until resending the Certificate Block.";
              }
              leaf cert-resend-count {
                type uint16;
                // NCS drop mandatory statement
                description
                  "This leaf specifies the maximum number of other
                   syslog messages to send until resending the
                   Certificate Block.";
              }
              leaf sig-max-delay {
                type uint16;
                // NCS drop mandatory statement
                description
                  "This leaf specifies when to generate a new
                   Signature Block. If this many seconds have
                   elapsed since the message with the first message
                   number of the Signature Block was sent, a new
                   Signature Block should be generated.";
              }
              leaf sig-number-resends {
                type uint16;
                // NCS drop mandatory statement
                description
                  "This leaf specifies the number of times a
                   Signature Block is resent. (It is recommended to
                   select a value of greater than 0 in particular
                   when the UDP transport [RFC5426] is used.).";
              }
              leaf sig-resend-delay {
                type uint16;
                // NCS drop mandatory statement
                description
                  "This leaf specifies when to send the next
                   Signature Block transmission based on time. If
                   this many seconds have elapsed since the previous
                   sending of this Signature Block, resend it.";
              }
              leaf sig-resend-count {
                type uint16;
                // NCS drop mandatory statement
                description
                  "This leaf specifies when to send the next
                   Signature Block transmission based on a count.
                   If this many other syslog messages have been sent
                   since the previous sending of this Signature
                   Block, resend it.";
              }
            }
          }
        }
        container terminal {
          // NCS drop if-feature statement
          description
            "This container describes the configuration parameters for
             the terminal logging configuration.";
          container all-terminals {
            presence "Enables logging to all terminals.";
            description
              "This container describes the configuration
               parameters for all terminals.";
            uses live_ncs_syslog-selector;
          }
          list terminal {
            // NCS drop if-feature statement
            key "name";
            description
              "This list describes a collection of ";
            leaf name {
              type string;
              description
                "This leaf uniquely describes a terminal which
                 will receive log messages.";
            }
            uses live_ncs_syslog-selector;
          }
        }
        container session {
          // NCS drop if-feature statement
          description
            "This container describes the configuration parameters for
             user CLI session logging configuration.";
          container all-users {
            presence "Enables logging to all user sessions.";
            description
              "This container describes the configuration
               parameters for all users.";
            uses live_ncs_syslog-selector;
          }
          list user {
            // NCS drop if-feature statement
            key "name";
            description
              "This list describes a collection of user names.";
            leaf name {
              type string;
              description
                "This leaf uniquely describes a user name which
                 is the login name of the user whose session
                 is to receive log messages.";
            }
            uses live_ncs_syslog-selector;
          }
        }
      }
    }
  }
  augment "/ncs:devices/ncs:template/ncs:ned-id/ncs:config" {
    container syslog {
      description
        "This container describes the configuration parameters for
         Syslog.";
      container log-actions {
        description
          "This container describes the log-action parameters
           for Syslog.";
        container console {
          // NCS drop if-feature statement
          presence "Enables logging console configuration";
          description
            "This container describes the configuration parameters for
             console logging.";
          uses ncs_template_syslog-selector;
        }
        container buffer {
          // NCS drop if-feature statement
          description
            "This container describes the configuration parameters for
             local memory buffer logging. The buffer is circular in
             nature, so newer messages overwrite older messages after
             the buffer is filled. The method used to read syslog messages
             from the buffer is supplied by the local implementation.";
          list log-buffer {
            // NCS patched for predictable order
            ordered-by user;
            key "name";
            description
              "This list describes a collection of local logging
               memory buffers. If buffer size limits are not supplied, it
               is assumed that the local implementation defined
               limits will be used.";
            leaf name {
              type string;
              description
                "This leaf specifies the name of the log buffer.";
            }
            uses ncs_template_syslog-selector;
            leaf buffer-size-bytes {
              // NCS drop if-feature statement
              type string;
              units "bytes";
              description
                "This leaf configures the amount of memory (in bytes) that
                 will be dedicated to the local memory logging buffer.
                 The default value varies by implementation.";
            }
            leaf buffer-size-messages {
              // NCS drop if-feature statement
              type string;
              units "log messages";
              description
                "This leaf configures the amount number of log messages that
                 can be stored in the local memory logging buffer. The
                 default value varies by implementation.";
            }
            uses ncs_template_syslog-structured-data;
          }
        }
        container file {
          description
            "This container describes the configuration parameters for
             file logging. If file-archive limits are not supplied, it
             is assumed that the local implementation defined limits will
             be used.";
          list log-file {
            // NCS patched for predictable order
            ordered-by user;
            key "name";
            description
              "This list describes a collection of local logging
               files.";
            leaf name {
              type string;
              description
                "This leaf specifies the name of the log file which
                 MUST use the uri scheme file:.";
            }
            uses ncs_template_syslog-selector;
            uses ncs_template_syslog-structured-data;
            container file-archive {
              description
                "This container describes the configuration
                 parameters for log file archiving.";
              leaf number-of-files {
                // NCS drop if-feature statement
                type string;
                description
                  "This leaf specifies the maximum number of log
                   files retained. Specify 1 for implementations
                   that only support one log file.";
              }
              leaf max-file-size {
                // NCS drop if-feature statement
                type string;
                units "megabytes";
                description
                  "This leaf specifies the maximum log file size.";
              }
              leaf rollover {
                // NCS drop if-feature statement
                type string;
                units "minutes";
                description
                  "This leaf specifies the length of time that log
                   events should be written to a specific log file.
                   Log events that arrive after the rollover period
                   cause the current log file to be closed and a new
                   log file to be opened.";
              }
              leaf retention {
                // NCS drop if-feature statement
                type string;
                units "hours";
                description
                  "This leaf specifies the length of time that
                   completed/closed log event files should be stored
                   in the file system before they are deleted.";
              }
            }
          }
        }
        container remote {
          description
            "This container describes the configuration parameters for
             remote logging.";
          list destination {
            // NCS patched for predictable order
            ordered-by user;
            key "name";
            description
              "This list describes a collection of remote logging
               destinations.";
            leaf name {
              type string;
              description
                "An arbitrary name for the endpoint to connect to.";
            }
            choice transport {
              // NCS drop mandatory statement
              description
                "This choice describes the transport option.";
              case tcp {
                container tcp {
                  description
                    "This container describes the TCP transport
                     options.";
                  reference "RFC 6587: Transmission of Syslog Messages over TCP";
                  leaf address {
                    type string;
                    description
                      "The leaf uniquely specifies the address of
                       the remote host. One of the following must
                       be specified: an ipv4 address, an ipv6
                       address, or a host name.";
                  }
                  leaf port {
                    type string;
                    // NCS drop default statement
                    description
                      "This leaf specifies the port number used to
                       deliver messages to the remote server.";
                  }
                }
              }
              case udp {
                container udp {
                  description
                    "This container describes the UDP transport
                     options.";
                  reference "RFC 5426: Transmission of Syslog Messages over UDP";
                  leaf address {
                    type string;
                    description
                      "The leaf uniquely specifies the address of
                       the remote host. One of the following must be
                       specified: an ipv4 address, an ipv6 address,
                       or a host name.";
                  }
                  leaf port {
                    type string;
                    // NCS drop default statement
                    description
                      "This leaf specifies the port number used to
                       deliver messages to the remote server.";
                  }
                }
              }
              case tls {
                container tls {
                  description
                    "This container describes the TLS transport options.";
                  reference
                    "RFC 5425: Transport Layer Security (TLS) Transport
                     Mapping for Syslog ";
                  leaf address {
                    type string;
                    description
                      "The leaf uniquely specifies the address of
                       the remote host. One of the following must be
                       specified: an ipv4 address, an ipv6 address,
                       or a host name.";
                  }
                  leaf port {
                    type string;
                    // NCS drop default statement
                    description
                      "This leaf specifies the port number used to
                       deliver messages to the remote server.";
                  }
                }
              }
            }
            uses ncs_template_syslog-selector;
            leaf destination-facility {
              type string;
              // NCS drop default statement
              description
                "This leaf specifies the facility used in messages
                 delivered to the remote server.";
            }
            leaf source-interface {
              type if:ncs_template_interface-ref;
              description
                "This leaf sets the source interface for the remote
                 Syslog server. Either the interface name or the
                 interface IP address can be specified. If not set,
                 messages sent to a remote syslog server will
                 contain the IP address of the interface the syslog
                 message uses to exit the network element";
            }
            uses ncs_template_syslog-structured-data;
            container syslog-sign {
              // NCS drop if-feature statement
              presence "If present, syslog-sign is activated.";
              description
                "This container describes the configuration
                 parameters for signed syslog messages as described
                 by RFC 5848.";
              reference "RFC 5848: Signed Syslog Messages";
              leaf cert-initial-repeat {
                type string;
                // NCS drop mandatory statement
                description
                  "This leaf specifies the number of times each
                   Certificate Block should be sent before the first
                   message is sent.";
              }
              leaf cert-resend-delay {
                type string;
                // NCS drop mandatory statement
                description
                  "This leaf specifies the maximum time delay in
                   seconds until resending the Certificate Block.";
              }
              leaf cert-resend-count {
                type string;
                // NCS drop mandatory statement
                description
                  "This leaf specifies the maximum number of other
                   syslog messages to send until resending the
                   Certificate Block.";
              }
              leaf sig-max-delay {
                type string;
                // NCS drop mandatory statement
                description
                  "This leaf specifies when to generate a new
                   Signature Block. If this many seconds have
                   elapsed since the message with the first message
                   number of the Signature Block was sent, a new
                   Signature Block should be generated.";
              }
              leaf sig-number-resends {
                type string;
                // NCS drop mandatory statement
                description
                  "This leaf specifies the number of times a
                   Signature Block is resent. (It is recommended to
                   select a value of greater than 0 in particular
                   when the UDP transport [RFC5426] is used.).";
              }
              leaf sig-resend-delay {
                type string;
                // NCS drop mandatory statement
                description
                  "This leaf specifies when to send the next
                   Signature Block transmission based on time. If
                   this many seconds have elapsed since the previous
                   sending of this Signature Block, resend it.";
              }
              leaf sig-resend-count {
                type string;
                // NCS drop mandatory statement
                description
                  "This leaf specifies when to send the next
                   Signature Block transmission based on a count.
                   If this many other syslog messages have been sent
                   since the previous sending of this Signature
                   Block, resend it.";
              }
            }
          }
        }
        container terminal {
          // NCS drop if-feature statement
          description
            "This container describes the configuration parameters for
             the terminal logging configuration.";
          container all-terminals {
            presence "Enables logging to all terminals.";
            description
              "This container describes the configuration
               parameters for all terminals.";
            uses ncs_template_syslog-selector;
          }
          list terminal {
            // NCS patched for predictable order
            ordered-by user;
            // NCS drop if-feature statement
            key "name";
            description
              "This list describes a collection of ";
            leaf name {
              type string;
              description
                "This leaf uniquely describes a terminal which
                 will receive log messages.";
            }
            uses ncs_template_syslog-selector;
          }
        }
        container session {
          // NCS drop if-feature statement
          description
            "This container describes the configuration parameters for
             user CLI session logging configuration.";
          container all-users {
            presence "Enables logging to all user sessions.";
            description
              "This container describes the configuration
               parameters for all users.";
            uses ncs_template_syslog-selector;
          }
          list user {
            // NCS patched for predictable order
            ordered-by user;
            // NCS drop if-feature statement
            key "name";
            description
              "This list describes a collection of user names.";
            leaf name {
              type string;
              description
                "This leaf uniquely describes a user name which
                 is the login name of the user whose session
                 is to receive log messages.";
            }
            uses ncs_template_syslog-selector;
          }
        }
      }
    }
  }

  feature signed-messages-config {
    description
      "This feature represents the ability to configure signed
       syslog messages according to RFC 5848.";
  }

  feature structured-data-config {
    description
      "This feature represents the ability to log messages
       in structured-data format as per RFC 5424.";
  }

  feature selector-match-config {
    description
      "This feature represents the ability to select messages based
       on a Posix 1003.2 regular expression pattern match.";
  }

  feature selector-sevop-config {
    description
      "This feature represents the ability to select messages
       using the additional operators equal to, or not equal to
       when comparing the Syslog message severity.";
  }

  feature session-facility-user-logging-config {
    description
      "This feature represents the ability to adjust
       log message settings for individual user CLI
       sessions.";
  }

  feature session-action {
    description
      "This feature indicates that logging to user
       CLI session is supported.";
  }

  feature terminal-facility-user-logging-config {
    description
      "This feature represents the ability to adjust
       log message settings for individual terminal
       devices.";
  }

  feature terminal-action {
    description
      "This feature indicates that logging to a terminal
       is supported.";
  }

  feature file-limit-duration {
    description
      "This feature indicates that file logging resources
       are managed using time based limits.";
  }

  feature file-limit-size {
    description
      "This feature indicates that file logging resources
       are managed using size and number limits.";
  }

  feature buffer-limit-messages {
    description
      "This feature indicates that local memory logging buffers
       are limited in size using a limit expressed in number
       of messages.";
  }

  feature buffer-limit-bytes {
    description
      "This feature indicates that local memory logging buffers
       are limited in size using a limit expressed in bytes.";
  }

  feature buffer-action {
    description
      "This feature indicates that logging to an in-memory
       buffer is supported.";
  }

  feature console-action {
    description
      "This feature indicates that logging to the console is
       supported.";
  }
}
