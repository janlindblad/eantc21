module ciena-te {
  // Generated by yanger -t ncs
  tailf:mount-id "saos1051-nc-1.0:saos1051-nc-1.0";
  tailf:ncs-device-type "netconf";

  namespace "http://ciena.com/ns/yang/ciena-te";
  prefix te;

  import ietf-inet-types {
    prefix inet;
  }
  import ietf-te-types {
    prefix te-types;
  }
  import ietf-sr-policy-types {
    prefix ietf-sr-policy-types;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Phone:   +1 408-904-2139
     Fax:     +1 410-694-5750";
  description
    "This YANG module defines Ciena's specific Segme/exnt Routing(SR) protocol

     Copyright (c) 2018  Ciena Corporation.  All rights
     reserved.

     All information contained herein is, and remains the
     property of Ciena Corporation. Dissemination of this
     information or reproduction of this material is strictly
     forbidden unless prior written permission is obtained
     from Ciena Corporation.";

  revision 2019-05-06 {
    description
      "added candidate path in config and oper data";
    reference "RFC XXXX";
  }
  revision 2018-10-23 {
    description
      "Based off of ciena-te.yang";
    reference "RFC XXXX";
  }

  grouping ncs_template_te-type {
    choice type {
      description
        "The explicit route subobject type";
      case num-unnum-hop {
        container num-unnum-hop {
          leaf node-id {
            type te-types:ncs_template_te-node-id;
            description
              "The identifier of a node in the TE topology.";
          }
          leaf link-tp-id {
            type te-types:ncs_template_te-tp-id;
            description
              "TE link termination point identifier. The combination
               of TE link ID and the TE node ID is used to identify an
               unnumbered TE link.";
          }
          leaf hop-type {
            type te-types:ncs_template_te-hop-type;
            // NCS drop default statement
            description
              "strict or loose hop";
          }
          leaf direction {
            type te-types:ncs_template_te-link-direction;
            // NCS drop default statement
            description
              "Link ERO direction";
          }
          description
            "Numbered and Unnumbered link/node explicit route
             subobject";
          reference
            "RFC3209: section 4.3 for EXPLICIT_ROUTE in RSVP-TE
             RFC3477: Signalling Unnumbered Links in RSVP-TE";
        }
      }
      case label {
        container label-hop {
          leaf te-label {
            type string;
            description
              "Label value";
          }
        }
      }
    }
  }

  grouping ncs_template_mpls-path-mode {
    description
      "Mpls path mode group";
    list mpls-path {
      // NCS patched for predictable order
      ordered-by user;
      key "name";
      description
        "show data for mpls te path";
      leaf name {
        type string;
        description
          "MPLS path name";
      }
      leaf path-id {
        type string;
        description
          " Tunnel path id";
      }
      leaf hop-count {
        type string;
        description
          "Tunnel hop count";
      }
      list path-hop {
        // NCS patched for predictable order
        ordered-by user;
        key "index";
        description
          "Hop address and type";
        leaf index {
          type string;
          description
            "route-object-include-exclude index";
        }
        leaf node-id {
          type te-types:ncs_template_te-node-id;
          description
            "The identifier of a node in the TE topology.";
        }
        leaf link-tp-id {
          type te-types:ncs_template_te-tp-id;
          description
            "TE link termination point identifier. The combination
             of TE link ID and the TE node ID is used to identify an
             unnumbered TE link.";
        }
        leaf hop-type {
          type te-types:ncs_template_te-hop-type;
          description
            "strict or loose hop";
        }
        leaf te-label {
          type string;
          description
            "Label value";
        }
      }
    }
  }

  grouping ncs_template_tunnel-state {
    description
      "Mpls tunnel state ";
    container tunnels {
      description
        "TE tunnels count summary";
      container summary {
        leaf tunnel-count {
          type string;
          description
            "Tunnel count";
        }
      }
      list tunnel {
        // NCS patched for predictable order
        ordered-by user;
        key "name";
        description
          "TE tunnel summary";
        leaf name {
          type string;
          description
            "Tunnel Name";
        }
        leaf identifier {
          type string;
          description
            "Tunnel index";
        }
        leaf source {
          type string;
          description
            " Source ip for the path";
        }
        leaf destination {
          type string;
          description
            " Destination ip for the path";
        }
        leaf color {
          type string;
          description
            "Color associated with the policy";
        }
        leaf in-label {
          type string;
          description
            "Tunnel in label";
        }
        leaf out-labels {
          type string;
          description
            "Tunnel Out labels";
        }
        leaf incoming-interface-name {
          type string;
          description
            "incoming interface name.";
        }
        leaf outgoing-interface-name {
          type string;
          description
            "outgoing interface name.";
        }
        leaf oper-status {
          type string;
          description
            "Tunnel oper status";
        }
        leaf admin-status {
          type string;
          description
            "Tunnel Admin status";
        }
        leaf tunnel-type {
          type string;
          description
            "Tunnel Type";
        }
        leaf signaling-type {
          type string;
          description
            "Signalling type of tunnel";
        }
        leaf create-time {
          type string;
          description
            "Creation time of tunnel";
        }
        leaf up-time {
          type string;
          description
            "Tunnel Up time";
        }
        container binding-sid {
          leaf alloc-mode {
            type ietf-sr-policy-types:ncs_template_binding-sid-alloc-mode;
            description
              "Binding SID Types";
          }
          leaf allocated-sid {
            type string;
            description
              "Allocated SID value for the Binding SID";
          }
        }
        uses ncs_template_candidate-paths-state;
        container segment-info {
          leaf segment-count {
            type string;
            description
              "Total segment count";
          }
          list active-segment-list {
            // NCS patched for predictable order
            ordered-by user;
            key "index";
            description
              "Active segment list";
            leaf index {
              type string;
              description
                "Index value of segment list";
            }
            leaf path-type {
              type string;
              description
                "segment list path type";
            }
            leaf hop-address {
              type string;
              description
                "segment list address";
            }
            leaf label {
              type string;
              description
                "segment list label value";
            }
          }
        }
      }
    }
  }

  grouping ncs_template_sr-path {
    description
      " Segment Routing Path Grouping";
    leaf source {
      type string;
      description
        " Source ip for the tunnel";
    }
    leaf destination {
      type string;
      description
        " Destination ip for the tunnel";
    }
  }

  grouping ncs_template_binding-sid_config {
    description
      "Binding SID configuration properties grouping";
    leaf dataplane {
      type ietf-sr-policy-types:ncs_template_dataplane-type;
      description
        "Binding SID dataplane type";
    }
    leaf value {
      type ietf-sr-policy-types:ncs_template_sid-value-type;
      description
        "Binding SID value";
    }
  }

  grouping ncs_template_explicit-path-properties {
    description
      "Explicit path properties of the candidate path";
    container segment-lists {
      description
        "Path segment list(s) properties";
      list segment-list {
        // NCS patched for predictable order
        ordered-by user;
        key "name-ref";
        // NCS drop max-elements statement
        description
          "SR policy candidate path segment lists";
        leaf name-ref {
          type string;
          description
            "Reference to segment-list name";
        }
      }
    }
  }

  grouping ncs_template_candidate-path-type {
    description
      "Candidate path type grouping";
    choice type {
      description
        "Type of candidate paths";
      case explicit {
        description
          "Candidate path with explicitly defined set/s of segment-lists";
        uses ncs_template_explicit-path-properties;
      }
    }
  }

  grouping ncs_template_candidate-paths {
    description
      "SR policy candidate path grouping";
    container candidate-paths {
      description
        "SR policy candidate path(s) ";
      list candidate-path {
        // NCS patched for predictable order
        ordered-by user;
        key "protocol-origin originator discriminator";
        // NCS drop max-elements statement
        description
          "SR policy Candidate path(s) list entry";
        leaf protocol-origin {
          type ietf-sr-policy-types:ncs_template_protocol-origin-type;
          description
            "Instantiation mechanism used to create the candidate path";
        }
        leaf originator {
          type string;
          description
            "Identifier (concatenation of ASN and node-address) of the node
             that signalled/instantiated the candidate path on headend";
        }
        leaf discriminator {
          type string;
          description
            "Candidate path distinguisher";
        }
        leaf preference {
          type string;
          // NCS drop mandatory statement
          description
            "Candidate path preference";
        }
        leaf description {
          type string;
          description
            "Candidate path description";
        }
        leaf isis-tag {
          type string;
          // NCS drop mandatory statement
          description
            "ISIS Instance Area Tag";
        }
        uses ncs_template_candidate-path-type;
      }
    }
  }

  grouping ncs_template_candidate-paths-state {
    description
      "SR policy candidate path grouping";
    container candidate-paths {
      description
        "SR policy candidate path(s) ";
      list candidate-path {
        // NCS patched for predictable order
        ordered-by user;
        key "protocol-origin originator discriminator";
        description
          "SR policy Candidate path(s) list entry";
        leaf protocol-origin {
          type ietf-sr-policy-types:ncs_template_protocol-origin-type;
          description
            "Instantiation mechanism used to create the candidate path";
        }
        leaf originator {
          type string;
          description
            "Identifier (concatenation of ASN and node-address) of the node
             that signalled/instantiated the candidate path on headend";
        }
        leaf discriminator {
          type string;
          description
            "Candidate path distinguisher";
        }
        leaf preference {
          type string;
          description
            "Candidate path preference";
        }
        leaf is-best-candidate-path {
          type string;
          description
            "Best candidate path";
        }
        leaf type {
          type string;
          description
            "Type of candidate paths";
        }
        container segment-lists {
          description
            "Path segment list(s) properties";
          list segment-list {
            // NCS patched for predictable order
            ordered-by user;
            key "name-ref";
            description
              "SR policy candidate path segment lists";
            leaf name-ref {
              type string;
              description
                "Reference to segment-list name";
            }
            leaf is-valid {
              type string;
              description
                "Segment-list weighted loadshare";
            }
            leaf hop-count {
              type string;
              description
                "Candidate path distinguisher";
            }
            list hop-list {
              // NCS patched for predictable order
              ordered-by user;
              key "hop-index";
              description
                "SR policy candidate path segment lists";
              leaf hop-index {
                type string;
                description
                  "Reference to segment-list name";
              }
              leaf hop-address {
                type string;
                description
                  "Reference to segment-list name";
              }
              leaf label {
                type string;
                description
                  "segment list label value";
              }
            }
          }
        }
      }
    }
  }

  grouping ncs_rpc_notif_te-type {
    choice type {
      description
        "The explicit route subobject type";
      case num-unnum-hop {
        container num-unnum-hop {
          leaf node-id {
            type te-types:ncs_rpc_notif_te-node-id;
            description
              "The identifier of a node in the TE topology.";
          }
          leaf link-tp-id {
            type te-types:ncs_rpc_notif_te-tp-id;
            description
              "TE link termination point identifier. The combination
               of TE link ID and the TE node ID is used to identify an
               unnumbered TE link.";
          }
          leaf hop-type {
            type te-types:ncs_rpc_notif_te-hop-type;
            default "LOOSE";
            description
              "strict or loose hop";
          }
          leaf direction {
            type te-types:ncs_rpc_notif_te-link-direction;
            default "INCOMING";
            description
              "Link ERO direction";
          }
          description
            "Numbered and Unnumbered link/node explicit route
             subobject";
          reference
            "RFC3209: section 4.3 for EXPLICIT_ROUTE in RSVP-TE
             RFC3477: Signalling Unnumbered Links in RSVP-TE";
        }
      }
      case label {
        container label-hop {
          leaf te-label {
            type uint32 {
              range "0..1048575";
            }
            description
              "Label value";
          }
        }
      }
    }
  }

  grouping ncs_rpc_notif_mpls-path-mode {
    description
      "Mpls path mode group";
    list mpls-path {
      key "name";
      description
        "show data for mpls te path";
      leaf name {
        type string;
        description
          "MPLS path name";
      }
      leaf path-id {
        type uint32;
        description
          " Tunnel path id";
      }
      leaf hop-count {
        type uint16;
        description
          "Tunnel hop count";
      }
      list path-hop {
        key "index";
        description
          "Hop address and type";
        leaf index {
          type uint32;
          description
            "route-object-include-exclude index";
        }
        leaf node-id {
          type te-types:ncs_rpc_notif_te-node-id;
          description
            "The identifier of a node in the TE topology.";
        }
        leaf link-tp-id {
          type te-types:ncs_rpc_notif_te-tp-id;
          description
            "TE link termination point identifier. The combination
             of TE link ID and the TE node ID is used to identify an
             unnumbered TE link.";
        }
        leaf hop-type {
          type te-types:ncs_rpc_notif_te-hop-type;
          description
            "strict or loose hop";
        }
        leaf te-label {
          type uint32;
          description
            "Label value";
        }
      }
    }
  }

  grouping ncs_rpc_notif_tunnel-state {
    description
      "Mpls tunnel state ";
    container tunnels {
      description
        "TE tunnels count summary";
      container summary {
        leaf tunnel-count {
          type uint16;
          description
            "Tunnel count";
        }
      }
      list tunnel {
        key "name";
        description
          "TE tunnel summary";
        leaf name {
          type string;
          description
            "Tunnel Name";
        }
        leaf identifier {
          type uint16;
          description
            "Tunnel index";
        }
        leaf source {
          type inet:ipv4-address;
          description
            " Source ip for the path";
        }
        leaf destination {
          type inet:ipv4-address;
          description
            " Destination ip for the path";
        }
        leaf color {
          type uint32;
          description
            "Color associated with the policy";
        }
        leaf in-label {
          type uint32;
          description
            "Tunnel in label";
        }
        leaf out-labels {
          type string;
          description
            "Tunnel Out labels";
        }
        leaf incoming-interface-name {
          type string;
          description
            "incoming interface name.";
        }
        leaf outgoing-interface-name {
          type string;
          description
            "outgoing interface name.";
        }
        leaf oper-status {
          type string {
            length "0..255";
          }
          description
            "Tunnel oper status";
        }
        leaf admin-status {
          type string {
            length "0..255";
          }
          description
            "Tunnel Admin status";
        }
        leaf tunnel-type {
          type string {
            length "0..255";
          }
          description
            "Tunnel Type";
        }
        leaf signaling-type {
          type string {
            length "0..255";
          }
          description
            "Signalling type of tunnel";
        }
        leaf create-time {
          type string;
          description
            "Creation time of tunnel";
        }
        leaf up-time {
          type string;
          description
            "Tunnel Up time";
        }
        container binding-sid {
          leaf alloc-mode {
            type ietf-sr-policy-types:ncs_rpc_notif_binding-sid-alloc-mode;
            description
              "Binding SID Types";
          }
          leaf allocated-sid {
            type uint32;
            description
              "Allocated SID value for the Binding SID";
          }
        }
        uses ncs_rpc_notif_candidate-paths-state;
        container segment-info {
          leaf segment-count {
            type uint32;
            description
              "Total segment count";
          }
          list active-segment-list {
            key "index";
            description
              "Active segment list";
            leaf index {
              type uint32;
              description
                "Index value of segment list";
            }
            leaf path-type {
              type string;
              description
                "segment list path type";
            }
            leaf hop-address {
              type inet:ipv4-prefix;
              description
                "segment list address";
            }
            leaf label {
              type uint32;
              description
                "segment list label value";
            }
          }
        }
      }
    }
  }

  grouping ncs_rpc_notif_sr-path {
    description
      " Segment Routing Path Grouping";
    leaf source {
      type inet:ipv4-address;
      description
        " Source ip for the tunnel";
    }
    leaf destination {
      type inet:ipv4-address;
      description
        " Destination ip for the tunnel";
    }
  }

  grouping ncs_rpc_notif_binding-sid_config {
    description
      "Binding SID configuration properties grouping";
    leaf dataplane {
      type ietf-sr-policy-types:ncs_rpc_notif_dataplane-type;
      description
        "Binding SID dataplane type";
    }
    leaf value {
      type ietf-sr-policy-types:ncs_rpc_notif_sid-value-type;
      description
        "Binding SID value";
    }
  }

  grouping ncs_rpc_notif_explicit-path-properties {
    description
      "Explicit path properties of the candidate path";
    container segment-lists {
      description
        "Path segment list(s) properties";
      list segment-list {
        key "name-ref";
        max-elements 1;
        description
          "SR policy candidate path segment lists";
        leaf name-ref {
          type string;
          description
            "Reference to segment-list name";
        }
      }
    }
  }

  grouping ncs_rpc_notif_candidate-path-type {
    description
      "Candidate path type grouping";
    choice type {
      description
        "Type of candidate paths";
      case explicit {
        description
          "Candidate path with explicitly defined set/s of segment-lists";
        uses ncs_rpc_notif_explicit-path-properties;
      }
    }
  }

  grouping ncs_rpc_notif_candidate-paths {
    description
      "SR policy candidate path grouping";
    container candidate-paths {
      description
        "SR policy candidate path(s) ";
      list candidate-path {
        key "protocol-origin originator discriminator";
        max-elements 1;
        description
          "SR policy Candidate path(s) list entry";
        leaf protocol-origin {
          type ietf-sr-policy-types:ncs_rpc_notif_protocol-origin-type;
          description
            "Instantiation mechanism used to create the candidate path";
        }
        leaf originator {
          type string;
          description
            "Identifier (concatenation of ASN and node-address) of the node
             that signalled/instantiated the candidate path on headend";
        }
        leaf discriminator {
          type uint32 {
            range "1..65535";
          }
          description
            "Candidate path distinguisher";
        }
        leaf preference {
          type uint32 {
            range "1..100";
          }
          mandatory true;
          description
            "Candidate path preference";
        }
        leaf description {
          type string;
          description
            "Candidate path description";
        }
        leaf isis-tag {
          type string;
          mandatory true;
          description
            "ISIS Instance Area Tag";
        }
        uses ncs_rpc_notif_candidate-path-type;
      }
    }
  }

  grouping ncs_rpc_notif_candidate-paths-state {
    description
      "SR policy candidate path grouping";
    container candidate-paths {
      description
        "SR policy candidate path(s) ";
      list candidate-path {
        key "protocol-origin originator discriminator";
        description
          "SR policy Candidate path(s) list entry";
        leaf protocol-origin {
          type ietf-sr-policy-types:ncs_rpc_notif_protocol-origin-type;
          description
            "Instantiation mechanism used to create the candidate path";
        }
        leaf originator {
          type string;
          description
            "Identifier (concatenation of ASN and node-address) of the node
             that signalled/instantiated the candidate path on headend";
        }
        leaf discriminator {
          type uint32;
          description
            "Candidate path distinguisher";
        }
        leaf preference {
          type uint32;
          description
            "Candidate path preference";
        }
        leaf is-best-candidate-path {
          type boolean;
          description
            "Best candidate path";
        }
        leaf type {
          type string;
          description
            "Type of candidate paths";
        }
        container segment-lists {
          description
            "Path segment list(s) properties";
          list segment-list {
            key "name-ref";
            description
              "SR policy candidate path segment lists";
            leaf name-ref {
              type string;
              description
                "Reference to segment-list name";
            }
            leaf is-valid {
              type boolean;
              description
                "Segment-list weighted loadshare";
            }
            leaf hop-count {
              type uint32;
              description
                "Candidate path distinguisher";
            }
            list hop-list {
              key "hop-index";
              description
                "SR policy candidate path segment lists";
              leaf hop-index {
                type uint32;
                description
                  "Reference to segment-list name";
              }
              leaf hop-address {
                type inet:ipv4-prefix;
                description
                  "Reference to segment-list name";
              }
              leaf label {
                type uint32;
                description
                  "segment list label value";
              }
            }
          }
        }
      }
    }
  }

  grouping live_ncs_te-type {
    choice type {
      description
        "The explicit route subobject type";
      case num-unnum-hop {
        container num-unnum-hop {
          leaf node-id {
            type te-types:live_ncs_te-node-id;
            description
              "The identifier of a node in the TE topology.";
          }
          leaf link-tp-id {
            type te-types:live_ncs_te-tp-id;
            description
              "TE link termination point identifier. The combination
               of TE link ID and the TE node ID is used to identify an
               unnumbered TE link.";
          }
          leaf hop-type {
            type te-types:live_ncs_te-hop-type;
            // NCS drop default statement
            description
              "strict or loose hop";
          }
          leaf direction {
            type te-types:live_ncs_te-link-direction;
            // NCS drop default statement
            description
              "Link ERO direction";
          }
          description
            "Numbered and Unnumbered link/node explicit route
             subobject";
          reference
            "RFC3209: section 4.3 for EXPLICIT_ROUTE in RSVP-TE
             RFC3477: Signalling Unnumbered Links in RSVP-TE";
        }
      }
      case label {
        container label-hop {
          leaf te-label {
            type uint32 {
              range "0..1048575";
            }
            description
              "Label value";
          }
        }
      }
    }
  }

  grouping live_ncs_mpls-path-mode {
    description
      "Mpls path mode group";
    list mpls-path {
      key "name";
      description
        "show data for mpls te path";
      leaf name {
        type leafref {
          path "/ncs:devices/ncs:device/ncs:live-status/te:te/te:globals/te:mpls-paths/te:mpls-path/te:name" {
            tailf:xpath-root 3;
          }
        }
        description
          "MPLS path name";
      }
      leaf path-id {
        type uint32;
        description
          " Tunnel path id";
      }
      leaf hop-count {
        type uint16;
        description
          "Tunnel hop count";
      }
      list path-hop {
        key "index";
        description
          "Hop address and type";
        leaf index {
          type uint32;
          description
            "route-object-include-exclude index";
        }
        leaf node-id {
          type te-types:live_ncs_te-node-id;
          description
            "The identifier of a node in the TE topology.";
        }
        leaf link-tp-id {
          type te-types:live_ncs_te-tp-id;
          description
            "TE link termination point identifier. The combination
             of TE link ID and the TE node ID is used to identify an
             unnumbered TE link.";
        }
        leaf hop-type {
          type te-types:live_ncs_te-hop-type;
          description
            "strict or loose hop";
        }
        leaf te-label {
          type uint32;
          description
            "Label value";
        }
      }
    }
  }

  grouping live_ncs_tunnel-state {
    description
      "Mpls tunnel state ";
    container tunnels {
      description
        "TE tunnels count summary";
      container summary {
        leaf tunnel-count {
          type uint16;
          description
            "Tunnel count";
        }
      }
      list tunnel {
        key "name";
        description
          "TE tunnel summary";
        leaf name {
          type leafref {
            path "/ncs:devices/ncs:device/ncs:live-status/te:te/te:tunnels/te:tunnel/te:name" {
              tailf:xpath-root 3;
            }
          }
          description
            "Tunnel Name";
        }
        leaf identifier {
          type uint16;
          description
            "Tunnel index";
        }
        leaf source {
          type inet:ipv4-address;
          description
            " Source ip for the path";
        }
        leaf destination {
          type inet:ipv4-address;
          description
            " Destination ip for the path";
        }
        leaf color {
          type uint32;
          description
            "Color associated with the policy";
        }
        leaf in-label {
          type uint32;
          description
            "Tunnel in label";
        }
        leaf out-labels {
          type string;
          description
            "Tunnel Out labels";
        }
        leaf incoming-interface-name {
          type string;
          description
            "incoming interface name.";
        }
        leaf outgoing-interface-name {
          type string;
          description
            "outgoing interface name.";
        }
        leaf oper-status {
          type string {
            length "0..255";
          }
          description
            "Tunnel oper status";
        }
        leaf admin-status {
          type string {
            length "0..255";
          }
          description
            "Tunnel Admin status";
        }
        leaf tunnel-type {
          type string {
            length "0..255";
          }
          description
            "Tunnel Type";
        }
        leaf signaling-type {
          type string {
            length "0..255";
          }
          description
            "Signalling type of tunnel";
        }
        leaf create-time {
          type string;
          description
            "Creation time of tunnel";
        }
        leaf up-time {
          type string;
          description
            "Tunnel Up time";
        }
        container binding-sid {
          leaf alloc-mode {
            type ietf-sr-policy-types:live_ncs_binding-sid-alloc-mode;
            description
              "Binding SID Types";
          }
          leaf allocated-sid {
            type uint32;
            description
              "Allocated SID value for the Binding SID";
          }
        }
        uses live_ncs_candidate-paths-state;
        container segment-info {
          leaf segment-count {
            type uint32;
            description
              "Total segment count";
          }
          list active-segment-list {
            key "index";
            description
              "Active segment list";
            leaf index {
              type uint32;
              description
                "Index value of segment list";
            }
            leaf path-type {
              type string;
              description
                "segment list path type";
            }
            leaf hop-address {
              type inet:ipv4-prefix;
              description
                "segment list address";
            }
            leaf label {
              type uint32;
              description
                "segment list label value";
            }
          }
        }
      }
    }
  }

  grouping live_ncs_sr-path {
    description
      " Segment Routing Path Grouping";
    leaf source {
      type inet:ipv4-address;
      description
        " Source ip for the tunnel";
    }
    leaf destination {
      type inet:ipv4-address;
      description
        " Destination ip for the tunnel";
    }
  }

  grouping live_ncs_binding-sid_config {
    description
      "Binding SID configuration properties grouping";
    leaf dataplane {
      type ietf-sr-policy-types:live_ncs_dataplane-type;
      description
        "Binding SID dataplane type";
    }
    leaf value {
      type ietf-sr-policy-types:live_ncs_sid-value-type;
      description
        "Binding SID value";
    }
  }

  grouping live_ncs_explicit-path-properties {
    description
      "Explicit path properties of the candidate path";
    container segment-lists {
      description
        "Path segment list(s) properties";
      list segment-list {
        key "name-ref";
        // NCS drop max-elements statement
        description
          "SR policy candidate path segment lists";
        leaf name-ref {
          type leafref {
            path "/ncs:devices/ncs:device/ncs:live-status/te:te/te:globals/te:mpls-paths/te:mpls-path/te:name" {
              tailf:xpath-root 3;
            }
          }
          description
            "Reference to segment-list name";
        }
      }
    }
  }

  grouping live_ncs_candidate-path-type {
    description
      "Candidate path type grouping";
    choice type {
      description
        "Type of candidate paths";
      case explicit {
        description
          "Candidate path with explicitly defined set/s of segment-lists";
        uses live_ncs_explicit-path-properties;
      }
    }
  }

  grouping live_ncs_candidate-paths {
    description
      "SR policy candidate path grouping";
    container candidate-paths {
      description
        "SR policy candidate path(s) ";
      list candidate-path {
        key "protocol-origin originator discriminator";
        // NCS drop max-elements statement
        description
          "SR policy Candidate path(s) list entry";
        leaf protocol-origin {
          type ietf-sr-policy-types:live_ncs_protocol-origin-type;
          description
            "Instantiation mechanism used to create the candidate path";
        }
        leaf originator {
          type string;
          description
            "Identifier (concatenation of ASN and node-address) of the node
             that signalled/instantiated the candidate path on headend";
        }
        leaf discriminator {
          type uint32 {
            range "1..65535";
          }
          description
            "Candidate path distinguisher";
        }
        leaf preference {
          type uint32 {
            range "1..100";
          }
          // NCS drop mandatory statement
          description
            "Candidate path preference";
        }
        leaf description {
          type string;
          description
            "Candidate path description";
        }
        leaf isis-tag {
          type string;
          // NCS drop mandatory statement
          description
            "ISIS Instance Area Tag";
        }
        uses live_ncs_candidate-path-type;
      }
    }
  }

  grouping live_ncs_candidate-paths-state {
    description
      "SR policy candidate path grouping";
    container candidate-paths {
      description
        "SR policy candidate path(s) ";
      list candidate-path {
        key "protocol-origin originator discriminator";
        description
          "SR policy Candidate path(s) list entry";
        leaf protocol-origin {
          type ietf-sr-policy-types:live_ncs_protocol-origin-type;
          description
            "Instantiation mechanism used to create the candidate path";
        }
        leaf originator {
          type string;
          description
            "Identifier (concatenation of ASN and node-address) of the node
             that signalled/instantiated the candidate path on headend";
        }
        leaf discriminator {
          type uint32;
          description
            "Candidate path distinguisher";
        }
        leaf preference {
          type uint32;
          description
            "Candidate path preference";
        }
        leaf is-best-candidate-path {
          type boolean;
          description
            "Best candidate path";
        }
        leaf type {
          type string;
          description
            "Type of candidate paths";
        }
        container segment-lists {
          description
            "Path segment list(s) properties";
          list segment-list {
            key "name-ref";
            description
              "SR policy candidate path segment lists";
            leaf name-ref {
              type leafref {
                path "/ncs:devices/ncs:device/ncs:live-status/te:te/te:globals/te:mpls-paths/te:mpls-path/te:name" {
                  tailf:xpath-root 3;
                }
              }
              description
                "Reference to segment-list name";
            }
            leaf is-valid {
              type boolean;
              description
                "Segment-list weighted loadshare";
            }
            leaf hop-count {
              type uint32;
              description
                "Candidate path distinguisher";
            }
            list hop-list {
              key "hop-index";
              description
                "SR policy candidate path segment lists";
              leaf hop-index {
                type uint32;
                description
                  "Reference to segment-list name";
              }
              leaf hop-address {
                type inet:ipv4-prefix;
                description
                  "Reference to segment-list name";
              }
              leaf label {
                type uint32;
                description
                  "segment list label value";
              }
            }
          }
        }
      }
    }
  }

  grouping te-type {
    choice type {
      description
        "The explicit route subobject type";
      case num-unnum-hop {
        container num-unnum-hop {
          leaf node-id {
            type te-types:te-node-id;
            description
              "The identifier of a node in the TE topology.";
          }
          leaf link-tp-id {
            type te-types:te-tp-id;
            description
              "TE link termination point identifier. The combination
               of TE link ID and the TE node ID is used to identify an
               unnumbered TE link.";
          }
          leaf hop-type {
            type te-types:te-hop-type;
            default "LOOSE";
            description
              "strict or loose hop";
          }
          leaf direction {
            type te-types:te-link-direction;
            default "INCOMING";
            description
              "Link ERO direction";
          }
          description
            "Numbered and Unnumbered link/node explicit route
             subobject";
          reference
            "RFC3209: section 4.3 for EXPLICIT_ROUTE in RSVP-TE
             RFC3477: Signalling Unnumbered Links in RSVP-TE";
        }
      }
      case label {
        container label-hop {
          leaf te-label {
            type uint32 {
              range "0..1048575";
            }
            description
              "Label value";
          }
        }
      }
    }
  }

  grouping mpls-path-mode {
    description
      "Mpls path mode group";
    list mpls-path {
      key "name";
      description
        "show data for mpls te path";
      leaf name {
        type leafref {
          path "/ncs:devices/ncs:device/ncs:config/te:te/te:globals/te:mpls-paths/te:mpls-path/te:name" {
            tailf:xpath-root 3;
          }
        }
        description
          "MPLS path name";
      }
      leaf path-id {
        type uint32;
        description
          " Tunnel path id";
      }
      leaf hop-count {
        type uint16;
        description
          "Tunnel hop count";
      }
      list path-hop {
        key "index";
        description
          "Hop address and type";
        leaf index {
          type uint32;
          description
            "route-object-include-exclude index";
        }
        leaf node-id {
          type te-types:te-node-id;
          description
            "The identifier of a node in the TE topology.";
        }
        leaf link-tp-id {
          type te-types:te-tp-id;
          description
            "TE link termination point identifier. The combination
             of TE link ID and the TE node ID is used to identify an
             unnumbered TE link.";
        }
        leaf hop-type {
          type te-types:te-hop-type;
          description
            "strict or loose hop";
        }
        leaf te-label {
          type uint32;
          description
            "Label value";
        }
      }
    }
  }

  grouping tunnel-state {
    description
      "Mpls tunnel state ";
    container tunnels {
      description
        "TE tunnels count summary";
      container summary {
        leaf tunnel-count {
          type uint16;
          description
            "Tunnel count";
        }
      }
      list tunnel {
        key "name";
        description
          "TE tunnel summary";
        leaf name {
          type leafref {
            path "/ncs:devices/ncs:device/ncs:config/te:te/te:tunnels/te:tunnel/te:name" {
              tailf:xpath-root 3;
            }
          }
          description
            "Tunnel Name";
        }
        leaf identifier {
          type uint16;
          description
            "Tunnel index";
        }
        leaf source {
          type inet:ipv4-address;
          description
            " Source ip for the path";
        }
        leaf destination {
          type inet:ipv4-address;
          description
            " Destination ip for the path";
        }
        leaf color {
          type uint32;
          description
            "Color associated with the policy";
        }
        leaf in-label {
          type uint32;
          description
            "Tunnel in label";
        }
        leaf out-labels {
          type string;
          description
            "Tunnel Out labels";
        }
        leaf incoming-interface-name {
          type string;
          description
            "incoming interface name.";
        }
        leaf outgoing-interface-name {
          type string;
          description
            "outgoing interface name.";
        }
        leaf oper-status {
          type string {
            length "0..255";
          }
          description
            "Tunnel oper status";
        }
        leaf admin-status {
          type string {
            length "0..255";
          }
          description
            "Tunnel Admin status";
        }
        leaf tunnel-type {
          type string {
            length "0..255";
          }
          description
            "Tunnel Type";
        }
        leaf signaling-type {
          type string {
            length "0..255";
          }
          description
            "Signalling type of tunnel";
        }
        leaf create-time {
          type string;
          description
            "Creation time of tunnel";
        }
        leaf up-time {
          type string;
          description
            "Tunnel Up time";
        }
        container binding-sid {
          leaf alloc-mode {
            type ietf-sr-policy-types:binding-sid-alloc-mode;
            description
              "Binding SID Types";
          }
          leaf allocated-sid {
            type uint32;
            description
              "Allocated SID value for the Binding SID";
          }
        }
        uses candidate-paths-state;
        container segment-info {
          leaf segment-count {
            type uint32;
            description
              "Total segment count";
          }
          list active-segment-list {
            key "index";
            description
              "Active segment list";
            leaf index {
              type uint32;
              description
                "Index value of segment list";
            }
            leaf path-type {
              type string;
              description
                "segment list path type";
            }
            leaf hop-address {
              type inet:ipv4-prefix;
              description
                "segment list address";
            }
            leaf label {
              type uint32;
              description
                "segment list label value";
            }
          }
        }
      }
    }
  }

  grouping sr-path {
    description
      " Segment Routing Path Grouping";
    leaf source {
      type inet:ipv4-address;
      description
        " Source ip for the tunnel";
    }
    leaf destination {
      type inet:ipv4-address;
      description
        " Destination ip for the tunnel";
    }
  }

  grouping binding-sid_config {
    description
      "Binding SID configuration properties grouping";
    leaf dataplane {
      type ietf-sr-policy-types:dataplane-type;
      description
        "Binding SID dataplane type";
    }
    leaf value {
      type ietf-sr-policy-types:sid-value-type;
      description
        "Binding SID value";
    }
  }

  grouping explicit-path-properties {
    description
      "Explicit path properties of the candidate path";
    container segment-lists {
      description
        "Path segment list(s) properties";
      list segment-list {
        key "name-ref";
        max-elements 1;
        description
          "SR policy candidate path segment lists";
        leaf name-ref {
          type leafref {
            path "/ncs:devices/ncs:device/ncs:config/te:te/te:globals/te:mpls-paths/te:mpls-path/te:name" {
              tailf:xpath-root 3;
            }
          }
          description
            "Reference to segment-list name";
        }
      }
    }
  }

  grouping candidate-path-type {
    description
      "Candidate path type grouping";
    choice type {
      description
        "Type of candidate paths";
      case explicit {
        description
          "Candidate path with explicitly defined set/s of segment-lists";
        uses explicit-path-properties;
      }
    }
  }

  grouping candidate-paths {
    description
      "SR policy candidate path grouping";
    container candidate-paths {
      description
        "SR policy candidate path(s) ";
      list candidate-path {
        key "protocol-origin originator discriminator";
        max-elements 1;
        description
          "SR policy Candidate path(s) list entry";
        leaf protocol-origin {
          type ietf-sr-policy-types:protocol-origin-type;
          description
            "Instantiation mechanism used to create the candidate path";
        }
        leaf originator {
          type string;
          description
            "Identifier (concatenation of ASN and node-address) of the node
             that signalled/instantiated the candidate path on headend";
        }
        leaf discriminator {
          type uint32 {
            range "1..65535";
          }
          description
            "Candidate path distinguisher";
        }
        leaf preference {
          type uint32 {
            range "1..100";
          }
          mandatory true;
          description
            "Candidate path preference";
        }
        leaf description {
          type string;
          description
            "Candidate path description";
        }
        leaf isis-tag {
          type string;
          mandatory true;
          description
            "ISIS Instance Area Tag";
        }
        uses candidate-path-type;
      }
    }
  }

  grouping candidate-paths-state {
    description
      "SR policy candidate path grouping";
    container candidate-paths {
      description
        "SR policy candidate path(s) ";
      list candidate-path {
        key "protocol-origin originator discriminator";
        description
          "SR policy Candidate path(s) list entry";
        leaf protocol-origin {
          type ietf-sr-policy-types:protocol-origin-type;
          description
            "Instantiation mechanism used to create the candidate path";
        }
        leaf originator {
          type string;
          description
            "Identifier (concatenation of ASN and node-address) of the node
             that signalled/instantiated the candidate path on headend";
        }
        leaf discriminator {
          type uint32;
          description
            "Candidate path distinguisher";
        }
        leaf preference {
          type uint32;
          description
            "Candidate path preference";
        }
        leaf is-best-candidate-path {
          type boolean;
          description
            "Best candidate path";
        }
        leaf type {
          type string;
          description
            "Type of candidate paths";
        }
        container segment-lists {
          description
            "Path segment list(s) properties";
          list segment-list {
            key "name-ref";
            description
              "SR policy candidate path segment lists";
            leaf name-ref {
              type leafref {
                path "/ncs:devices/ncs:device/ncs:config/te:te/te:globals/te:mpls-paths/te:mpls-path/te:name" {
                  tailf:xpath-root 3;
                }
              }
              description
                "Reference to segment-list name";
            }
            leaf is-valid {
              type boolean;
              description
                "Segment-list weighted loadshare";
            }
            leaf hop-count {
              type uint32;
              description
                "Candidate path distinguisher";
            }
            list hop-list {
              key "hop-index";
              description
                "SR policy candidate path segment lists";
              leaf hop-index {
                type uint32;
                description
                  "Reference to segment-list name";
              }
              leaf hop-address {
                type inet:ipv4-prefix;
                description
                  "Reference to segment-list name";
              }
              leaf label {
                type uint32;
                description
                  "segment list label value";
              }
            }
          }
        }
      }
    }
  }

  augment "/ncs:devices/ncs:device/ncs:config" {
    container te {
      tailf:ncs-device-type "netconf";
      tailf:display-when "not(../../ncs:module) or ../../ncs:module[ncs:name='ciena-te']";
      description
        " TE Tunnel  model";
      container globals {
        description
          "Global TE config";
        container mpls-paths {
          description
            "Set of mpls paths ";
          list mpls-path {
            key "name";
            description
              "List of paths for this tunnel.";
            leaf name {
              type string;
              description
                "TE path name";
            }
            container explicit-route-objects {
              description
                "Container for the exclude route objects";
              list route-object-include-exclude {
                key "index";
                description
                  "List of explicit route objects to include or
                   exclude in path computation";
                leaf index {
                  type uint32 {
                    range "1..4095";
                  }
                  description
                    "ERO subobject index";
                }
                leaf explicit-route-usage {
                  type identityref {
                    base te-types:route-usage-type;
                  }
                  description
                    "Explicit-route usage.";
                }
                uses te-type;
              }
            }
          }
        }
      }
      container tunnels {
        description
          "TE tunnel configuration data";
        list tunnel {
          key "name";
          description
            "List for the tunnel.";
          leaf name {
            type string {
              length "0..255";
              pattern 'Tunnel([1-9]|[1-9][0-9]|[1-9][0-9][0-9]|[1-3][0-9][0-9][0-9]|40[0-8][0-9]|409[0-5])';
            }
            description
              "TE Tunnel Names are only in the format of Tunnelx where x is a number from 1-4095.";
          }
          leaf identifier {
            type uint16 {
              range "1..4095";
            }
            description
              "TE tunnel Identifier.";
          }
          leaf description {
            type string {
              length "0..255";
            }
            description
              "Textual description for this TE tunnel";
          }
          uses sr-path;
          leaf signaling-type {
            type identityref {
              base te-types:path-signaling-type;
            }
            description
              "Tunnel mode is MPLS Segment-Routing";
          }
          leaf color {
            type uint32 {
              range "0..31";
            }
            default "0";
            description
              "Color associated with the policy";
          }
          container binding-sid {
            description
              "Binding segment ID";
            uses binding-sid_config;
          }
          uses candidate-paths;
        }
      }
    }
    // NCS drop config false container 'mpls-te-state'
  }
  augment "/ncs:devices/ncs:device/ncs:live-status" {
    container te {
      tailf:ncs-device-type "netconf";
      tailf:display-when "not(../../ncs:module) or ../../ncs:module[ncs:name='ciena-te'] or (../../ncs:live-status-protocol[not(ncs:capability)]) or (../../ncs:live-status-protocol/ncs:capability/ncs:module[.='ciena-te'])";
      description
        " TE Tunnel  model";
      container globals {
        description
          "Global TE config";
        container mpls-paths {
          description
            "Set of mpls paths ";
          list mpls-path {
            key "name";
            description
              "List of paths for this tunnel.";
            leaf name {
              type string;
              description
                "TE path name";
            }
            container explicit-route-objects {
              description
                "Container for the exclude route objects";
              list route-object-include-exclude {
                key "index";
                description
                  "List of explicit route objects to include or
                   exclude in path computation";
                leaf index {
                  type uint32 {
                    range "1..4095";
                  }
                  description
                    "ERO subobject index";
                }
                leaf explicit-route-usage {
                  type identityref {
                    base te-types:route-usage-type;
                  }
                  description
                    "Explicit-route usage.";
                }
                uses live_ncs_te-type;
              }
            }
          }
        }
      }
      container tunnels {
        description
          "TE tunnel configuration data";
        list tunnel {
          key "name";
          description
            "List for the tunnel.";
          leaf name {
            type string {
              length "0..255";
              pattern 'Tunnel([1-9]|[1-9][0-9]|[1-9][0-9][0-9]|[1-3][0-9][0-9][0-9]|40[0-8][0-9]|409[0-5])';
            }
            description
              "TE Tunnel Names are only in the format of Tunnelx where x is a number from 1-4095.";
          }
          leaf identifier {
            type uint16 {
              range "1..4095";
            }
            description
              "TE tunnel Identifier.";
          }
          leaf description {
            type string {
              length "0..255";
            }
            description
              "Textual description for this TE tunnel";
          }
          uses live_ncs_sr-path;
          leaf signaling-type {
            type identityref {
              base te-types:path-signaling-type;
            }
            description
              "Tunnel mode is MPLS Segment-Routing";
          }
          leaf color {
            type uint32 {
              range "0..31";
            }
            // NCS drop default statement
            description
              "Color associated with the policy";
          }
          container binding-sid {
            description
              "Binding segment ID";
            uses live_ncs_binding-sid_config;
          }
          uses live_ncs_candidate-paths;
        }
      }
    }
    container mpls-te-state {
      tailf:ncs-device-type "netconf";
      tailf:display-when "not(../../ncs:module) or ../../ncs:module[ncs:name='ciena-te'] or (../../ncs:live-status-protocol[not(ncs:capability)]) or (../../ncs:live-status-protocol/ncs:capability/ncs:module[.='ciena-te'])";
      description
        "Mpls-te state container.";
      uses live_ncs_mpls-path-mode;
      uses live_ncs_tunnel-state;
    }
  }
  augment "/ncs:devices/ncs:template/ncs:ned-id/ncs:config" {
    container te {
      description
        " TE Tunnel  model";
      container globals {
        description
          "Global TE config";
        container mpls-paths {
          description
            "Set of mpls paths ";
          list mpls-path {
            // NCS patched for predictable order
            ordered-by user;
            key "name";
            description
              "List of paths for this tunnel.";
            leaf name {
              type string;
              description
                "TE path name";
            }
            container explicit-route-objects {
              description
                "Container for the exclude route objects";
              list route-object-include-exclude {
                // NCS patched for predictable order
                ordered-by user;
                key "index";
                description
                  "List of explicit route objects to include or
                   exclude in path computation";
                leaf index {
                  type string;
                  description
                    "ERO subobject index";
                }
                leaf explicit-route-usage {
                  type string;
                  description
                    "Explicit-route usage.";
                }
                uses ncs_template_te-type;
              }
            }
          }
        }
      }
      container tunnels {
        description
          "TE tunnel configuration data";
        list tunnel {
          // NCS patched for predictable order
          ordered-by user;
          key "name";
          description
            "List for the tunnel.";
          leaf name {
            type string;
            description
              "TE Tunnel Names are only in the format of Tunnelx where x is a number from 1-4095.";
          }
          leaf identifier {
            type string;
            description
              "TE tunnel Identifier.";
          }
          leaf description {
            type string;
            description
              "Textual description for this TE tunnel";
          }
          uses ncs_template_sr-path;
          leaf signaling-type {
            type string;
            description
              "Tunnel mode is MPLS Segment-Routing";
          }
          leaf color {
            type string;
            // NCS drop default statement
            description
              "Color associated with the policy";
          }
          container binding-sid {
            description
              "Binding segment ID";
            uses ncs_template_binding-sid_config;
          }
          uses ncs_template_candidate-paths;
        }
      }
    }
    // NCS drop config false container 'mpls-te-state'
  }
}
