module yumaworks-sesmgr {
  // Generated by yanger -t ncs
  tailf:mount-id "saos1051-nc-1.0:saos1051-nc-1.0";
  tailf:ncs-device-type "netconf";

  yang-version 1.1;
  namespace "http://yumaworks.com/ns/yumaworks-sesmgr";
  prefix ysmgr;

  import ietf-yang-types {
    prefix yang;
  }
  import ietf-inet-types {
    prefix inet;
  }
  import yuma-ncx {
    prefix ncx;
  }
  import yuma-types {
    prefix nt;
  }
  import yuma-app-common {
    prefix appcmn;
  }
  import yumaworks-app-common {
    prefix ywapp;
  }
  import yumaworks-types {
    prefix ywt;
  }
  import tailf-common {
    prefix tailf;
  }
  import tailf-ncs {
    prefix ncs;
  }

  organization
    "YumaWorks, Inc.";
  contact
    "Support <support at yumaworks.com>";
  description
    "yp-controller session manager

     Copyright (c) 2018 YumaWorks, Inc. All rights reserved.

     Redistribution and use in source and binary forms, with or
     without modification, is permitted pursuant to, and subject
     to the license terms contained in, the BSD 3-Clause License
     http://opensource.org/licenses/BSD-3-Clause.
    ";

  revision 2018-04-28 {
    description
      "Initial version";
  }

  typedef ncs_template_sesmgr-device-ref {
    type string;
  }

  typedef ncs_template_sesmgr-user-ref {
    type string;
  }

  typedef ncs_template_sesmgr-session-ref {
    type string;
  }

  typedef ncs_rpc_notif_sesmgr-device-ref {
    type string;
  }

  typedef ncs_rpc_notif_sesmgr-user-ref {
    type string;
  }

  typedef ncs_rpc_notif_sesmgr-session-ref {
    type string;
  }

  typedef live_ncs_sesmgr-device-ref {
    type leafref {
      path "/ncs:devices/ncs:device/ncs:live-status/ysmgr:sesmgr/ysmgr:devices/ysmgr:device/ysmgr:name" {
        tailf:xpath-root 3;
      }
    }
  }

  typedef live_ncs_sesmgr-user-ref {
    type leafref {
      path "/ncs:devices/ncs:device/ncs:live-status/ysmgr:sesmgr/ysmgr:users/ysmgr:user/ysmgr:name" {
        tailf:xpath-root 3;
      }
    }
  }

  typedef live_ncs_sesmgr-session-ref {
    type leafref {
      path "/ncs:devices/ncs:device/ncs:live-status/ysmgr:sesmgr/ysmgr:sessions/ysmgr:session/ysmgr:name" {
        tailf:xpath-root 3;
      }
    }
  }

  typedef sesmgr-device-ref {
    type leafref {
      path "/ncs:devices/ncs:device/ncs:config/ysmgr:sesmgr/ysmgr:devices/ysmgr:device/ysmgr:name" {
        tailf:xpath-root 3;
      }
    }
  }

  typedef sesmgr-user-ref {
    type leafref {
      path "/ncs:devices/ncs:device/ncs:config/ysmgr:sesmgr/ysmgr:users/ysmgr:user/ysmgr:name" {
        tailf:xpath-root 3;
      }
    }
  }

  typedef sesmgr-session-ref {
    type leafref {
      path "/ncs:devices/ncs:device/ncs:config/ysmgr:sesmgr/ysmgr:sessions/ysmgr:session/ysmgr:name" {
        tailf:xpath-root 3;
      }
    }
  }

  grouping ncs_template_device-cmn {
    description
      "one device endpoint configuration contents";
    leaf server {
      type string;
      // NCS drop mandatory statement
      description
        "IP address or DNS name of the NETCONF server target.";
    }
    leaf port {
      type string;
      description
        "NETCONF over SSH port number to use.";
    }
    leaf rc-entry-point {
      type string;
      description
        "RESTCONF entry point. Use this string instead of
         retrieving the XRD from the RESTCONF server to
         discover the entry point.";
    }
    uses appcmn:ncs_template_ProtocolsParm;
    leaf transport {
      type ywt:ncs_template_transport-type;
      description
        "transport protocol to use";
    }
  }

  grouping ncs_template_session-cmn {
    leaf name {
      type nt:ncs_template_NcxName;
      description
        "The name of the saved session.";
    }
    leaf user-ref {
      type ncs_template_sesmgr-user-ref;
      // NCS drop mandatory statement
      description
        "The user to use for this session";
    }
  }

  grouping ncs_template_session-state {
    // NCS drop config false container state
  }

  grouping ncs_rpc_notif_device-cmn {
    description
      "one device endpoint configuration contents";
    leaf server {
      type inet:host;
      mandatory true;
      description
        "IP address or DNS name of the NETCONF server target.";
    }
    leaf port {
      type inet:port-number;
      description
        "NETCONF over SSH port number to use.";
    }
    leaf rc-entry-point {
      type string;
      description
        "RESTCONF entry point. Use this string instead of
         retrieving the XRD from the RESTCONF server to
         discover the entry point.";
    }
    uses appcmn:ncs_rpc_notif_ProtocolsParm;
    leaf transport {
      type ywt:ncs_rpc_notif_transport-type;
      description
        "transport protocol to use";
    }
  }

  grouping ncs_rpc_notif_session-cmn {
    leaf name {
      type nt:ncs_rpc_notif_NcxName;
      description
        "The name of the saved session.";
    }
    leaf user-ref {
      type ncs_rpc_notif_sesmgr-user-ref;
      mandatory true;
      description
        "The user to use for this session";
    }
  }

  grouping ncs_rpc_notif_session-state {
    container state {
      config false;
      leaf connected {
        type boolean;
        description
          "Indicates if session currently connected";
      }
      leaf connect-time {
        type yang:date-and-time;
        description
          "Date and time the session connected.";
      }
      container counters {
        leaf out-rpcs {
          type yang:zero-based-counter32;
          description
            "Number of <rpc> messages sent.";
        }
        leaf in-rpc-errors {
          type yang:zero-based-counter32;
          description
            "Number of <rpc-reply> messages received
             that contained an <rpc-error>";
        }
        leaf in-notifications {
          type yang:zero-based-counter32;
          description
            "Number of <notification> messages received.";
        }
        leaf in-octets {
          type yang:zero-based-counter32;
          description
            "Number of octets received by netconfd-pro
             for this session.";
        }
        leaf out-octets {
          type yang:zero-based-counter32;
          description
            "Number of octets sent by netconfd-pro
             for this session.";
        }
      }
    }
  }

  grouping live_ncs_device-cmn {
    description
      "one device endpoint configuration contents";
    leaf server {
      type inet:host;
      // NCS drop mandatory statement
      description
        "IP address or DNS name of the NETCONF server target.";
    }
    leaf port {
      type inet:port-number;
      description
        "NETCONF over SSH port number to use.";
    }
    leaf rc-entry-point {
      type string;
      description
        "RESTCONF entry point. Use this string instead of
         retrieving the XRD from the RESTCONF server to
         discover the entry point.";
    }
    uses appcmn:live_ncs_ProtocolsParm;
    leaf transport {
      type ywt:live_ncs_transport-type;
      description
        "transport protocol to use";
    }
  }

  grouping live_ncs_session-cmn {
    leaf name {
      type nt:live_ncs_NcxName;
      description
        "The name of the saved session.";
    }
    leaf user-ref {
      type live_ncs_sesmgr-user-ref;
      // NCS drop mandatory statement
      description
        "The user to use for this session";
    }
  }

  grouping live_ncs_session-state {
    container state {
      leaf connected {
        type boolean;
        description
          "Indicates if session currently connected";
      }
      leaf connect-time {
        type yang:date-and-time;
        description
          "Date and time the session connected.";
      }
      container counters {
        leaf out-rpcs {
          type yang:zero-based-counter32;
          description
            "Number of <rpc> messages sent.";
        }
        leaf in-rpc-errors {
          type yang:zero-based-counter32;
          description
            "Number of <rpc-reply> messages received
             that contained an <rpc-error>";
        }
        leaf in-notifications {
          type yang:zero-based-counter32;
          description
            "Number of <notification> messages received.";
        }
        leaf in-octets {
          type yang:zero-based-counter32;
          description
            "Number of octets received by netconfd-pro
             for this session.";
        }
        leaf out-octets {
          type yang:zero-based-counter32;
          description
            "Number of octets sent by netconfd-pro
             for this session.";
        }
      }
    }
  }

  grouping device-cmn {
    description
      "one device endpoint configuration contents";
    leaf server {
      type inet:host;
      mandatory true;
      description
        "IP address or DNS name of the NETCONF server target.";
    }
    leaf port {
      type inet:port-number;
      description
        "NETCONF over SSH port number to use.";
    }
    leaf rc-entry-point {
      type string;
      description
        "RESTCONF entry point. Use this string instead of
         retrieving the XRD from the RESTCONF server to
         discover the entry point.";
    }
    uses appcmn:ProtocolsParm;
    leaf transport {
      type ywt:transport-type;
      description
        "transport protocol to use";
    }
  }

  grouping session-cmn {
    leaf name {
      type nt:NcxName;
      description
        "The name of the saved session.";
    }
    leaf user-ref {
      type sesmgr-user-ref;
      mandatory true;
      description
        "The user to use for this session";
    }
  }

  grouping session-state {
    // NCS drop config false container state
  }

  augment "/ncs:devices/ncs:device/ncs:config" {
    container sesmgr {
      tailf:ncs-device-type "netconf";
      tailf:display-when "not(../../ncs:module) or ../../ncs:module[ncs:name='yumaworks-sesmgr']";
      ncx:sil-delete-children-first;
      description
        "yp-controller session management configuration";
      container devices {
        ncx:sil-delete-children-first;
        description
          "yp-controller device configuration";
        list device {
          description
            "one device endpoint configuration";
          key "name";
          leaf name {
            type nt:NcxName;
            description
              "The name of the saved device.";
          }
          uses device-cmn;
        }
      }
      container users {
        ncx:sil-delete-children-first;
        description
          "yp-controller user configuration";
        list user {
          description
            "one user configuration";
          key "name";
          leaf name {
            type nt:NcxName;
            description
              "The name of the saved user.";
          }
          leaf user {
            type nt:NcxName;
            mandatory true;
            description
              "The user name of the session.";
          }
          choice pass {
            mandatory true;
            leaf password {
              type string;
              ncx:password;
              description
                "User password to use for NETCONF users.
                 If none, then user will be prompted before connecting.";
            }
            leaf no-password {
              type empty;
            }
          }
          uses ywapp:SshKeyParms;
          uses ywapp:SslKeyParms;
          leaf-list admin-group {
            type nt:NcxName;
            description
              "The name of an allowed admin group for the saved user.";
          }
        }
      }
      container sessions {
        ncx:sil-delete-children-first;
        description
          "yp-controller session configuration";
        list session {
          description
            "one session configuration";
          key "name";
          uses session-cmn;
          leaf device-ref {
            type sesmgr-device-ref;
            mandatory true;
            description
              "The device to use for this session";
          }
          uses session-state;
        }
        // NCS drop config false list 'callhome-session'
      }
    }
  }
  augment "/ncs:devices/ncs:device/ncs:live-status" {
    container sesmgr {
      tailf:ncs-device-type "netconf";
      tailf:display-when "not(../../ncs:module) or ../../ncs:module[ncs:name='yumaworks-sesmgr'] or (../../ncs:live-status-protocol[not(ncs:capability)]) or (../../ncs:live-status-protocol/ncs:capability/ncs:module[.='yumaworks-sesmgr'])";
      ncx:sil-delete-children-first;
      description
        "yp-controller session management configuration";
      container devices {
        ncx:sil-delete-children-first;
        description
          "yp-controller device configuration";
        list device {
          description
            "one device endpoint configuration";
          key "name";
          leaf name {
            type nt:live_ncs_NcxName;
            description
              "The name of the saved device.";
          }
          uses live_ncs_device-cmn;
        }
      }
      container users {
        ncx:sil-delete-children-first;
        description
          "yp-controller user configuration";
        list user {
          description
            "one user configuration";
          key "name";
          leaf name {
            type nt:live_ncs_NcxName;
            description
              "The name of the saved user.";
          }
          leaf user {
            type nt:live_ncs_NcxName;
            // NCS drop mandatory statement
            description
              "The user name of the session.";
          }
          choice pass {
            // NCS drop mandatory statement
            leaf password {
              type string;
              ncx:password;
              description
                "User password to use for NETCONF users.
                 If none, then user will be prompted before connecting.";
            }
            leaf no-password {
              type empty;
            }
          }
          uses ywapp:live_ncs_SshKeyParms;
          uses ywapp:live_ncs_SslKeyParms;
          leaf-list admin-group {
            type nt:live_ncs_NcxName;
            description
              "The name of an allowed admin group for the saved user.";
          }
        }
      }
      container sessions {
        ncx:sil-delete-children-first;
        description
          "yp-controller session configuration";
        list session {
          description
            "one session configuration";
          key "name";
          uses live_ncs_session-cmn;
          leaf device-ref {
            type live_ncs_sesmgr-device-ref;
            // NCS drop mandatory statement
            description
              "The device to use for this session";
          }
          uses live_ncs_session-state;
        }
        list callhome-session {
          description
            "one callhome session added by sesmgr";
          key "name";
          uses live_ncs_session-cmn;
          container device {
            uses live_ncs_device-cmn;
          }
          uses live_ncs_session-state;
        }
      }
    }
  }
  augment "/ncs:devices/ncs:template/ncs:ned-id/ncs:config" {
    container sesmgr {
      ncx:sil-delete-children-first;
      description
        "yp-controller session management configuration";
      container devices {
        ncx:sil-delete-children-first;
        description
          "yp-controller device configuration";
        list device {
          // NCS patched for predictable order
          ordered-by user;
          description
            "one device endpoint configuration";
          key "name";
          leaf name {
            type nt:ncs_template_NcxName;
            description
              "The name of the saved device.";
          }
          uses ncs_template_device-cmn;
        }
      }
      container users {
        ncx:sil-delete-children-first;
        description
          "yp-controller user configuration";
        list user {
          // NCS patched for predictable order
          ordered-by user;
          description
            "one user configuration";
          key "name";
          leaf name {
            type nt:ncs_template_NcxName;
            description
              "The name of the saved user.";
          }
          leaf user {
            type nt:ncs_template_NcxName;
            // NCS drop mandatory statement
            description
              "The user name of the session.";
          }
          choice pass {
            // NCS drop mandatory statement
            leaf password {
              type string;
              ncx:password;
              description
                "User password to use for NETCONF users.
                 If none, then user will be prompted before connecting.";
            }
            leaf no-password {
              type empty;
            }
          }
          uses ywapp:ncs_template_SshKeyParms;
          uses ywapp:ncs_template_SslKeyParms;
          leaf-list admin-group {
            // NCS patched for predictable order
            ordered-by user;
            type nt:ncs_template_NcxName;
            description
              "The name of an allowed admin group for the saved user.";
          }
        }
      }
      container sessions {
        ncx:sil-delete-children-first;
        description
          "yp-controller session configuration";
        list session {
          // NCS patched for predictable order
          ordered-by user;
          description
            "one session configuration";
          key "name";
          uses ncs_template_session-cmn;
          leaf device-ref {
            type ncs_template_sesmgr-device-ref;
            // NCS drop mandatory statement
            description
              "The device to use for this session";
          }
          uses ncs_template_session-state;
        }
        // NCS drop config false list 'callhome-session'
      }
    }
  }
}
