module ciena-mef-egress-qos-show {
  // Generated by yanger -t ncs
  tailf:mount-id "saos1051-nc-1.0:saos1051-nc-1.0";
  tailf:ncs-device-type "netconf";

  yang-version 1.1;
  namespace "http://www.ciena.com/ns/ciena-mef-egress-qos-show";
  prefix ciena-mef-egress-qos-show;

  import yangcli-pro {
    prefix yp;
  }
  import tailf-common {
    prefix tailf;
  }
  import tailf-ncs {
    prefix ncs;
  }

  description
    "Show command extensions by ciena for ciena-mef-egress-qos";

  revision 2017-09-28 {
    description
      "Initial version";
  }

  augment "/ncs:devices/ncs:device/ncs:rpc/yp:rpc-show/yp:show/yp:input/yp:showtype" {
    case scheduler-profile {
      leaf scheduler-profile {
        type union {
          type string;
        }
      }
    }
    case cos-to-queue-map {
      leaf cos-to-queue-map {
        type union {
          type string;
        }
      }
    }
    case queue-group-profile {
      leaf queue-group-profile {
        type union {
          type string;
        }
      }
    }
    case queue-group-instance {
      leaf queue-group-instance {
        type union {
          type string;
        }
      }
    }
    case scheduler-instance {
      leaf scheduler-instance {
        type union {
          type string;
        }
      }
    }
  }
}
