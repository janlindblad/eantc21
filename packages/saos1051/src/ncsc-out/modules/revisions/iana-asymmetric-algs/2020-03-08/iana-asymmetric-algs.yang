module iana-asymmetric-algs {
  // Generated by yanger -t ncs
  tailf:mount-id "saos1051-nc-1.0:saos1051-nc-1.0";
  tailf:ncs-device-type "netconf";

  yang-version 1.1;
  namespace "urn:ietf:params:xml:ns:yang:iana-asymmetric-algs";
  prefix iasa;

  import tailf-common {
    prefix tailf;
  }
  import tailf-ncs {
    prefix ncs;
  }

  organization
    "IETF NETCONF (Network Configuration) Working Group";
  contact
    "WG Web:   <http://datatracker.ietf.org/wg/netconf/>
     WG List:  <mailto:netconf@ietf.org>
     Author:   Kent Watsen <mailto:kent+ietf@watsen.net>
     Author:   Wang Haiguang <wang.haiguang.shieldlab@huawei.com>";
  description
    "This module defines a typedef for asymmetric algorithms, and
     a container for a list of asymmetric algorithms supported by
     the server.

     Copyright (c) 2019 IETF Trust and the persons identified
     as authors of the code. All rights reserved.
     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2020-03-08 {
    description
      "Initial version";
    reference "RFC XXXX: Common YANG Data Types for Cryptography";
  }

  typedef ncs_template_asymmetric-algorithm-type {
    type string;
    description
      "A typedef enumerating various asymmetric key algorithms.";
  }

  typedef ncs_rpc_notif_asymmetric-algorithm-type {
    type enumeration {
      enum "rsa1024" {
        value 1;
        description
          "The RSA algorithm using a 1024-bit key.";
        reference
          "RFC 8017: PKCS #1: RSA Cryptography
           Specifications Version 2.2.";
      }
      enum "rsa2048" {
        value 2;
        description
          "The RSA algorithm using a 2048-bit key.";
        reference
          "RFC 8017:
           PKCS #1: RSA Cryptography Specifications Version 2.2.";
      }
      enum "rsa3072" {
        value 3;
        description
          "The RSA algorithm using a 3072-bit key.";
        reference
          "RFC 8017:
           PKCS #1: RSA Cryptography Specifications Version 2.2.";
      }
      enum "rsa4096" {
        value 4;
        description
          "The RSA algorithm using a 4096-bit key.";
        reference
          "RFC 8017:
           PKCS #1: RSA Cryptography Specifications Version 2.2.";
      }
      enum "rsa7680" {
        value 5;
        description
          "The RSA algorithm using a 7680-bit key.";
        reference
          "RFC 8017:
           PKCS #1: RSA Cryptography Specifications Version 2.2.";
      }
      enum "rsa15360" {
        value 6;
        description
          "The RSA algorithm using a 15360-bit key.";
        reference
          "RFC 8017:
           PKCS #1: RSA Cryptography Specifications Version 2.2.";
      }
      enum "secp192r1" {
        value 7;
        description
          "The asymmetric algorithm using a NIST P192 Curve.";
        reference
          "RFC 6090:
             Fundamental Elliptic Curve Cryptography Algorithms.
           RFC 5480:
              Elliptic Curve Cryptography Subject Public Key
              Information.";
      }
      enum "secp224r1" {
        value 8;
        description
          "The asymmetric algorithm using a NIST P224 Curve.";
        reference
          "RFC 6090:
             Fundamental Elliptic Curve Cryptography Algorithms.
           RFC 5480:
             Elliptic Curve Cryptography Subject Public Key
             Information.";
      }
      enum "secp256r1" {
        value 9;
        description
          "The asymmetric algorithm using a NIST P256 Curve.";
        reference
          "RFC 6090:
             Fundamental Elliptic Curve Cryptography Algorithms.
           RFC 5480:
             Elliptic Curve Cryptography Subject Public Key
             Information.";
      }
      enum "secp384r1" {
        value 10;
        description
          "The asymmetric algorithm using a NIST P384 Curve.";
        reference
          "RFC 6090:
             Fundamental Elliptic Curve Cryptography Algorithms.
           RFC 5480:
             Elliptic Curve Cryptography Subject Public Key
             Information.";
      }
      enum "secp521r1" {
        value 11;
        description
          "The asymmetric algorithm using a NIST P521 Curve.";
        reference
          "RFC 6090:
             Fundamental Elliptic Curve Cryptography Algorithms.
           RFC 5480:
             Elliptic Curve Cryptography Subject Public Key
             Information.";
      }
      enum "x25519" {
        value 12;
        description
          "The asymmetric algorithm using a x.25519 Curve.";
        reference
          "RFC 7748:
             Elliptic Curves for Security.";
      }
      enum "x448" {
        value 13;
        description
          "The asymmetric algorithm using a x.448 Curve.";
        reference
          "RFC 7748:
             Elliptic Curves for Security.";
      }
    }
    description
      "A typedef enumerating various asymmetric key algorithms.";
  }

  typedef live_ncs_asymmetric-algorithm-type {
    type enumeration {
      enum "rsa1024" {
        value 1;
        description
          "The RSA algorithm using a 1024-bit key.";
        reference
          "RFC 8017: PKCS #1: RSA Cryptography
           Specifications Version 2.2.";
      }
      enum "rsa2048" {
        value 2;
        description
          "The RSA algorithm using a 2048-bit key.";
        reference
          "RFC 8017:
           PKCS #1: RSA Cryptography Specifications Version 2.2.";
      }
      enum "rsa3072" {
        value 3;
        description
          "The RSA algorithm using a 3072-bit key.";
        reference
          "RFC 8017:
           PKCS #1: RSA Cryptography Specifications Version 2.2.";
      }
      enum "rsa4096" {
        value 4;
        description
          "The RSA algorithm using a 4096-bit key.";
        reference
          "RFC 8017:
           PKCS #1: RSA Cryptography Specifications Version 2.2.";
      }
      enum "rsa7680" {
        value 5;
        description
          "The RSA algorithm using a 7680-bit key.";
        reference
          "RFC 8017:
           PKCS #1: RSA Cryptography Specifications Version 2.2.";
      }
      enum "rsa15360" {
        value 6;
        description
          "The RSA algorithm using a 15360-bit key.";
        reference
          "RFC 8017:
           PKCS #1: RSA Cryptography Specifications Version 2.2.";
      }
      enum "secp192r1" {
        value 7;
        description
          "The asymmetric algorithm using a NIST P192 Curve.";
        reference
          "RFC 6090:
             Fundamental Elliptic Curve Cryptography Algorithms.
           RFC 5480:
              Elliptic Curve Cryptography Subject Public Key
              Information.";
      }
      enum "secp224r1" {
        value 8;
        description
          "The asymmetric algorithm using a NIST P224 Curve.";
        reference
          "RFC 6090:
             Fundamental Elliptic Curve Cryptography Algorithms.
           RFC 5480:
             Elliptic Curve Cryptography Subject Public Key
             Information.";
      }
      enum "secp256r1" {
        value 9;
        description
          "The asymmetric algorithm using a NIST P256 Curve.";
        reference
          "RFC 6090:
             Fundamental Elliptic Curve Cryptography Algorithms.
           RFC 5480:
             Elliptic Curve Cryptography Subject Public Key
             Information.";
      }
      enum "secp384r1" {
        value 10;
        description
          "The asymmetric algorithm using a NIST P384 Curve.";
        reference
          "RFC 6090:
             Fundamental Elliptic Curve Cryptography Algorithms.
           RFC 5480:
             Elliptic Curve Cryptography Subject Public Key
             Information.";
      }
      enum "secp521r1" {
        value 11;
        description
          "The asymmetric algorithm using a NIST P521 Curve.";
        reference
          "RFC 6090:
             Fundamental Elliptic Curve Cryptography Algorithms.
           RFC 5480:
             Elliptic Curve Cryptography Subject Public Key
             Information.";
      }
      enum "x25519" {
        value 12;
        description
          "The asymmetric algorithm using a x.25519 Curve.";
        reference
          "RFC 7748:
             Elliptic Curves for Security.";
      }
      enum "x448" {
        value 13;
        description
          "The asymmetric algorithm using a x.448 Curve.";
        reference
          "RFC 7748:
             Elliptic Curves for Security.";
      }
    }
    description
      "A typedef enumerating various asymmetric key algorithms.";
  }

  typedef asymmetric-algorithm-type {
    type enumeration {
      enum "rsa1024" {
        value 1;
        description
          "The RSA algorithm using a 1024-bit key.";
        reference
          "RFC 8017: PKCS #1: RSA Cryptography
           Specifications Version 2.2.";
      }
      enum "rsa2048" {
        value 2;
        description
          "The RSA algorithm using a 2048-bit key.";
        reference
          "RFC 8017:
           PKCS #1: RSA Cryptography Specifications Version 2.2.";
      }
      enum "rsa3072" {
        value 3;
        description
          "The RSA algorithm using a 3072-bit key.";
        reference
          "RFC 8017:
           PKCS #1: RSA Cryptography Specifications Version 2.2.";
      }
      enum "rsa4096" {
        value 4;
        description
          "The RSA algorithm using a 4096-bit key.";
        reference
          "RFC 8017:
           PKCS #1: RSA Cryptography Specifications Version 2.2.";
      }
      enum "rsa7680" {
        value 5;
        description
          "The RSA algorithm using a 7680-bit key.";
        reference
          "RFC 8017:
           PKCS #1: RSA Cryptography Specifications Version 2.2.";
      }
      enum "rsa15360" {
        value 6;
        description
          "The RSA algorithm using a 15360-bit key.";
        reference
          "RFC 8017:
           PKCS #1: RSA Cryptography Specifications Version 2.2.";
      }
      enum "secp192r1" {
        value 7;
        description
          "The asymmetric algorithm using a NIST P192 Curve.";
        reference
          "RFC 6090:
             Fundamental Elliptic Curve Cryptography Algorithms.
           RFC 5480:
              Elliptic Curve Cryptography Subject Public Key
              Information.";
      }
      enum "secp224r1" {
        value 8;
        description
          "The asymmetric algorithm using a NIST P224 Curve.";
        reference
          "RFC 6090:
             Fundamental Elliptic Curve Cryptography Algorithms.
           RFC 5480:
             Elliptic Curve Cryptography Subject Public Key
             Information.";
      }
      enum "secp256r1" {
        value 9;
        description
          "The asymmetric algorithm using a NIST P256 Curve.";
        reference
          "RFC 6090:
             Fundamental Elliptic Curve Cryptography Algorithms.
           RFC 5480:
             Elliptic Curve Cryptography Subject Public Key
             Information.";
      }
      enum "secp384r1" {
        value 10;
        description
          "The asymmetric algorithm using a NIST P384 Curve.";
        reference
          "RFC 6090:
             Fundamental Elliptic Curve Cryptography Algorithms.
           RFC 5480:
             Elliptic Curve Cryptography Subject Public Key
             Information.";
      }
      enum "secp521r1" {
        value 11;
        description
          "The asymmetric algorithm using a NIST P521 Curve.";
        reference
          "RFC 6090:
             Fundamental Elliptic Curve Cryptography Algorithms.
           RFC 5480:
             Elliptic Curve Cryptography Subject Public Key
             Information.";
      }
      enum "x25519" {
        value 12;
        description
          "The asymmetric algorithm using a x.25519 Curve.";
        reference
          "RFC 7748:
             Elliptic Curves for Security.";
      }
      enum "x448" {
        value 13;
        description
          "The asymmetric algorithm using a x.448 Curve.";
        reference
          "RFC 7748:
             Elliptic Curves for Security.";
      }
    }
    description
      "A typedef enumerating various asymmetric key algorithms.";
  }

  augment "/ncs:devices/ncs:device/ncs:config" {
    // NCS drop config false container 'supported-asymmetric-algorithms'
  }
  augment "/ncs:devices/ncs:device/ncs:live-status" {
    container supported-asymmetric-algorithms {
      tailf:ncs-device-type "netconf";
      tailf:display-when "not(../../ncs:module) or ../../ncs:module[ncs:name='iana-asymmetric-algs'] or (../../ncs:live-status-protocol[not(ncs:capability)]) or (../../ncs:live-status-protocol/ncs:capability/ncs:module[.='iana-asymmetric-algs'])";
      description
        "A container for a list of supported asymmetric algorithms.
         How algorithms come to be supported is outside the scope
         of this module.";
      list supported-asymmetric-algorithm {
        key "algorithm";
        description
          "A lists of asymmetric algorithms supported by the server.";
        leaf algorithm {
          type live_ncs_asymmetric-algorithm-type;
          description
            "An asymmetric algorithms supported by the server.";
        }
      }
    }
  }
  augment "/ncs:devices/ncs:template/ncs:ned-id/ncs:config" {
    // NCS drop config false container 'supported-asymmetric-algorithms'
  }
}
