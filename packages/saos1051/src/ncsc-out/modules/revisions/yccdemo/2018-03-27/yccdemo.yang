module yccdemo {
  // Generated by yanger -t ncs
  tailf:mount-id "saos1051-nc-1.0:saos1051-nc-1.0";
  tailf:ncs-device-type "netconf";

  namespace "http://www.ciena.com/ns/yang/yccdemo";
  prefix yccdemo;

  import ietf-inet-types {
    prefix inet;
  }
  import tailf-common {
    prefix tailf;
  }
  import tailf-ncs {
    prefix ncs;
  }

  revision 2018-03-27;

  typedef ncs_template_int-type {
    type string;
  }

  typedef ncs_template_union-type {
    type string;
  }

  typedef ncs_template_enum-type {
    type string;
  }

  typedef ncs_template_season-enum {
    type string;
  }

  typedef ncs_template_bits-type {
    type string;
    description
      "Basic type is bits(zero one two etc)";
  }

  typedef ncs_template_id-type {
    type string;
    description
      "Basic type is identityref(id1 id2 id2.1 id2.2 id3)";
  }

  typedef ncs_rpc_notif_int-type {
    type int32 {
      range "0..7777";
    }
  }

  typedef ncs_rpc_notif_union-type {
    type union {
      type ncs_rpc_notif_int-type;
      type ncs_rpc_notif_enum-type;
      type string;
    }
  }

  typedef ncs_rpc_notif_enum-type {
    type enumeration {
      enum "zero";
      enum "one";
      enum "two";
      enum "three";
      enum "four";
      enum "five";
      enum "six";
    }
  }

  typedef ncs_rpc_notif_season-enum {
    type enumeration {
      enum "spring";
      enum "summer";
      enum "fall";
      enum "winter";
    }
  }

  typedef ncs_rpc_notif_bits-type {
    type bits {
      bit zero;
      bit one;
      bit two {
        position 2;
      }
      bit after_two;
      bit four;
      bit five;
      bit six;
      bit seven;
      bit eight;
      bit nine;
      bit ten;
      bit alpha;
      bit beta;
      bit charlie;
      bit delta;
      bit echo;
      bit foxtrot;
      bit golf;
      bit hotel;
      bit india;
      bit juliett;
      bit kilo;
      bit lima;
      bit mike;
      bit november;
      bit oscar;
      bit papa;
      bit quebec;
      bit romeo;
      bit sierra;
      bit tango;
      bit uniform;
      bit victor;
      bit whiskey;
      bit xray;
      bit yankee;
      bit zulu;
    }
    description
      "Basic type is bits(zero one two etc)";
  }

  typedef ncs_rpc_notif_id-type {
    type identityref {
      base id;
    }
    description
      "Basic type is identityref(id1 id2 id2.1 id2.2 id3)";
  }

  typedef live_ncs_int-type {
    type int32 {
      range "0..7777";
    }
  }

  typedef live_ncs_union-type {
    type union {
      type live_ncs_int-type;
      type live_ncs_enum-type;
      type string;
    }
  }

  typedef live_ncs_enum-type {
    type enumeration {
      enum "zero";
      enum "one";
      enum "two";
      enum "three";
      enum "four";
      enum "five";
      enum "six";
    }
  }

  typedef live_ncs_season-enum {
    type enumeration {
      enum "spring";
      enum "summer";
      enum "fall";
      enum "winter";
    }
  }

  typedef live_ncs_bits-type {
    type bits {
      bit zero;
      bit one;
      bit two {
        position 2;
      }
      bit after_two;
      bit four;
      bit five;
      bit six;
      bit seven;
      bit eight;
      bit nine;
      bit ten;
      bit alpha;
      bit beta;
      bit charlie;
      bit delta;
      bit echo;
      bit foxtrot;
      bit golf;
      bit hotel;
      bit india;
      bit juliett;
      bit kilo;
      bit lima;
      bit mike;
      bit november;
      bit oscar;
      bit papa;
      bit quebec;
      bit romeo;
      bit sierra;
      bit tango;
      bit uniform;
      bit victor;
      bit whiskey;
      bit xray;
      bit yankee;
      bit zulu;
    }
    description
      "Basic type is bits(zero one two etc)";
  }

  typedef live_ncs_id-type {
    type identityref {
      base id;
    }
    description
      "Basic type is identityref(id1 id2 id2.1 id2.2 id3)";
  }

  typedef int-type {
    type int32 {
      range "0..7777";
    }
  }

  typedef union-type {
    type union {
      type int-type;
      type enum-type;
      type string;
    }
  }

  typedef enum-type {
    type enumeration {
      enum "zero";
      enum "one";
      enum "two";
      enum "three";
      enum "four";
      enum "five";
      enum "six";
    }
  }

  typedef season-enum {
    type enumeration {
      enum "spring";
      enum "summer";
      enum "fall";
      enum "winter";
    }
  }

  typedef bits-type {
    type bits {
      bit zero;
      bit one;
      bit two {
        position 2;
      }
      bit after_two;
      bit four;
      bit five;
      bit six;
      bit seven;
      bit eight;
      bit nine;
      bit ten;
      bit alpha;
      bit beta;
      bit charlie;
      bit delta;
      bit echo;
      bit foxtrot;
      bit golf;
      bit hotel;
      bit india;
      bit juliett;
      bit kilo;
      bit lima;
      bit mike;
      bit november;
      bit oscar;
      bit papa;
      bit quebec;
      bit romeo;
      bit sierra;
      bit tango;
      bit uniform;
      bit victor;
      bit whiskey;
      bit xray;
      bit yankee;
      bit zulu;
    }
    description
      "Basic type is bits(zero one two etc)";
  }

  typedef id-type {
    type identityref {
      base id;
    }
    description
      "Basic type is identityref(id1 id2 id2.1 id2.2 id3)";
  }

  grouping ncs_template_all-type-leaves {
    leaf int8-leaf {
      type string;
    }
    leaf int16-leaf {
      type string;
    }
    leaf int32-leaf {
      type string;
    }
    leaf int64-leaf {
      type string;
    }
    leaf uint8-leaf {
      type string;
    }
    leaf uint16-leaf {
      type string;
    }
    leaf uint32-leaf {
      type string;
    }
    leaf uint64-leaf {
      type string;
    }
    leaf decimal64-leaf {
      type string;
    }
    leaf string-leaf {
      type string;
    }
    leaf boolean-leaf {
      type string;
    }
    leaf enumeration-leaf {
      type ncs_template_season-enum;
    }
    leaf bits-leaf {
      type ncs_template_bits-type;
    }
    leaf identityref-leaf {
      type ncs_template_id-type;
    }
    leaf empty-leaf {
      type empty;
    }
    leaf leafref-string {
      type string;
    }
    leaf leafref-boolean {
      type string;
    }
  }

  grouping ncs_template_all-type-leaf-lists {
    leaf-list int8-leaflist {
      // NCS patched for predictable order
      ordered-by user;
      type string;
    }
    leaf-list int16-leaflist {
      // NCS patched for predictable order
      ordered-by user;
      type string;
    }
    leaf-list int32-leaflist {
      // NCS patched for predictable order
      ordered-by user;
      type string;
    }
    leaf-list int64-leaflist {
      // NCS patched for predictable order
      ordered-by user;
      type string;
    }
    leaf-list uint8-leaflist {
      // NCS patched for predictable order
      ordered-by user;
      type string;
    }
    leaf-list uint16-leaflist {
      // NCS patched for predictable order
      ordered-by user;
      type string;
    }
    leaf-list uint32-leaflist {
      // NCS patched for predictable order
      ordered-by user;
      type string;
    }
    leaf-list uint64-leaflist {
      // NCS patched for predictable order
      ordered-by user;
      type string;
    }
    leaf-list decimal64-leaflist {
      // NCS patched for predictable order
      ordered-by user;
      type string;
    }
    leaf-list string-leaflist {
      // NCS patched for predictable order
      ordered-by user;
      type string;
    }
    leaf-list boolean-leaflist {
      // NCS patched for predictable order
      ordered-by user;
      type string;
    }
    leaf-list enumeration-leaflist {
      // NCS patched for predictable order
      ordered-by user;
      type ncs_template_season-enum;
    }
    leaf-list bits-leaflist {
      // NCS patched for predictable order
      ordered-by user;
      type ncs_template_bits-type;
    }
    leaf-list identityref-leaflist {
      // NCS patched for predictable order
      ordered-by user;
      type ncs_template_id-type;
    }
  }

  grouping ncs_template_all-type-union-leaf {
    leaf union-leaf-int8 {
      type string;
    }
    leaf union-leaf-int16 {
      type string;
    }
    leaf union-leaf-int32 {
      type string;
    }
    leaf union-leaf-int64 {
      type string;
    }
    leaf union-leaf-uint8 {
      type string;
    }
    leaf union-leaf-uint16 {
      type string;
    }
    leaf union-leaf-uint32 {
      type string;
    }
    leaf union-leaf-uint64 {
      type string;
    }
    leaf union-leaf-enumeration {
      type string;
    }
    leaf union-leaf-identityref {
      type string;
    }
    leaf union-leaf-boolean {
      type string;
    }
    leaf union-leaf-string {
      type string;
    }
  }

  grouping ncs_template_all-type-union-leaflist {
    leaf-list union-leaflist1 {
      // NCS patched for predictable order
      ordered-by user;
      type string;
    }
    leaf-list union-leaflist-integer8 {
      // NCS patched for predictable order
      ordered-by user;
      type string;
    }
    leaf-list union-leaflist-integer16 {
      // NCS patched for predictable order
      ordered-by user;
      type string;
    }
    leaf-list union-leaflist-integer32 {
      // NCS patched for predictable order
      ordered-by user;
      type string;
    }
  }

  grouping ncs_rpc_notif_all-type-leaves {
    leaf int8-leaf {
      type int8;
    }
    leaf int16-leaf {
      type int16;
    }
    leaf int32-leaf {
      type int32;
    }
    leaf int64-leaf {
      type int64;
    }
    leaf uint8-leaf {
      type uint8;
    }
    leaf uint16-leaf {
      type uint16;
    }
    leaf uint32-leaf {
      type uint32;
    }
    leaf uint64-leaf {
      type uint64;
    }
    leaf decimal64-leaf {
      type decimal64 {
        fraction-digits 2;
      }
    }
    leaf string-leaf {
      type string;
    }
    leaf boolean-leaf {
      type boolean;
    }
    leaf enumeration-leaf {
      type ncs_rpc_notif_season-enum;
    }
    leaf bits-leaf {
      type ncs_rpc_notif_bits-type;
    }
    leaf identityref-leaf {
      type ncs_rpc_notif_id-type;
    }
    leaf empty-leaf {
      type empty;
    }
    leaf leafref-string {
      type leafref {
        path "../string-leaf";
      }
    }
    leaf leafref-boolean {
      type leafref {
        path "../boolean-leaf";
      }
    }
  }

  grouping ncs_rpc_notif_all-type-leaf-lists {
    leaf-list int8-leaflist {
      type int8;
    }
    leaf-list int16-leaflist {
      type int16;
    }
    leaf-list int32-leaflist {
      type int32;
    }
    leaf-list int64-leaflist {
      type int64;
    }
    leaf-list uint8-leaflist {
      type uint8;
    }
    leaf-list uint16-leaflist {
      type uint16;
    }
    leaf-list uint32-leaflist {
      type uint32;
    }
    leaf-list uint64-leaflist {
      type uint64;
    }
    leaf-list decimal64-leaflist {
      type decimal64 {
        fraction-digits 2;
      }
    }
    leaf-list string-leaflist {
      type string;
    }
    leaf-list boolean-leaflist {
      type boolean;
    }
    leaf-list enumeration-leaflist {
      type ncs_rpc_notif_season-enum;
    }
    leaf-list bits-leaflist {
      type ncs_rpc_notif_bits-type;
    }
    leaf-list identityref-leaflist {
      type ncs_rpc_notif_id-type;
    }
  }

  grouping ncs_rpc_notif_all-type-union-leaf {
    leaf union-leaf-int8 {
      type union {
        type int8;
        type string;
      }
    }
    leaf union-leaf-int16 {
      type union {
        type int16;
        type string;
      }
    }
    leaf union-leaf-int32 {
      type union {
        type int32;
        type string;
      }
    }
    leaf union-leaf-int64 {
      type union {
        type int64;
        type string;
      }
    }
    leaf union-leaf-uint8 {
      type union {
        type uint8;
        type string;
      }
    }
    leaf union-leaf-uint16 {
      type union {
        type uint16;
        type string;
      }
    }
    leaf union-leaf-uint32 {
      type union {
        type uint32;
        type string;
      }
    }
    leaf union-leaf-uint64 {
      type union {
        type uint64;
        type string;
      }
    }
    leaf union-leaf-enumeration {
      type union {
        type enumeration {
          enum "one";
          enum "two";
          enum "three";
        }
        type string;
      }
    }
    leaf union-leaf-identityref {
      type union {
        type ncs_rpc_notif_id-type;
        type string;
      }
    }
    leaf union-leaf-boolean {
      type union {
        type boolean;
        type string;
      }
    }
    leaf union-leaf-string {
      type union {
        type string;
        type int8;
      }
    }
  }

  grouping ncs_rpc_notif_all-type-union-leaflist {
    leaf-list union-leaflist1 {
      type union {
        type boolean;
        type uint64;
        type int64;
        type ncs_rpc_notif_id-type;
        type decimal64 {
          fraction-digits 8;
        }
        type enumeration {
          enum "red";
          enum "blue";
          enum "voilet";
        }
        type bits {
          bit zero;
          bit one;
        }
        type string;
      }
    }
    leaf-list union-leaflist-integer8 {
      type union {
        type uint8;
        type int8;
      }
    }
    leaf-list union-leaflist-integer16 {
      type union {
        type uint16;
        type int16;
      }
    }
    leaf-list union-leaflist-integer32 {
      type union {
        type uint32;
        type int32;
      }
    }
  }

  grouping live_ncs_all-type-leaves {
    leaf int8-leaf {
      type int8;
    }
    leaf int16-leaf {
      type int16;
    }
    leaf int32-leaf {
      type int32;
    }
    leaf int64-leaf {
      type int64;
    }
    leaf uint8-leaf {
      type uint8;
    }
    leaf uint16-leaf {
      type uint16;
    }
    leaf uint32-leaf {
      type uint32;
    }
    leaf uint64-leaf {
      type uint64;
    }
    leaf decimal64-leaf {
      type decimal64 {
        fraction-digits 2;
      }
    }
    leaf string-leaf {
      type string;
    }
    leaf boolean-leaf {
      type boolean;
    }
    leaf enumeration-leaf {
      type live_ncs_season-enum;
    }
    leaf bits-leaf {
      type live_ncs_bits-type;
    }
    leaf identityref-leaf {
      type live_ncs_id-type;
    }
    leaf empty-leaf {
      type empty;
    }
    leaf leafref-string {
      type leafref {
        path "../string-leaf";
      }
    }
    leaf leafref-boolean {
      type leafref {
        path "../boolean-leaf";
      }
    }
  }

  grouping live_ncs_all-type-leaf-lists {
    leaf-list int8-leaflist {
      type int8;
    }
    leaf-list int16-leaflist {
      type int16;
    }
    leaf-list int32-leaflist {
      type int32;
    }
    leaf-list int64-leaflist {
      type int64;
    }
    leaf-list uint8-leaflist {
      type uint8;
    }
    leaf-list uint16-leaflist {
      type uint16;
    }
    leaf-list uint32-leaflist {
      type uint32;
    }
    leaf-list uint64-leaflist {
      type uint64;
    }
    leaf-list decimal64-leaflist {
      type decimal64 {
        fraction-digits 2;
      }
    }
    leaf-list string-leaflist {
      type string;
    }
    leaf-list boolean-leaflist {
      type boolean;
    }
    leaf-list enumeration-leaflist {
      type live_ncs_season-enum;
    }
    leaf-list bits-leaflist {
      type live_ncs_bits-type;
    }
    leaf-list identityref-leaflist {
      type live_ncs_id-type;
    }
  }

  grouping live_ncs_all-type-union-leaf {
    leaf union-leaf-int8 {
      type union {
        type int8;
        type string;
      }
    }
    leaf union-leaf-int16 {
      type union {
        type int16;
        type string;
      }
    }
    leaf union-leaf-int32 {
      type union {
        type int32;
        type string;
      }
    }
    leaf union-leaf-int64 {
      type union {
        type int64;
        type string;
      }
    }
    leaf union-leaf-uint8 {
      type union {
        type uint8;
        type string;
      }
    }
    leaf union-leaf-uint16 {
      type union {
        type uint16;
        type string;
      }
    }
    leaf union-leaf-uint32 {
      type union {
        type uint32;
        type string;
      }
    }
    leaf union-leaf-uint64 {
      type union {
        type uint64;
        type string;
      }
    }
    leaf union-leaf-enumeration {
      type union {
        type enumeration {
          enum "one";
          enum "two";
          enum "three";
        }
        type string;
      }
    }
    leaf union-leaf-identityref {
      type union {
        type live_ncs_id-type;
        type string;
      }
    }
    leaf union-leaf-boolean {
      type union {
        type boolean;
        type string;
      }
    }
    leaf union-leaf-string {
      type union {
        type string;
        type int8;
      }
    }
  }

  grouping live_ncs_all-type-union-leaflist {
    leaf-list union-leaflist1 {
      type union {
        type boolean;
        type uint64;
        type int64;
        type live_ncs_id-type;
        type decimal64 {
          fraction-digits 8;
        }
        type enumeration {
          enum "red";
          enum "blue";
          enum "voilet";
        }
        type bits {
          bit zero;
          bit one;
        }
        type string;
      }
    }
    leaf-list union-leaflist-integer8 {
      type union {
        type uint8;
        type int8;
      }
    }
    leaf-list union-leaflist-integer16 {
      type union {
        type uint16;
        type int16;
      }
    }
    leaf-list union-leaflist-integer32 {
      type union {
        type uint32;
        type int32;
      }
    }
  }

  grouping all-type-leaves {
    leaf int8-leaf {
      type int8;
    }
    leaf int16-leaf {
      type int16;
    }
    leaf int32-leaf {
      type int32;
    }
    leaf int64-leaf {
      type int64;
    }
    leaf uint8-leaf {
      type uint8;
    }
    leaf uint16-leaf {
      type uint16;
    }
    leaf uint32-leaf {
      type uint32;
    }
    leaf uint64-leaf {
      type uint64;
    }
    leaf decimal64-leaf {
      type decimal64 {
        fraction-digits 2;
      }
    }
    leaf string-leaf {
      type string;
    }
    leaf boolean-leaf {
      type boolean;
    }
    leaf enumeration-leaf {
      type season-enum;
    }
    leaf bits-leaf {
      type bits-type;
    }
    leaf identityref-leaf {
      type id-type;
    }
    leaf empty-leaf {
      type empty;
    }
    leaf leafref-string {
      type leafref {
        path "../string-leaf";
      }
    }
    leaf leafref-boolean {
      type leafref {
        path "../boolean-leaf";
      }
    }
  }

  grouping all-type-leaf-lists {
    leaf-list int8-leaflist {
      type int8;
    }
    leaf-list int16-leaflist {
      type int16;
    }
    leaf-list int32-leaflist {
      type int32;
    }
    leaf-list int64-leaflist {
      type int64;
    }
    leaf-list uint8-leaflist {
      type uint8;
    }
    leaf-list uint16-leaflist {
      type uint16;
    }
    leaf-list uint32-leaflist {
      type uint32;
    }
    leaf-list uint64-leaflist {
      type uint64;
    }
    leaf-list decimal64-leaflist {
      type decimal64 {
        fraction-digits 2;
      }
    }
    leaf-list string-leaflist {
      type string;
    }
    leaf-list boolean-leaflist {
      type boolean;
    }
    leaf-list enumeration-leaflist {
      type season-enum;
    }
    leaf-list bits-leaflist {
      type bits-type;
    }
    leaf-list identityref-leaflist {
      type id-type;
    }
  }

  grouping all-type-union-leaf {
    leaf union-leaf-int8 {
      type union {
        type int8;
        type string;
      }
    }
    leaf union-leaf-int16 {
      type union {
        type int16;
        type string;
      }
    }
    leaf union-leaf-int32 {
      type union {
        type int32;
        type string;
      }
    }
    leaf union-leaf-int64 {
      type union {
        type int64;
        type string;
      }
    }
    leaf union-leaf-uint8 {
      type union {
        type uint8;
        type string;
      }
    }
    leaf union-leaf-uint16 {
      type union {
        type uint16;
        type string;
      }
    }
    leaf union-leaf-uint32 {
      type union {
        type uint32;
        type string;
      }
    }
    leaf union-leaf-uint64 {
      type union {
        type uint64;
        type string;
      }
    }
    leaf union-leaf-enumeration {
      type union {
        type enumeration {
          enum "one";
          enum "two";
          enum "three";
        }
        type string;
      }
    }
    leaf union-leaf-identityref {
      type union {
        type id-type;
        type string;
      }
    }
    leaf union-leaf-boolean {
      type union {
        type boolean;
        type string;
      }
    }
    leaf union-leaf-string {
      type union {
        type string;
        type int8;
      }
    }
  }

  grouping all-type-union-leaflist {
    leaf-list union-leaflist1 {
      type union {
        type boolean;
        type uint64;
        type int64;
        type id-type;
        type decimal64 {
          fraction-digits 8;
        }
        type enumeration {
          enum "red";
          enum "blue";
          enum "voilet";
        }
        type bits {
          bit zero;
          bit one;
        }
        type string;
      }
    }
    leaf-list union-leaflist-integer8 {
      type union {
        type uint8;
        type int8;
      }
    }
    leaf-list union-leaflist-integer16 {
      type union {
        type uint16;
        type int16;
      }
    }
    leaf-list union-leaflist-integer32 {
      type union {
        type uint32;
        type int32;
      }
    }
  }

  augment "/ncs:devices/ncs:device/ncs:config" {
    container config-nodes {
      tailf:ncs-device-type "netconf";
      tailf:display-when "not(../../ncs:module) or ../../ncs:module[ncs:name='yccdemo']";
      description
        "For testing Edit-ConfigData for basic types";
      uses all-type-leaves;
      uses all-type-union-leaf;
    }
    container level1 {
      tailf:ncs-device-type "netconf";
      tailf:display-when "not(../../ncs:module) or ../../ncs:module[ncs:name='yccdemo']";
      leaf level1leaf {
        type bits-type;
      }
      list level2 {
        key "level2keyleaf";
        leaf level2keyleaf {
          type int8;
        }
        leaf level2leaf {
          type bits-type;
        }
        list level3 {
          key "level3keyleaf";
          leaf level3keyleaf {
            type int8;
          }
          leaf level3leaf {
            type bits-type;
          }
        }
      }
    }
    list lrefUnionKeyList {
      tailf:ncs-device-type "netconf";
      tailf:display-when "not(../ncs:module) or ../ncs:module[ncs:name='yccdemo']";
      key "leaf-ref-key";
      leaf leaf-ref-key {
        type leafref {
          path "/ncs:devices/ncs:device/ncs:config/yccdemo:config-nodes/yccdemo:union-leaf-int8" {
            tailf:xpath-root 3;
          }
        }
      }
    }
    list U {
      tailf:ncs-device-type "netconf";
      tailf:display-when "not(../ncs:module) or ../ncs:module[ncs:name='yccdemo']";
      key "u1";
      leaf u1 {
        type union-type;
      }
      leaf u2 {
        type string;
      }
      list V {
        key "v1";
        leaf v1 {
          type union-type;
        }
        leaf v2 {
          type string;
        }
        list W {
          key "w1";
          leaf w1 {
            type union-type;
          }
          leaf w2 {
            type string;
          }
          leaf wbool-leafref {
            type leafref {
              path "/ncs:devices/ncs:device/ncs:config/yccdemo:config-nodes/boolean-leaf" {
                tailf:xpath-root 3;
              }
            }
          }
        }
      }
      list Boo {
        key "w1";
        leaf w1 {
          type union-type;
        }
        leaf bool-keyref {
          type leafref {
            path "/ncs:devices/ncs:device/ncs:config/yccdemo:config-nodes/boolean-leaf" {
              tailf:xpath-root 3;
            }
          }
        }
      }
    }
    container parent-container {
      tailf:ncs-device-type "netconf";
      tailf:display-when "not(../../ncs:module) or ../../ncs:module[ncs:name='yccdemo']";
      description
        "For testing Edit nodes with container and nested container";
      leaf alpha {
        type string;
      }
      leaf-list beta {
        type string;
      }
      leaf omega {
        type decimal64 {
          fraction-digits 4;
        }
      }
      leaf-list kappa {
        type uint8;
      }
      list child-list {
        key "gama";
        leaf gama {
          type string;
        }
        leaf delta {
          type int8;
        }
        leaf-list theta {
          type string;
        }
        leaf-list lambda {
          type uint8;
        }
      }
      list dec64-list {
        key "decimal64-leaf";
        leaf decimal64-leaf {
          type decimal64 {
            fraction-digits 2;
          }
        }
        leaf phi {
          type int8;
        }
      }
      list enumList {
        key "enum-leaf";
        leaf enum-leaf {
          type season-enum;
        }
      }
    }
    // NCS drop config false list operlevel1
    // NCS drop config false container 'oper-nodes'
    // NCS drop config false list 'oper-AList'
    // NCS drop config false container 'oper-P'
    // NCS drop config false list operEnum1
  }
  augment "/ncs:devices/ncs:device/ncs:live-status" {
    container config-nodes {
      tailf:ncs-device-type "netconf";
      tailf:display-when "not(../../ncs:module) or ../../ncs:module[ncs:name='yccdemo'] or (../../ncs:live-status-protocol[not(ncs:capability)]) or (../../ncs:live-status-protocol/ncs:capability/ncs:module[.='yccdemo'])";
      description
        "For testing Edit-ConfigData for basic types";
      uses live_ncs_all-type-leaves;
      uses live_ncs_all-type-union-leaf;
    }
    container level1 {
      tailf:ncs-device-type "netconf";
      tailf:display-when "not(../../ncs:module) or ../../ncs:module[ncs:name='yccdemo'] or (../../ncs:live-status-protocol[not(ncs:capability)]) or (../../ncs:live-status-protocol/ncs:capability/ncs:module[.='yccdemo'])";
      leaf level1leaf {
        type live_ncs_bits-type;
      }
      list level2 {
        key "level2keyleaf";
        leaf level2keyleaf {
          type int8;
        }
        leaf level2leaf {
          type live_ncs_bits-type;
        }
        list level3 {
          key "level3keyleaf";
          leaf level3keyleaf {
            type int8;
          }
          leaf level3leaf {
            type live_ncs_bits-type;
          }
        }
      }
    }
    list lrefUnionKeyList {
      tailf:ncs-device-type "netconf";
      tailf:display-when "not(../ncs:module) or ../ncs:module[ncs:name='yccdemo'] or (../ncs:live-status-protocol[not(ncs:capability)]) or (../ncs:live-status-protocol/ncs:capability/ncs:module[.='yccdemo'])";
      key "leaf-ref-key";
      leaf leaf-ref-key {
        type leafref {
          path "/ncs:devices/ncs:device/ncs:live-status/yccdemo:config-nodes/yccdemo:union-leaf-int8" {
            tailf:xpath-root 3;
          }
        }
      }
    }
    list U {
      tailf:ncs-device-type "netconf";
      tailf:display-when "not(../ncs:module) or ../ncs:module[ncs:name='yccdemo'] or (../ncs:live-status-protocol[not(ncs:capability)]) or (../ncs:live-status-protocol/ncs:capability/ncs:module[.='yccdemo'])";
      key "u1";
      leaf u1 {
        type live_ncs_union-type;
      }
      leaf u2 {
        type string;
      }
      list V {
        key "v1";
        leaf v1 {
          type live_ncs_union-type;
        }
        leaf v2 {
          type string;
        }
        list W {
          key "w1";
          leaf w1 {
            type live_ncs_union-type;
          }
          leaf w2 {
            type string;
          }
          leaf wbool-leafref {
            type leafref {
              path "/ncs:devices/ncs:device/ncs:live-status/yccdemo:config-nodes/boolean-leaf" {
                tailf:xpath-root 3;
              }
            }
          }
        }
      }
      list Boo {
        key "w1";
        leaf w1 {
          type live_ncs_union-type;
        }
        leaf bool-keyref {
          type leafref {
            path "/ncs:devices/ncs:device/ncs:live-status/yccdemo:config-nodes/boolean-leaf" {
              tailf:xpath-root 3;
            }
          }
        }
      }
    }
    container parent-container {
      tailf:ncs-device-type "netconf";
      tailf:display-when "not(../../ncs:module) or ../../ncs:module[ncs:name='yccdemo'] or (../../ncs:live-status-protocol[not(ncs:capability)]) or (../../ncs:live-status-protocol/ncs:capability/ncs:module[.='yccdemo'])";
      description
        "For testing Edit nodes with container and nested container";
      leaf alpha {
        type string;
      }
      leaf-list beta {
        type string;
      }
      leaf omega {
        type decimal64 {
          fraction-digits 4;
        }
      }
      leaf-list kappa {
        type uint8;
      }
      list child-list {
        key "gama";
        leaf gama {
          type string;
        }
        leaf delta {
          type int8;
        }
        leaf-list theta {
          type string;
        }
        leaf-list lambda {
          type uint8;
        }
      }
      list dec64-list {
        key "decimal64-leaf";
        leaf decimal64-leaf {
          type decimal64 {
            fraction-digits 2;
          }
        }
        leaf phi {
          type int8;
        }
      }
      list enumList {
        key "enum-leaf";
        leaf enum-leaf {
          type live_ncs_season-enum;
        }
      }
    }
    list operlevel1 {
      tailf:ncs-device-type "netconf";
      tailf:display-when "not(../ncs:module) or ../ncs:module[ncs:name='yccdemo'] or (../ncs:live-status-protocol[not(ncs:capability)]) or (../ncs:live-status-protocol/ncs:capability/ncs:module[.='yccdemo'])";
      key "operlevel1keyleaf";
      leaf operlevel1keyleaf {
        type int8;
      }
      leaf operlevel1leaf {
        type live_ncs_bits-type;
      }
      list operlevel2 {
        key "operlevel2keyleaf";
        leaf operlevel2keyleaf {
          type int8;
        }
        leaf operlevel2leaf {
          type live_ncs_bits-type;
        }
        list operlevel3 {
          key "operlevel3keyleaf";
          leaf operlevel3keyleaf {
            type int8;
          }
          leaf operlevel3leaf {
            type live_ncs_bits-type;
          }
        }
      }
    }
    container oper-nodes {
      tailf:ncs-device-type "netconf";
      tailf:display-when "not(../../ncs:module) or ../../ncs:module[ncs:name='yccdemo'] or (../../ncs:live-status-protocol[not(ncs:capability)]) or (../../ncs:live-status-protocol/ncs:capability/ncs:module[.='yccdemo'])";
      uses live_ncs_all-type-leaves;
      uses live_ncs_all-type-union-leaf;
      leaf-list uint8-leaflist {
        type uint8;
      }
      leaf-list string-leaflist {
        type string;
      }
    }
    list oper-AList {
      tailf:ncs-device-type "netconf";
      tailf:display-when "not(../ncs:module) or ../ncs:module[ncs:name='yccdemo'] or (../ncs:live-status-protocol[not(ncs:capability)]) or (../ncs:live-status-protocol/ncs:capability/ncs:module[.='yccdemo'])";
      key "union-enum-key-leaf";
      leaf union-enum-key-leaf {
        type live_ncs_union-type;
      }
      list BList {
        key "union-ip-key-leaf";
        leaf union-ip-key-leaf {
          type inet:ip-address;
        }
        leaf-list uint8-bleaflist {
          type uint8;
        }
        leaf-list string-bleaflist {
          type string;
        }
        list CList {
          key "union-c-leaf";
          leaf union-c-leaf {
            type live_ncs_union-type;
          }
          leaf-list uint8-cleaflist {
            type uint8;
          }
          leaf-list string-cleaflist {
            type string;
          }
        }
      }
    }
    container oper-P {
      tailf:ncs-device-type "netconf";
      tailf:display-when "not(../../ncs:module) or ../../ncs:module[ncs:name='yccdemo'] or (../../ncs:live-status-protocol[not(ncs:capability)]) or (../../ncs:live-status-protocol/ncs:capability/ncs:module[.='yccdemo'])";
      leaf int8-leaf {
        type int8;
      }
      list QList {
        key "address";
        leaf address {
          type inet:ip-address;
        }
        leaf string-leaf {
          type string;
        }
      }
    }
    list operEnum1 {
      tailf:ncs-device-type "netconf";
      tailf:display-when "not(../ncs:module) or ../ncs:module[ncs:name='yccdemo'] or (../ncs:live-status-protocol[not(ncs:capability)]) or (../ncs:live-status-protocol/ncs:capability/ncs:module[.='yccdemo'])";
      key "operEnum1KeyLeaf";
      leaf operEnum1KeyLeaf {
        type live_ncs_enum-type;
      }
      leaf enum1leaf {
        type live_ncs_season-enum;
      }
      list operEnum2 {
        key "operEnum2KeyLeaf";
        leaf operEnum2KeyLeaf {
          type live_ncs_enum-type;
        }
        leaf enum2leaf {
          type live_ncs_season-enum;
        }
        list operEnum3 {
          key "operEnum3KeyLeaf";
          leaf operEnum3KeyLeaf {
            type live_ncs_enum-type;
          }
          leaf enum3leaf {
            type live_ncs_season-enum;
          }
        }
      }
    }
  }
  augment "/ncs:devices/ncs:template/ncs:ned-id/ncs:config" {
    container config-nodes {
      description
        "For testing Edit-ConfigData for basic types";
      uses ncs_template_all-type-leaves;
      uses ncs_template_all-type-union-leaf;
    }
    container level1 {
      leaf level1leaf {
        type ncs_template_bits-type;
      }
      list level2 {
        // NCS patched for predictable order
        ordered-by user;
        key "level2keyleaf";
        leaf level2keyleaf {
          type string;
        }
        leaf level2leaf {
          type ncs_template_bits-type;
        }
        list level3 {
          // NCS patched for predictable order
          ordered-by user;
          key "level3keyleaf";
          leaf level3keyleaf {
            type string;
          }
          leaf level3leaf {
            type ncs_template_bits-type;
          }
        }
      }
    }
    list lrefUnionKeyList {
      // NCS patched for predictable order
      ordered-by user;
      key "leaf-ref-key";
      leaf leaf-ref-key {
        type string;
      }
    }
    list U {
      // NCS patched for predictable order
      ordered-by user;
      key "u1";
      leaf u1 {
        type ncs_template_union-type;
      }
      leaf u2 {
        type string;
      }
      list V {
        // NCS patched for predictable order
        ordered-by user;
        key "v1";
        leaf v1 {
          type ncs_template_union-type;
        }
        leaf v2 {
          type string;
        }
        list W {
          // NCS patched for predictable order
          ordered-by user;
          key "w1";
          leaf w1 {
            type ncs_template_union-type;
          }
          leaf w2 {
            type string;
          }
          leaf wbool-leafref {
            type string;
          }
        }
      }
      list Boo {
        // NCS patched for predictable order
        ordered-by user;
        key "w1";
        leaf w1 {
          type ncs_template_union-type;
        }
        leaf bool-keyref {
          type string;
        }
      }
    }
    container parent-container {
      description
        "For testing Edit nodes with container and nested container";
      leaf alpha {
        type string;
      }
      leaf-list beta {
        // NCS patched for predictable order
        ordered-by user;
        type string;
      }
      leaf omega {
        type string;
      }
      leaf-list kappa {
        // NCS patched for predictable order
        ordered-by user;
        type string;
      }
      list child-list {
        // NCS patched for predictable order
        ordered-by user;
        key "gama";
        leaf gama {
          type string;
        }
        leaf delta {
          type string;
        }
        leaf-list theta {
          // NCS patched for predictable order
          ordered-by user;
          type string;
        }
        leaf-list lambda {
          // NCS patched for predictable order
          ordered-by user;
          type string;
        }
      }
      list dec64-list {
        // NCS patched for predictable order
        ordered-by user;
        key "decimal64-leaf";
        leaf decimal64-leaf {
          type string;
        }
        leaf phi {
          type string;
        }
      }
      list enumList {
        // NCS patched for predictable order
        ordered-by user;
        key "enum-leaf";
        leaf enum-leaf {
          type ncs_template_season-enum;
        }
      }
    }
    // NCS drop config false list operlevel1
    // NCS drop config false container 'oper-nodes'
    // NCS drop config false list 'oper-AList'
    // NCS drop config false container 'oper-P'
    // NCS drop config false list operEnum1
  }

  identity "id2.2" {
    base id2;
  }

  identity "id2.1" {
    base id2;
  }

  identity id3 {
    base id;
  }

  identity id2 {
    base id;
  }

  identity id1 {
    base id;
  }

  identity id;
}
