module ciena-openconfig-system {
  // Generated by yanger -t ncs
  tailf:mount-id "saos1051-nc-1.0:saos1051-nc-1.0";
  tailf:ncs-device-type "netconf";

  namespace "http://www.ciena.com/ns/yang/ciena-openconfig-system";
  prefix ciena-oc-sys;

  import openconfig-system {
    prefix oc-sys;
  }
  import yuma-ncx {
    prefix ncx;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's augmentations to openconfig-system.

      Copyright (c) 2018 Ciena Corporation.  All rights
      reserved.

      All information contained herein is, and remains
      the property of Ciena Corporation. Dissemination of this
      information or reproduction of this material is strictly
      forbidden unless prior written permission is obtained from
      Ciena Corporation.";

  revision 2018-01-29 {
    description
      "Initial version";
    reference
      "RFC 6020: YANG - A Data Modeling Language for
       the Network Configuration Protocol (NETCONF).
       No specific reference; standard not available.";
  }

  augment "/ncs:devices/ncs:template/ncs:ned-id/ncs:config/oc-sys:system/oc-sys:aaa/oc-sys:authentication/oc-sys:users/oc-sys:user/oc-sys:config" {
    leaf password {
      type string;
      ncx:password;
      description
        "The user password in cleartext, only the hashed
         value will be stored";
    }
  }
  augment "/ncs:devices/ncs:device/ncs:live-status/oc-sys:system/oc-sys:aaa/oc-sys:authentication/oc-sys:users/oc-sys:user/oc-sys:config" {
    leaf password {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type string;
      ncx:password;
      description
        "The user password in cleartext, only the hashed
         value will be stored";
    }
  }
  augment "/ncs:devices/ncs:device/ncs:config/oc-sys:system/oc-sys:aaa/oc-sys:authentication/oc-sys:users/oc-sys:user/oc-sys:config" {
    leaf password {
      tailf:ncs-device-type "netconf";
      tailf:display-when "not(../../../../../../../../ncs:module) or ../../../../../../../../ncs:module[ncs:name='ciena-openconfig-system']";
      type string;
      ncx:password;
      description
        "The user password in cleartext, only the hashed
         value will be stored";
    }
  }
  augment "/ncs:devices/ncs:device/ncs:live-status/oc-sys:system/oc-sys:aaa/oc-sys:authentication/oc-sys:users/oc-sys:user/oc-sys:state" {
    leaf lockout-time {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type uint16;
      description
        "Amount of time left before the lockout ends";
    }
    leaf last-failure {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type yang:date-and-time;
      description
        "Last timestamp of user login failure";
    }
  }
}
