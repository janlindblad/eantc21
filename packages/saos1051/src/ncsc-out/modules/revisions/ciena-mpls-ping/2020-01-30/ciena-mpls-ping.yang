module ciena-mpls-ping {
  // Generated by yanger -t ncs
  tailf:mount-id "saos1051-nc-1.0:saos1051-nc-1.0";
  tailf:ncs-device-type "netconf";

  yang-version 1.1;
  namespace "http://ciena.com/ns/yang/ciena-mpls-ping";
  prefix mpls-ping;

  import ietf-inet-types {
    prefix inet;
  }
  import ciena-oam-options {
    prefix oam-options;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's specific implementation
     for MPLS ping.

     Copyright (c) 2018  Ciena Corporation.  All rights
     reserved.

     All information contained herein is, and remains the
     property of Ciena Corporation. Dissemination of this
     information or reproduction of this material is strictly
     forbidden unless prior written permission is obtained
     from Ciena Corporation.";

  revision 2020-01-30 {
    description
      "Marking this yang model as deprecated, as a generic
       modelling approach will be used for both ip & mpls.";
  }
  revision 2019-06-05 {
    description
      "Added support for L2VPN, BGP-LU, and SR pings.";
  }
  revision 2018-08-27 {
    description
      "Initial version of MPLS ping datamodel.";
  }

  augment "/ncs:devices/ncs:device/ncs:rpc" {
    container rpc-ping-mpls-pseudowire {
      tailf:ncs-device-type "netconf";
      tailf:display-when "not(../../ncs:module) or ../../ncs:module[ncs:name='ciena-mpls-ping']";
      tailf:action ping-mpls-pseudowire {
        tailf:actionpoint ncsproxy {
          tailf:internal;
        }
        status deprecated;
        input {
          leaf pseudowire-name {
            type string {
              length "1..255";
            }
            mandatory true;
            description
              "Pseudowire Name";
          }
          uses oam-options:ncs_rpc_notif_ping-base-input-options;
        }
        output {
          leaf return-code {
            type oam-options:ncs_rpc_notif_mpls-oam-return-code;
            description
              "The response for an echo request";
          }
          uses oam-options:ncs_rpc_notif_ping-base-output;
        }
      }
    }
  }
  augment "/ncs:devices/ncs:device-group/ncs:ned-id/ncs:rpc" {
    container rpc-ping-mpls-pseudowire {
      tailf:ncs-device-type "netconf";
      tailf:display-when "/ncs:devices/ncs:device[ncs:name=current()/../../../ncs:member]/ncs:module[ncs:name='ciena-mpls-ping']";
      tailf:action ping-mpls-pseudowire {
        tailf:actionpoint ncsproxy {
          tailf:internal;
        }
        status deprecated;
        input {
          leaf pseudowire-name {
            type string {
              length "1..255";
            }
            mandatory true;
            description
              "Pseudowire Name";
          }
          uses oam-options:ncs_rpc_notif_ping-base-input-options;
        }
        output {
          container "device" {
            leaf "name" {
              type string;
            }
            leaf "info" {
              type string;
            }
            container "result" {
              leaf return-code {
                type oam-options:ncs_rpc_notif_mpls-oam-return-code;
                description
                  "The response for an echo request";
              }
              uses oam-options:ncs_rpc_notif_ping-base-output;
            }
          }
        }
      }
    }
  }
  augment "/ncs:devices/ncs:device/ncs:rpc" {
    container rpc-ping-mpls-lsp {
      tailf:ncs-device-type "netconf";
      tailf:display-when "not(../../ncs:module) or ../../ncs:module[ncs:name='ciena-mpls-ping']";
      tailf:action ping-mpls-lsp {
        tailf:actionpoint ncsproxy {
          tailf:internal;
        }
        status deprecated;
        input {
          leaf fec-type {
            type oam-options:ncs_rpc_notif_mpls-fec-type;
            mandatory true;
            description
              "FEC type of the destination";
          }
          leaf destination {
            type inet:ip-prefix;
            mandatory true;
            description
              "Destination address";
          }
          leaf source {
            type inet:ip-address;
            description
              "Source address";
          }
          uses oam-options:ncs_rpc_notif_ping-base-input-options;
          leaf backup {
            when "../fec-type='sr-isis'" {
              tailf:xpath-root 3;
            }
            type empty;
            description
              "Backup Path";
          }
        }
        output {
          leaf return-code {
            type oam-options:ncs_rpc_notif_mpls-oam-return-code;
            description
              "The response for an echo request";
          }
          uses oam-options:ncs_rpc_notif_ping-base-output;
        }
      }
    }
  }
  augment "/ncs:devices/ncs:device-group/ncs:ned-id/ncs:rpc" {
    container rpc-ping-mpls-lsp {
      tailf:ncs-device-type "netconf";
      tailf:display-when "/ncs:devices/ncs:device[ncs:name=current()/../../../ncs:member]/ncs:module[ncs:name='ciena-mpls-ping']";
      tailf:action ping-mpls-lsp {
        tailf:actionpoint ncsproxy {
          tailf:internal;
        }
        status deprecated;
        input {
          leaf fec-type {
            type oam-options:ncs_rpc_notif_mpls-fec-type;
            mandatory true;
            description
              "FEC type of the destination";
          }
          leaf destination {
            type inet:ip-prefix;
            mandatory true;
            description
              "Destination address";
          }
          leaf source {
            type inet:ip-address;
            description
              "Source address";
          }
          uses oam-options:ncs_rpc_notif_ping-base-input-options;
          leaf backup {
            when "../fec-type='sr-isis'" {
              tailf:xpath-root 4;
            }
            type empty;
            description
              "Backup Path";
          }
        }
        output {
          container "device" {
            leaf "name" {
              type string;
            }
            leaf "info" {
              type string;
            }
            container "result" {
              leaf return-code {
                type oam-options:ncs_rpc_notif_mpls-oam-return-code;
                description
                  "The response for an echo request";
              }
              uses oam-options:ncs_rpc_notif_ping-base-output;
            }
          }
        }
      }
    }
  }
}
