module ciena-nfvi-virtual-interface {
  // Generated by yanger -t ncs
  tailf:mount-id "saos1051-nc-1.0:saos1051-nc-1.0";
  tailf:ncs-device-type "netconf";

  namespace "http://www.ciena.com/ns/yang/ciena-nfvi-virtual-interface";
  prefix ciena-nfvi-vintf;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's global configuration for virtual interfaces settings.

     Copyright (c) 2019 Ciena Corporation.  All rights
     reserved.

     All information contained herein is, and remains
     the property of Ciena Corporation. Dissemination of this
     information or reproduction of this material is strictly
     forbidden unless prior written permission is obtained from
     Ciena Corporation.";

  revision 2019-05-15 {
    description
      "Initial version";
    reference
      "RFC 6020: YANG - A Data Modeling Language for
       the Network Configuration Protocol (NETCONF).
       No specific reference; standard not available.";
  }

  typedef ncs_template_nfvi-virtual-interface-type {
    type string;
  }

  typedef ncs_template_nfvi-virtual-interface-name-type {
    type string;
    description
      "The NFVI virtual interface name can be start
       with letters, and ends with letters or digits.
       It can contains letters, digits and '-' and '_'
       character in the middle.";
  }

  typedef ncs_rpc_notif_nfvi-virtual-interface-type {
    type enumeration {
      enum "vhost-user" {
        description
          "NFVi virtual interface type vhost";
      }
    }
  }

  typedef ncs_rpc_notif_nfvi-virtual-interface-name-type {
    type string {
      length "1..255";
      pattern '[A-Za-z]+([A-Za-z0-9_-]*[A-Za-z0-9]+)?';
    }
    description
      "The NFVI virtual interface name can be start
       with letters, and ends with letters or digits.
       It can contains letters, digits and '-' and '_'
       character in the middle.";
  }

  typedef live_ncs_nfvi-virtual-interface-type {
    type enumeration {
      enum "vhost-user" {
        description
          "NFVi virtual interface type vhost";
      }
    }
  }

  typedef live_ncs_nfvi-virtual-interface-name-type {
    type string {
      length "1..255";
      pattern '[A-Za-z]+([A-Za-z0-9_-]*[A-Za-z0-9]+)?';
    }
    description
      "The NFVI virtual interface name can be start
       with letters, and ends with letters or digits.
       It can contains letters, digits and '-' and '_'
       character in the middle.";
  }

  typedef nfvi-virtual-interface-type {
    type enumeration {
      enum "vhost-user" {
        description
          "NFVi virtual interface type vhost";
      }
    }
  }

  typedef nfvi-virtual-interface-name-type {
    type string {
      length "1..255";
      pattern '[A-Za-z]+([A-Za-z0-9_-]*[A-Za-z0-9]+)?';
    }
    description
      "The NFVI virtual interface name can be start
       with letters, and ends with letters or digits.
       It can contains letters, digits and '-' and '_'
       character in the middle.";
  }

  augment "/ncs:devices/ncs:device/ncs:config" {
    container nfvi-virtual-interfaces {
      tailf:ncs-device-type "netconf";
      tailf:display-when "not(../../ncs:module) or ../../ncs:module[ncs:name='ciena-nfvi-virtual-interface']";
      description
        "The virtual interfaces created for NFVi.";
      list nfvi-virtual-interface {
        key "name";
        leaf name {
          type nfvi-virtual-interface-name-type;
          description
            "The name of the NFVi virtual interface.";
        }
        leaf type {
          type nfvi-virtual-interface-type;
          description
            "The type of the NFVi virtual interface.";
        }
        // NCS drop config false container state
      }
    }
  }
  augment "/ncs:devices/ncs:device/ncs:live-status" {
    container nfvi-virtual-interfaces {
      tailf:ncs-device-type "netconf";
      tailf:display-when "not(../../ncs:module) or ../../ncs:module[ncs:name='ciena-nfvi-virtual-interface'] or (../../ncs:live-status-protocol[not(ncs:capability)]) or (../../ncs:live-status-protocol/ncs:capability/ncs:module[.='ciena-nfvi-virtual-interface'])";
      description
        "The virtual interfaces created for NFVi.";
      list nfvi-virtual-interface {
        key "name";
        leaf name {
          type live_ncs_nfvi-virtual-interface-name-type;
          description
            "The name of the NFVi virtual interface.";
        }
        leaf type {
          type live_ncs_nfvi-virtual-interface-type;
          description
            "The type of the NFVi virtual interface.";
        }
        container state {
          description
            "Operational state of the NFVi virtual interface";
          leaf ettp {
            type string;
            description
              "The corresponding ettp name of the NFVi virtual interface.";
          }
          leaf logical-port {
            type string;
            description
              "The corresponding logical port name of the NFVi virtual interface.";
          }
        }
      }
    }
  }
  augment "/ncs:devices/ncs:template/ncs:ned-id/ncs:config" {
    container nfvi-virtual-interfaces {
      description
        "The virtual interfaces created for NFVi.";
      list nfvi-virtual-interface {
        // NCS patched for predictable order
        ordered-by user;
        key "name";
        leaf name {
          type ncs_template_nfvi-virtual-interface-name-type;
          description
            "The name of the NFVi virtual interface.";
        }
        leaf type {
          type ncs_template_nfvi-virtual-interface-type;
          description
            "The type of the NFVi virtual interface.";
        }
        // NCS drop config false container state
      }
    }
  }
}
