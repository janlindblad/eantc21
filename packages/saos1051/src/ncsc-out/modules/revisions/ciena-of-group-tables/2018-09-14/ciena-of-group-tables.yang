module ciena-of-group-tables {
  // Generated by yanger -t ncs
  tailf:mount-id "saos1051-nc-1.0:saos1051-nc-1.0";
  tailf:ncs-device-type "netconf";

  namespace "http://www.ciena.com/ns/yang/ciena-pn/ciena-of-group-tables";
  prefix of-group-tables;

  import ciena-of-types {
    prefix of-types;
  }
  import ciena-of-vfsi {
    prefix of-vfsi;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's management data definition for the definition of
     Open Flow Group Tables.";

  revision 2018-09-14 {
    description
      "Initial Version.";
  }

  typedef ncs_template_group-table-ref {
    type string;
    description
      "This type is used by data models that need to reference
       configured group tables.";
  }

  typedef ncs_template_group-table-entry-ref {
    type string;
    description
      "This type is used by data models that need to reference
       configured group table entries.";
  }

  typedef ncs_rpc_notif_group-table-ref {
    type string;
    description
      "This type is used by data models that need to reference
       configured group tables.";
  }

  typedef ncs_rpc_notif_group-table-entry-ref {
    type string;
    description
      "This type is used by data models that need to reference
       configured group table entries.";
  }

  typedef live_ncs_group-table-ref {
    type leafref {
      path "/ncs:devices/ncs:device/ncs:live-status/of-group-tables:of-group-tables/of-group-tables:of-group-table/of-group-tables:name" {
        tailf:xpath-root 3;
      }
    }
    description
      "This type is used by data models that need to reference
       configured group tables.";
  }

  typedef live_ncs_group-table-entry-ref {
    type leafref {
      path "/ncs:devices/ncs:device/ncs:live-status/of-group-tables:of-group-tables/of-group-tables:of-group-table-entry/of-group-tables:group-identifier" {
        tailf:xpath-root 3;
      }
    }
    description
      "This type is used by data models that need to reference
       configured group table entries.";
  }

  typedef group-table-ref {
    type leafref {
      path "/ncs:devices/ncs:device/ncs:config/of-group-tables:of-group-tables/of-group-tables:of-group-table/of-group-tables:name" {
        tailf:xpath-root 3;
      }
    }
    description
      "This type is used by data models that need to reference
       configured group tables.";
  }

  typedef group-table-entry-ref {
    type leafref {
      path "/ncs:devices/ncs:device/ncs:config/of-group-tables:of-group-tables/of-group-tables:of-group-table-entry/of-group-tables:group-identifier" {
        tailf:xpath-root 3;
      }
    }
    description
      "This type is used by data models that need to reference
       configured group table entries.";
  }

  augment "/ncs:devices/ncs:device/ncs:rpc" {
    container rpc-of-group-table-entry-clear-statistics {
      tailf:ncs-device-type "netconf";
      tailf:display-when "not(../../ncs:module) or ../../ncs:module[ncs:name='ciena-of-group-tables']";
      tailf:action of-group-table-entry-clear-statistics {
        tailf:actionpoint ncsproxy {
          tailf:internal;
        }
        description
          "An RPC operation to clear the statistics for one or more Group Table Entries.";
        input {
          choice clear-scope {
            case group-table-entry {
              leaf group-table-entry {
                type of-group-tables:ncs_rpc_notif_group-table-entry-ref;
              }
              leaf group-table-entry-vfsi {
                type of-vfsi:ncs_rpc_notif_vfsi-id-ref;
              }
              description
                "Clear stats for this group-table-entry.";
            }
            case group-table {
              leaf group-table {
                type of-group-tables:ncs_rpc_notif_group-table-ref;
              }
              leaf group-table-vfsi {
                type of-vfsi:ncs_rpc_notif_vfsi-id-ref;
              }
              description
                "Clear stats for all group-table-entries with a group-table.";
            }
            case vfsi {
              leaf vfsi {
                type of-vfsi:ncs_rpc_notif_vfsi-id-ref;
              }
              description
                "Clear stats for all group-table-entries within a vfsi.";
            }
            case all {
              leaf all {
                type empty;
              }
              description
                "Clear stats for all group-table-entries.";
            }
          }
        }
        output {
          leaf status {
            type string;
            description
              "Status of the clear statistics operation.";
          }
        }
      }
    }
  }
  augment "/ncs:devices/ncs:device-group/ncs:ned-id/ncs:rpc" {
    container rpc-of-group-table-entry-clear-statistics {
      tailf:ncs-device-type "netconf";
      tailf:display-when "/ncs:devices/ncs:device[ncs:name=current()/../../../ncs:member]/ncs:module[ncs:name='ciena-of-group-tables']";
      tailf:action of-group-table-entry-clear-statistics {
        tailf:actionpoint ncsproxy {
          tailf:internal;
        }
        description
          "An RPC operation to clear the statistics for one or more Group Table Entries.";
        input {
          choice clear-scope {
            case group-table-entry {
              leaf group-table-entry {
                type of-group-tables:ncs_rpc_notif_group-table-entry-ref;
              }
              leaf group-table-entry-vfsi {
                type of-vfsi:ncs_rpc_notif_vfsi-id-ref;
              }
              description
                "Clear stats for this group-table-entry.";
            }
            case group-table {
              leaf group-table {
                type of-group-tables:ncs_rpc_notif_group-table-ref;
              }
              leaf group-table-vfsi {
                type of-vfsi:ncs_rpc_notif_vfsi-id-ref;
              }
              description
                "Clear stats for all group-table-entries with a group-table.";
            }
            case vfsi {
              leaf vfsi {
                type of-vfsi:ncs_rpc_notif_vfsi-id-ref;
              }
              description
                "Clear stats for all group-table-entries within a vfsi.";
            }
            case all {
              leaf all {
                type empty;
              }
              description
                "Clear stats for all group-table-entries.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:config" {
    container of-group-tables {
      tailf:ncs-device-type "netconf";
      tailf:display-when "not(../../ncs:module) or ../../ncs:module[ncs:name='ciena-of-group-tables']";
      description
        "Although the OpenFlow protocol calls for a single group table with all
         group table entries, the Broadcom OF-DPA describes models the pipeline
         with separate group tables.  OF-DPA reconciles with the OpenFlow protocol
         by encoding the group table into the group entry id.

         This YANG model does not need to reconcile directly with the OpenFlow
         protocol, so it explicitly models separate group tables in a similar fashion
         to the flow table definitions.

         The configuration model for group tables include a list of pre-created
         group tables, and a flat list of group table entries, where each entry is
         associated to a particular flow table by a reference.";
      list of-group-table {
        description
          "This is the list of OF-DPA-like Group Tables.  These are automatically
           created and configured by the switch, and should not be created by the
           controller. The group tables correspond to the Broadcom OF-DPA 2.0 tables.
           Only the table-description should be configured by the controller.

           The group table entries in this list do not contain the actual group table
           entries.  Those are in a separate list, with each flow entry pointing to
           the table which logically containers it.";
        key "name vfsi-id";
        leaf name {
          type of-types:name;
          description
            "This object indicates the identifier and is a text string that is
             used to identify a Group Table.
             Unique string values are chosen to uniquely identify the group-table.
             A Group Table can be considered to be a Forwarding Plane Table that
             is looked up in a Forwarding Plane Pipeline.";
        }
        leaf vfsi-id {
          type of-vfsi:vfsi-id-ref;
          description
            "An identifier of a Virtual Flow Switch Instance that this Group Table belongs to.
             This element should not be modified by the controller.";
        }
        leaf table-number {
          type of-types:table-number;
          description
            "An identifier of the Open Flow Group Table.";
        }
        leaf table-description {
          type string {
            length "1..127";
          }
          description
            "A more detailed description that an operator can use to describe the
             Group Table.";
        }
        // NCS drop config false leaf 'default-table'
      }
      list of-group-table-entry {
        description
          "This is the list of OpenFlow-like group table entries.  The controller
           creates and modifies these group table entries (along with the flow table
           entries) to directly control the switch forwarding plane.

           The group table entries are in a flat list, but they are logically
           associated with a specific group table by the group-table reference.";
        key "group-identifier vfsi-id";
        leaf group-identifier {
          type of-types:entry-id;
          description
            "An identifier to uniquely identify the group entry (unique across
             all group tables).";
        }
        leaf vfsi-id {
          type of-vfsi:vfsi-id-ref;
          description
            "An identifier of a Virtual Flow Switch Instance that this Flow Table belongs to.";
        }
        leaf group-table {
          type of-group-tables:group-table-ref;
          description
            "A reference to a Group Table.";
          mandatory true;
        }
        leaf entry-description {
          type string {
            length "1..127";
          }
          description
            "A more detailed description that an operator can use to describe the
             Group Table Entry.";
        }
        leaf group-type {
          type of-types:group-type;
          description
            "Identifies whether this is a select (ECMP) entry, an all (multicast/
             broadcast) entry, an indirect entry, or a fast failover entry.";
        }
        list action-buckets {
          description
            "The key to the group table entries are the action buckets.  The bucket
             semantics are specific to each group entry type.  Buckets are executed
             according to the OpenFlow specification semantics.  Another way to
             describe this is that packets are sent to one or more bucket when
             the packet is sent to a group table entry.

             The buckets each contain an action set which is applied to the packet.";
          key "bucket-id";
          leaf bucket-id {
            type of-types:entry-id;
            description
              "An identifier of the Bucket within an Open Flow Group Table.";
          }
          leaf weight {
            type of-types:weight;
          }
          container action-set {
            uses of-types:action-set;
            leaf group-id {
              type of-group-tables:group-table-entry-ref;
            }
          }
          leaf stats-collection {
            type of-types:stats-collection;
            description
              "Determines whether stats collection will be turned on or not for
               an action-bucket";
          }
        }
        leaf stats-collection {
          type of-types:stats-collection;
          description
            "Determines whether stats collection will be turned on or not for a
             group table entry";
        }
        // NCS drop config false leaf 'default-entry'
      }
    }
    // NCS drop config false container 'of-group-tables-state'
  }
  augment "/ncs:devices/ncs:device/ncs:live-status" {
    container of-group-tables {
      tailf:ncs-device-type "netconf";
      tailf:display-when "not(../../ncs:module) or ../../ncs:module[ncs:name='ciena-of-group-tables'] or (../../ncs:live-status-protocol[not(ncs:capability)]) or (../../ncs:live-status-protocol/ncs:capability/ncs:module[.='ciena-of-group-tables'])";
      description
        "Although the OpenFlow protocol calls for a single group table with all
         group table entries, the Broadcom OF-DPA describes models the pipeline
         with separate group tables.  OF-DPA reconciles with the OpenFlow protocol
         by encoding the group table into the group entry id.

         This YANG model does not need to reconcile directly with the OpenFlow
         protocol, so it explicitly models separate group tables in a similar fashion
         to the flow table definitions.

         The configuration model for group tables include a list of pre-created
         group tables, and a flat list of group table entries, where each entry is
         associated to a particular flow table by a reference.";
      list of-group-table {
        description
          "This is the list of OF-DPA-like Group Tables.  These are automatically
           created and configured by the switch, and should not be created by the
           controller. The group tables correspond to the Broadcom OF-DPA 2.0 tables.
           Only the table-description should be configured by the controller.

           The group table entries in this list do not contain the actual group table
           entries.  Those are in a separate list, with each flow entry pointing to
           the table which logically containers it.";
        key "name vfsi-id";
        leaf name {
          type of-types:live_ncs_name;
          description
            "This object indicates the identifier and is a text string that is
             used to identify a Group Table.
             Unique string values are chosen to uniquely identify the group-table.
             A Group Table can be considered to be a Forwarding Plane Table that
             is looked up in a Forwarding Plane Pipeline.";
        }
        leaf vfsi-id {
          type of-vfsi:live_ncs_vfsi-id-ref;
          description
            "An identifier of a Virtual Flow Switch Instance that this Group Table belongs to.
             This element should not be modified by the controller.";
        }
        leaf table-number {
          type of-types:live_ncs_table-number;
          description
            "An identifier of the Open Flow Group Table.";
        }
        leaf table-description {
          type string {
            length "1..127";
          }
          description
            "A more detailed description that an operator can use to describe the
             Group Table.";
        }
        leaf default-table {
          type empty;
          description
            "Table is a default Table. (e.g. autogenerated by a flowswitch)";
        }
      }
      list of-group-table-entry {
        description
          "This is the list of OpenFlow-like group table entries.  The controller
           creates and modifies these group table entries (along with the flow table
           entries) to directly control the switch forwarding plane.

           The group table entries are in a flat list, but they are logically
           associated with a specific group table by the group-table reference.";
        key "group-identifier vfsi-id";
        leaf group-identifier {
          type of-types:live_ncs_entry-id;
          description
            "An identifier to uniquely identify the group entry (unique across
             all group tables).";
        }
        leaf vfsi-id {
          type of-vfsi:live_ncs_vfsi-id-ref;
          description
            "An identifier of a Virtual Flow Switch Instance that this Flow Table belongs to.";
        }
        leaf group-table {
          type of-group-tables:live_ncs_group-table-ref;
          description
            "A reference to a Group Table.";
          // NCS drop mandatory statement
        }
        leaf entry-description {
          type string {
            length "1..127";
          }
          description
            "A more detailed description that an operator can use to describe the
             Group Table Entry.";
        }
        leaf group-type {
          type of-types:live_ncs_group-type;
          description
            "Identifies whether this is a select (ECMP) entry, an all (multicast/
             broadcast) entry, an indirect entry, or a fast failover entry.";
        }
        list action-buckets {
          description
            "The key to the group table entries are the action buckets.  The bucket
             semantics are specific to each group entry type.  Buckets are executed
             according to the OpenFlow specification semantics.  Another way to
             describe this is that packets are sent to one or more bucket when
             the packet is sent to a group table entry.

             The buckets each contain an action set which is applied to the packet.";
          key "bucket-id";
          leaf bucket-id {
            type of-types:live_ncs_entry-id;
            description
              "An identifier of the Bucket within an Open Flow Group Table.";
          }
          leaf weight {
            type of-types:live_ncs_weight;
          }
          container action-set {
            uses of-types:live_ncs_action-set;
            leaf group-id {
              type of-group-tables:live_ncs_group-table-entry-ref;
            }
          }
          leaf stats-collection {
            type of-types:live_ncs_stats-collection;
            description
              "Determines whether stats collection will be turned on or not for
               an action-bucket";
          }
        }
        leaf stats-collection {
          type of-types:live_ncs_stats-collection;
          description
            "Determines whether stats collection will be turned on or not for a
             group table entry";
        }
        leaf default-entry {
          type empty;
          description
            "Entry is a default Entry. (e.g. autogenerated by a flowswitch)";
        }
      }
    }
    container of-group-tables-state {
      tailf:ncs-device-type "netconf";
      tailf:display-when "not(../../ncs:module) or ../../ncs:module[ncs:name='ciena-of-group-tables'] or (../../ncs:live-status-protocol[not(ncs:capability)]) or (../../ncs:live-status-protocol/ncs:capability/ncs:module[.='ciena-of-group-tables'])";
      list of-group-table {
        key "name vfsi-id";
        leaf name {
          type of-types:live_ncs_name;
          description
            "Operational data for this Group Table.";
        }
        leaf vfsi-id {
          type of-types:live_ncs_vfsi-id;
          description
            "An identifier of a Virtual Flow Switch Instance that this Flow Table belongs to.";
        }
      }
      list of-group-table-entry {
        key "group-identifier vfsi-id";
        leaf group-identifier {
          type of-types:live_ncs_entry-id;
          description
            "An identifier of the Open Flow Group Table Entry within an Open Flow Group Table.";
        }
        leaf vfsi-id {
          type of-types:live_ncs_vfsi-id;
          description
            "An identifier of a Virtual Flow Switch Instance that this Flow Table belongs to.";
        }
        container statistics {
          uses of-types:live_ncs_of-group-statistics;
        }
        leaf group-entry-status {
          type of-types:live_ncs_entry-status;
          description
            "indicates the current status of the group entry relative to the actual
             hardware data plane.";
        }
        list action-buckets {
          key "bucket-id";
          leaf bucket-id {
            type of-types:live_ncs_entry-id;
            description
              "An identifier of the Bucket within an Open Flow Group Table.";
          }
          container statistics {
            uses of-types:live_ncs_of-bucket-statistics;
          }
        }
      }
    }
  }
  augment "/ncs:devices/ncs:template/ncs:ned-id/ncs:config" {
    container of-group-tables {
      description
        "Although the OpenFlow protocol calls for a single group table with all
         group table entries, the Broadcom OF-DPA describes models the pipeline
         with separate group tables.  OF-DPA reconciles with the OpenFlow protocol
         by encoding the group table into the group entry id.

         This YANG model does not need to reconcile directly with the OpenFlow
         protocol, so it explicitly models separate group tables in a similar fashion
         to the flow table definitions.

         The configuration model for group tables include a list of pre-created
         group tables, and a flat list of group table entries, where each entry is
         associated to a particular flow table by a reference.";
      list of-group-table {
        // NCS patched for predictable order
        ordered-by user;
        description
          "This is the list of OF-DPA-like Group Tables.  These are automatically
           created and configured by the switch, and should not be created by the
           controller. The group tables correspond to the Broadcom OF-DPA 2.0 tables.
           Only the table-description should be configured by the controller.

           The group table entries in this list do not contain the actual group table
           entries.  Those are in a separate list, with each flow entry pointing to
           the table which logically containers it.";
        key "name vfsi-id";
        leaf name {
          type of-types:ncs_template_name;
          description
            "This object indicates the identifier and is a text string that is
             used to identify a Group Table.
             Unique string values are chosen to uniquely identify the group-table.
             A Group Table can be considered to be a Forwarding Plane Table that
             is looked up in a Forwarding Plane Pipeline.";
        }
        leaf vfsi-id {
          type of-vfsi:ncs_template_vfsi-id-ref;
          description
            "An identifier of a Virtual Flow Switch Instance that this Group Table belongs to.
             This element should not be modified by the controller.";
        }
        leaf table-number {
          type of-types:ncs_template_table-number;
          description
            "An identifier of the Open Flow Group Table.";
        }
        leaf table-description {
          type string;
          description
            "A more detailed description that an operator can use to describe the
             Group Table.";
        }
        // NCS drop config false leaf 'default-table'
      }
      list of-group-table-entry {
        // NCS patched for predictable order
        ordered-by user;
        description
          "This is the list of OpenFlow-like group table entries.  The controller
           creates and modifies these group table entries (along with the flow table
           entries) to directly control the switch forwarding plane.

           The group table entries are in a flat list, but they are logically
           associated with a specific group table by the group-table reference.";
        key "group-identifier vfsi-id";
        leaf group-identifier {
          type of-types:ncs_template_entry-id;
          description
            "An identifier to uniquely identify the group entry (unique across
             all group tables).";
        }
        leaf vfsi-id {
          type of-vfsi:ncs_template_vfsi-id-ref;
          description
            "An identifier of a Virtual Flow Switch Instance that this Flow Table belongs to.";
        }
        leaf group-table {
          type of-group-tables:ncs_template_group-table-ref;
          description
            "A reference to a Group Table.";
          // NCS drop mandatory statement
        }
        leaf entry-description {
          type string;
          description
            "A more detailed description that an operator can use to describe the
             Group Table Entry.";
        }
        leaf group-type {
          type of-types:ncs_template_group-type;
          description
            "Identifies whether this is a select (ECMP) entry, an all (multicast/
             broadcast) entry, an indirect entry, or a fast failover entry.";
        }
        list action-buckets {
          // NCS patched for predictable order
          ordered-by user;
          description
            "The key to the group table entries are the action buckets.  The bucket
             semantics are specific to each group entry type.  Buckets are executed
             according to the OpenFlow specification semantics.  Another way to
             describe this is that packets are sent to one or more bucket when
             the packet is sent to a group table entry.

             The buckets each contain an action set which is applied to the packet.";
          key "bucket-id";
          leaf bucket-id {
            type of-types:ncs_template_entry-id;
            description
              "An identifier of the Bucket within an Open Flow Group Table.";
          }
          leaf weight {
            type of-types:ncs_template_weight;
          }
          container action-set {
            uses of-types:ncs_template_action-set;
            leaf group-id {
              type of-group-tables:ncs_template_group-table-entry-ref;
            }
          }
          leaf stats-collection {
            type of-types:ncs_template_stats-collection;
            description
              "Determines whether stats collection will be turned on or not for
               an action-bucket";
          }
        }
        leaf stats-collection {
          type of-types:ncs_template_stats-collection;
          description
            "Determines whether stats collection will be turned on or not for a
             group table entry";
        }
        // NCS drop config false leaf 'default-entry'
      }
    }
    // NCS drop config false container 'of-group-tables-state'
  }
}
