module ciena-ietf-alarms-deviation {
  // Generated by yanger -t ncs
  tailf:mount-id "saos1051-nc-1.0:saos1051-nc-1.0";
  tailf:ncs-device-type "netconf";

  yang-version 1.1;
  namespace "http://www.ciena.com/ns/yang/ciena-ietf-alarms-deviation";
  prefix ciena-alarms-dev;

  import ietf-alarms {
    prefix al;
  }
  import ciena-ietf-alarms {
    prefix ciena-al;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's augmentations to the draft-ietf-ccamp-alarm-module-01 model.

      Copyright (c) 2016 Ciena Corporation.  All rights
      reserved.

      All information contained herein is, and remains
      the property of Ciena Corporation. Dissemination of this
      information or reproduction of this material is strictly
      forbidden unless prior written permission is obtained from
      Ciena Corporation.";

  revision 2018-08-01 {
    description
      "Initial version";
    reference
      "RFC 6020: YANG - A Data Modeling Language for
       the Network Configuration Protocol (NETCONF).
       No specific reference; standard not available.";
  }

  deviation "/ncs:devices/ncs:template/ncs:ned-id/ncs:config/al:alarms/al:control/al:alarm-shelving/al:shelf/al:resource" {
    deviate replace {
      type string;
    }
  }
  deviation "/ncs:devices/ncs:device/ncs:live-status/al:alarms/al:control/al:alarm-shelving/al:shelf/al:resource" {
    deviate replace {
      type string;
    }
  }
  deviation "/ncs:devices/ncs:device/ncs:config/al:alarms/al:control/al:alarm-shelving/al:shelf/al:resource" {
    deviate replace {
      type string;
    }
  }
  deviation "/ncs:devices/ncs:template/ncs:ned-id/ncs:config/al:alarms/al:control/al:alarm-shelving/al:shelf/al:alarm-type-id" {
    deviate replace {
      type ciena-al:ncs_template_alarm-types;
    }
  }
  deviation "/ncs:devices/ncs:device/ncs:live-status/al:alarms/al:control/al:alarm-shelving/al:shelf/al:alarm-type-id" {
    deviate replace {
      type ciena-al:live_ncs_alarm-types;
    }
  }
  deviation "/ncs:devices/ncs:device/ncs:config/al:alarms/al:control/al:alarm-shelving/al:shelf/al:alarm-type-id" {
    deviate replace {
      type ciena-al:alarm-types;
    }
  }
  deviation "/ncs:devices/ncs:device/ncs:live-status/al:alarms/al:alarm-inventory/al:alarm-type/al:alarm-type-id" {
    deviate replace {
      type ciena-al:live_ncs_alarm-types;
    }
  }
  deviation "/ncs:devices/ncs:device/ncs:live-status/al:alarms/al:alarm-list/al:alarm/al:resource" {
    deviate replace {
      type string;
    }
  }
  deviation "/ncs:devices/ncs:device/ncs:live-status/al:alarms/al:alarm-list/al:alarm/al:alarm-type-id" {
    deviate replace {
      type ciena-al:live_ncs_alarm-types;
    }
  }
  deviation "/ncs:devices/ncs:device/ncs:live-status/al:alarms/al:shelved-alarms/al:shelved-alarm/al:resource" {
    deviate replace {
      type string;
    }
  }
  deviation "/ncs:devices/ncs:device/ncs:live-status/al:alarms/al:shelved-alarms/al:shelved-alarm/al:alarm-type-id" {
    deviate replace {
      type ciena-al:live_ncs_alarm-types;
    }
  }
  deviation "/ncs:devices/ncs:device/ncs:live-status/al:alarms/al:alarm-inventory/al:alarm-type/al:resource" {
    deviate not-supported;
  }
  deviation "/ncs:devices/ncs:device/ncs:live-status/al:alarms/al:alarm-inventory/al:alarm-type/al:severity-levels" {
    deviate not-supported;
  }
  deviation "/ncs:devices/ncs:device/ncs:live-status/al:alarms/al:summary/al:shelves-active" {
    deviate not-supported;
  }
  deviation "/ncs:devices/ncs:device/ncs:live-status/al:alarms/al:alarm-list/al:alarm/al:alt-resource" {
    deviate not-supported;
  }
  deviation "/ncs:devices/ncs:device/ncs:live-status/al:alarms/al:alarm-list/al:alarm/al:related-alarm" {
    deviate not-supported;
  }
  deviation "/ncs:devices/ncs:device/ncs:live-status/al:alarms/al:alarm-list/al:alarm/al:impacted-resource" {
    deviate not-supported;
  }
  deviation "/ncs:devices/ncs:device/ncs:live-status/al:alarms/al:alarm-list/al:alarm/al:root-cause-resource" {
    deviate not-supported;
  }
  deviation "/ncs:devices/ncs:device/ncs:live-status/al:alarms/al:alarm-list/al:alarm/al:set-operator-state" {
    deviate not-supported;
  }
  deviation "/ncs:devices/ncs:device/ncs:live-status/al:alarms/al:shelved-alarms/al:shelved-alarm/al:alt-resource" {
    deviate not-supported;
  }
  deviation "/ncs:devices/ncs:device/ncs:live-status/al:alarms/al:shelved-alarms/al:shelved-alarm/al:related-alarm" {
    deviate not-supported;
  }
  deviation "/ncs:devices/ncs:device/ncs:live-status/al:alarms/al:shelved-alarms/al:shelved-alarm/al:impacted-resource" {
    deviate not-supported;
  }
  deviation "/ncs:devices/ncs:device/ncs:live-status/al:alarms/al:shelved-alarms/al:shelved-alarm/al:root-cause-resource" {
    deviate not-supported;
  }
  deviation "/ncs:devices/ncs:device/ncs:netconf-notifications/ncs:received-notifications/ncs:notification/ncs:data/al:alarm-notification/al:alt-resource" {
    deviate not-supported;
  }
  deviation "/ncs:devices/ncs:device/ncs:netconf-notifications/ncs:received-notifications/ncs:notification/ncs:data/al:alarm-notification/al:related-alarm" {
    deviate not-supported;
  }
  deviation "/ncs:devices/ncs:device/ncs:netconf-notifications/ncs:received-notifications/ncs:notification/ncs:data/al:alarm-notification/al:impacted-resource" {
    deviate not-supported;
  }
  deviation "/ncs:devices/ncs:device/ncs:netconf-notifications/ncs:received-notifications/ncs:notification/ncs:data/al:alarm-notification/al:root-cause-resource" {
    deviate not-supported;
  }
  deviation "/ncs:devices/ncs:device/ncs:netconf-notifications/ncs:received-notifications/ncs:notification/ncs:data/al:alarm-notification/al:resource" {
    deviate replace {
      type string;
    }
  }
  deviation "/ncs:devices/ncs:device/ncs:netconf-notifications/ncs:received-notifications/ncs:notification/ncs:data/al:alarm-notification/al:alarm-type-id" {
    deviate replace {
      type ciena-al:ncs_rpc_notif_alarm-types;
    }
  }
  deviation "/ncs:devices/ncs:device/ncs:rpc/al:rpc-compress-alarms/al:compress-alarms/al:input/al:resource" {
    deviate replace {
      type string;
    }
  }
  deviation "/ncs:devices/ncs:device/ncs:rpc/al:rpc-compress-alarms/al:compress-alarms/al:input/al:alarm-type-id" {
    deviate replace {
      type ciena-al:ncs_rpc_notif_alarm-types;
    }
  }
  deviation "/ncs:devices/ncs:device/ncs:rpc/al:rpc-compress-alarms/al:compress-alarms/al:input/al:alarm-type-qualifier" {
    deviate replace {
      type string;
    }
  }
}
