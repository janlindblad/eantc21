module ciena-nat-deviation {
  // Generated by yanger -t ncs
  tailf:mount-id "saos1051-nc-1.0:saos1051-nc-1.0";
  tailf:ncs-device-type "netconf";

  namespace "http://www.ciena.com/ns/yang/ciena-nat-deviation";
  prefix cn-nat-deviation;

  import ciena-nat {
    prefix ciena-nat;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's Network Address Translations (NAT) deviations.";

  revision 2020-03-13 {
    description
      "Initial Version.";
    reference "IEEE Std 8512 .";
  }

  deviation "/ncs:devices/ncs:template/ncs:ned-id/ncs:config/ciena-nat:nat/ciena-nat:instances/ciena-nat:instance/ciena-nat:interface/ciena-nat:type" {
    deviate replace {
      type string;
    }
  }
  deviation "/ncs:devices/ncs:device/ncs:live-status/ciena-nat:nat/ciena-nat:instances/ciena-nat:instance/ciena-nat:interface/ciena-nat:type" {
    deviate replace {
      type enumeration {
        enum "external" {
          description
            "Identifies the realm of NAT interface as External.";
        }
      }
    }
  }
  deviation "/ncs:devices/ncs:device/ncs:config/ciena-nat:nat/ciena-nat:instances/ciena-nat:instance/ciena-nat:interface/ciena-nat:type" {
    deviate replace {
      type enumeration {
        enum "external" {
          description
            "Identifies the realm of NAT interface as External.";
        }
      }
    }
  }
  deviation "/ncs:devices/ncs:template/ncs:ned-id/ncs:config/ciena-nat:nat/ciena-nat:instances/ciena-nat:instance/ciena-nat:mapping-table/ciena-nat:mapping-entry/ciena-nat:internal-dst-port" {
    deviate not-supported;
  }
  deviation "/ncs:devices/ncs:device/ncs:live-status/ciena-nat:nat/ciena-nat:instances/ciena-nat:instance/ciena-nat:mapping-table/ciena-nat:mapping-entry/ciena-nat:internal-dst-port" {
    deviate not-supported;
  }
  deviation "/ncs:devices/ncs:device/ncs:config/ciena-nat:nat/ciena-nat:instances/ciena-nat:instance/ciena-nat:mapping-table/ciena-nat:mapping-entry/ciena-nat:internal-dst-port" {
    deviate not-supported;
  }
  deviation "/ncs:devices/ncs:template/ncs:ned-id/ncs:config/ciena-nat:nat/ciena-nat:instances/ciena-nat:instance/ciena-nat:mapping-table/ciena-nat:mapping-entry/ciena-nat:internal-dst-address" {
    deviate not-supported;
  }
  deviation "/ncs:devices/ncs:device/ncs:live-status/ciena-nat:nat/ciena-nat:instances/ciena-nat:instance/ciena-nat:mapping-table/ciena-nat:mapping-entry/ciena-nat:internal-dst-address" {
    deviate not-supported;
  }
  deviation "/ncs:devices/ncs:device/ncs:config/ciena-nat:nat/ciena-nat:instances/ciena-nat:instance/ciena-nat:mapping-table/ciena-nat:mapping-entry/ciena-nat:internal-dst-address" {
    deviate not-supported;
  }
  deviation "/ncs:devices/ncs:template/ncs:ned-id/ncs:config/ciena-nat:nat/ciena-nat:instances/ciena-nat:instance/ciena-nat:mapping-table/ciena-nat:mapping-entry/ciena-nat:external-dst-address" {
    deviate not-supported;
  }
  deviation "/ncs:devices/ncs:device/ncs:live-status/ciena-nat:nat/ciena-nat:instances/ciena-nat:instance/ciena-nat:mapping-table/ciena-nat:mapping-entry/ciena-nat:external-dst-address" {
    deviate not-supported;
  }
  deviation "/ncs:devices/ncs:device/ncs:config/ciena-nat:nat/ciena-nat:instances/ciena-nat:instance/ciena-nat:mapping-table/ciena-nat:mapping-entry/ciena-nat:external-dst-address" {
    deviate not-supported;
  }
  deviation "/ncs:devices/ncs:template/ncs:ned-id/ncs:config/ciena-nat:nat/ciena-nat:instances/ciena-nat:instance/ciena-nat:mapping-table/ciena-nat:mapping-entry/ciena-nat:external-dst-port" {
    deviate not-supported;
  }
  deviation "/ncs:devices/ncs:device/ncs:live-status/ciena-nat:nat/ciena-nat:instances/ciena-nat:instance/ciena-nat:mapping-table/ciena-nat:mapping-entry/ciena-nat:external-dst-port" {
    deviate not-supported;
  }
  deviation "/ncs:devices/ncs:device/ncs:config/ciena-nat:nat/ciena-nat:instances/ciena-nat:instance/ciena-nat:mapping-table/ciena-nat:mapping-entry/ciena-nat:external-dst-port" {
    deviate not-supported;
  }
  deviation "/ncs:devices/ncs:template/ncs:ned-id/ncs:config/ciena-nat:nat/ciena-nat:instances/ciena-nat:instance/ciena-nat:mapping-table/ciena-nat:mapping-entry/ciena-nat:lifetime" {
    deviate not-supported;
  }
  deviation "/ncs:devices/ncs:device/ncs:live-status/ciena-nat:nat/ciena-nat:instances/ciena-nat:instance/ciena-nat:mapping-table/ciena-nat:mapping-entry/ciena-nat:lifetime" {
    deviate not-supported;
  }
  deviation "/ncs:devices/ncs:device/ncs:config/ciena-nat:nat/ciena-nat:instances/ciena-nat:instance/ciena-nat:mapping-table/ciena-nat:mapping-entry/ciena-nat:lifetime" {
    deviate not-supported;
  }
  deviation "/ncs:devices/ncs:template/ncs:ned-id/ncs:config/ciena-nat:nat/ciena-nat:instances/ciena-nat:instance/ciena-nat:mapping-table/ciena-nat:mapping-entry/ciena-nat:internal-src-port/ciena-nat:end-port-number" {
    deviate not-supported;
  }
  deviation "/ncs:devices/ncs:device/ncs:live-status/ciena-nat:nat/ciena-nat:instances/ciena-nat:instance/ciena-nat:mapping-table/ciena-nat:mapping-entry/ciena-nat:internal-src-port/ciena-nat:end-port-number" {
    deviate not-supported;
  }
  deviation "/ncs:devices/ncs:device/ncs:config/ciena-nat:nat/ciena-nat:instances/ciena-nat:instance/ciena-nat:mapping-table/ciena-nat:mapping-entry/ciena-nat:internal-src-port/ciena-nat:end-port-number" {
    deviate not-supported;
  }
  deviation "/ncs:devices/ncs:template/ncs:ned-id/ncs:config/ciena-nat:nat/ciena-nat:instances/ciena-nat:instance/ciena-nat:mapping-table/ciena-nat:mapping-entry/ciena-nat:external-src-port/ciena-nat:end-port-number" {
    deviate not-supported;
  }
  deviation "/ncs:devices/ncs:device/ncs:live-status/ciena-nat:nat/ciena-nat:instances/ciena-nat:instance/ciena-nat:mapping-table/ciena-nat:mapping-entry/ciena-nat:external-src-port/ciena-nat:end-port-number" {
    deviate not-supported;
  }
  deviation "/ncs:devices/ncs:device/ncs:config/ciena-nat:nat/ciena-nat:instances/ciena-nat:instance/ciena-nat:mapping-table/ciena-nat:mapping-entry/ciena-nat:external-src-port/ciena-nat:end-port-number" {
    deviate not-supported;
  }
}
