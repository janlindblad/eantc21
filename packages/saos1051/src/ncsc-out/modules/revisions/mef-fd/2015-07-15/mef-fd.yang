module mef-fd {
  // Generated by yanger -t ncs
  tailf:mount-id "saos1051-nc-1.0:saos1051-nc-1.0";
  tailf:ncs-device-type "netconf";

  namespace "http://metroethernetforum.org/ns/yang/mef-fd";
  prefix mef-fd;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's configuration of
     the Forwarding Domain (Bridge Domain, Virtual Switch,
     VPLS representation for the NETCONF protocol).";

  revision 2015-07-15 {
    description
      "Initial version";
  }

  augment "/ncs:devices/ncs:device/ncs:config" {
    container fds {
      tailf:ncs-device-type "netconf";
      tailf:display-when "not(../../ncs:module) or ../../ncs:module[ncs:name='mef-fd']";
      list fd {
        key "mode name";
        description
          "The list of configured forwarding domains on the device.

           The operational state of a forwarding domain is available
           in the /fds-state/fd list.";
        leaf name {
          type string {
            length "1..1024";
          }
          description
            "An administratively assigned string, which may be used
             to identify the forwarding domain.";
        }
        leaf label {
          type string;
        }
        leaf description {
          type string;
          description
            "This is string used to describe the Forwarding Domain.";
        }
        leaf mode {
          type enumeration {
            enum "vlan";
            enum "vpls";
            enum "vpws";
          }
        }
        leaf vlan-id {
          type uint16 {
            range "1..4094";
          }
          mandatory true;
          when "../mode='vlan'" {
            tailf:xpath-root 3;
          }
        }
        leaf mac-learning {
          type enumeration {
            enum "enabled";
            enum "disabled";
          }
        }
        leaf ce-vlan-id-preservation {
          type boolean;
          description
            "Preserve the customer VLAN id as it traverses across
             the network.";
        }
        leaf ce-vlan-cos-preservation {
          type boolean;
          description
            "Preserve the customer VLAN CoS as it traverses the
             network..";
        }
        leaf l2cp-profile {
          type string;
          description
            "Reference to a Layer 2 Control Protocol Tunneling
             Profile. Should be changed to a leafref when l2cp-profile
             is defined.";
        }
        leaf private-forwarding-profile {
          type string;
          description
            "Reference to Private Forwarding Profile.";
        }
        leaf type {
          type identityref {
            base fd-type;
          }
          mandatory true;
          description
            "The type of forwarding domain.

             When a forwarding domain entry is created, a server MAY
             initialize the type leaf with a valid value, e.g. if it
             is possible to derive the type from the name of the
             forwarding domain.

             If a client tries to set the type of a forwarding domain to a
             value that can never be used by the system, e.g., if the
             type is not supported or if the type does not match the
             name of the forwarding domain, the server MUST reject the request.
             A NETCONF server MUST reply with an rpc-error with the
             error-tag 'invalid-value' in this case.";
        }
        leaf flood-containment-profile {
          type string;
          description
            "Reference to a Flood Containment Profile definition.";
        }
      }
    }
  }
  augment "/ncs:devices/ncs:device/ncs:live-status" {
    container fds {
      tailf:ncs-device-type "netconf";
      tailf:display-when "not(../../ncs:module) or ../../ncs:module[ncs:name='mef-fd'] or (../../ncs:live-status-protocol[not(ncs:capability)]) or (../../ncs:live-status-protocol/ncs:capability/ncs:module[.='mef-fd'])";
      list fd {
        key "mode name";
        description
          "The list of configured forwarding domains on the device.

           The operational state of a forwarding domain is available
           in the /fds-state/fd list.";
        leaf name {
          type string {
            length "1..1024";
          }
          description
            "An administratively assigned string, which may be used
             to identify the forwarding domain.";
        }
        leaf label {
          type string;
        }
        leaf description {
          type string;
          description
            "This is string used to describe the Forwarding Domain.";
        }
        leaf mode {
          type enumeration {
            enum "vlan";
            enum "vpls";
            enum "vpws";
          }
        }
        leaf vlan-id {
          type uint16 {
            range "1..4094";
          }
          // NCS drop mandatory statement
          // NCS drop when statement
        }
        leaf mac-learning {
          type enumeration {
            enum "enabled";
            enum "disabled";
          }
        }
        leaf ce-vlan-id-preservation {
          type boolean;
          description
            "Preserve the customer VLAN id as it traverses across
             the network.";
        }
        leaf ce-vlan-cos-preservation {
          type boolean;
          description
            "Preserve the customer VLAN CoS as it traverses the
             network..";
        }
        leaf l2cp-profile {
          type string;
          description
            "Reference to a Layer 2 Control Protocol Tunneling
             Profile. Should be changed to a leafref when l2cp-profile
             is defined.";
        }
        leaf private-forwarding-profile {
          type string;
          description
            "Reference to Private Forwarding Profile.";
        }
        leaf type {
          type identityref {
            base fd-type;
          }
          // NCS drop mandatory statement
          description
            "The type of forwarding domain.

             When a forwarding domain entry is created, a server MAY
             initialize the type leaf with a valid value, e.g. if it
             is possible to derive the type from the name of the
             forwarding domain.

             If a client tries to set the type of a forwarding domain to a
             value that can never be used by the system, e.g., if the
             type is not supported or if the type does not match the
             name of the forwarding domain, the server MUST reject the request.
             A NETCONF server MUST reply with an rpc-error with the
             error-tag 'invalid-value' in this case.";
        }
        leaf flood-containment-profile {
          type string;
          description
            "Reference to a Flood Containment Profile definition.";
        }
      }
    }
  }
  augment "/ncs:devices/ncs:template/ncs:ned-id/ncs:config" {
    container fds {
      list fd {
        // NCS patched for predictable order
        ordered-by user;
        key "mode name";
        description
          "The list of configured forwarding domains on the device.

           The operational state of a forwarding domain is available
           in the /fds-state/fd list.";
        leaf name {
          type string;
          description
            "An administratively assigned string, which may be used
             to identify the forwarding domain.";
        }
        leaf label {
          type string;
        }
        leaf description {
          type string;
          description
            "This is string used to describe the Forwarding Domain.";
        }
        leaf mode {
          type string;
        }
        leaf vlan-id {
          type string;
          // NCS drop mandatory statement
          // NCS drop when statement
        }
        leaf mac-learning {
          type string;
        }
        leaf ce-vlan-id-preservation {
          type string;
          description
            "Preserve the customer VLAN id as it traverses across
             the network.";
        }
        leaf ce-vlan-cos-preservation {
          type string;
          description
            "Preserve the customer VLAN CoS as it traverses the
             network..";
        }
        leaf l2cp-profile {
          type string;
          description
            "Reference to a Layer 2 Control Protocol Tunneling
             Profile. Should be changed to a leafref when l2cp-profile
             is defined.";
        }
        leaf private-forwarding-profile {
          type string;
          description
            "Reference to Private Forwarding Profile.";
        }
        leaf type {
          type string;
          // NCS drop mandatory statement
          description
            "The type of forwarding domain.

             When a forwarding domain entry is created, a server MAY
             initialize the type leaf with a valid value, e.g. if it
             is possible to derive the type from the name of the
             forwarding domain.

             If a client tries to set the type of a forwarding domain to a
             value that can never be used by the system, e.g., if the
             type is not supported or if the type does not match the
             name of the forwarding domain, the server MUST reject the request.
             A NETCONF server MUST reply with an rpc-error with the
             error-tag 'invalid-value' in this case.";
        }
        leaf flood-containment-profile {
          type string;
          description
            "Reference to a Flood Containment Profile definition.";
        }
      }
    }
  }

  identity fd-type {
    description
      "Base identity from which specific forwarding domain types are
       derived.";
  }
}
