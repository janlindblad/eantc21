module ciena-evpn-deviation {
  // Generated by yanger -t ncs
  tailf:mount-id "saos1051-nc-1.0:saos1051-nc-1.0";
  tailf:ncs-device-type "netconf";

  namespace "http://ciena.com/ns/yang/ciena-evpn-deviation";
  prefix cn-evpn-deviation;

  import ciena-evpn {
    prefix cnevpn;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This module contains the Ciena proprietary YANG deviations
     of the standard ethernet-segment YANG module.
     Copyright (c) 2019 Ciena Corporation.  All rights reserved.

     All information contained herein is, and remains
     the property of Ciena Corporation. Dissemination of this
     information or reproduction of this material is strictly
     forbidden unless prior written permission is obtained from
     Ciena Corporation.";

  revision 2020-03-25 {
    description
      "Initial version";
  }

  deviation "/ncs:devices/ncs:template/ncs:ned-id/ncs:config/cnevpn:evpn/cnevpn:global-route-distinguisher" {
    deviate not-supported;
  }
  deviation "/ncs:devices/ncs:device/ncs:live-status/cnevpn:evpn/cnevpn:global-route-distinguisher" {
    deviate not-supported;
  }
  deviation "/ncs:devices/ncs:device/ncs:config/cnevpn:evpn/cnevpn:global-route-distinguisher" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-0/cnevpn:arbitrary" {
    deviate not-supported;
  }
  deviation "/ncs:devices/ncs:device/ncs:live-status/cnevpn:evpn/cnevpn:ethernet-segments/cnevpn:ethernet-segment/cnevpn:ethernet-segment-identifier/cnevpn:esi-type/cnevpn:type-0/cnevpn:arbitrary" {
    deviate not-supported;
  }
  deviation "/ncs:devices/ncs:device/ncs:config/cnevpn:evpn/cnevpn:ethernet-segments/cnevpn:ethernet-segment/cnevpn:ethernet-segment-identifier/cnevpn:esi-type/cnevpn:type-0/cnevpn:arbitrary" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-0" {
    deviate not-supported;
  }
  deviation "/ncs:devices/ncs:device/ncs:live-status/cnevpn:evpn/cnevpn:ethernet-segments/cnevpn:ethernet-segment/cnevpn:ethernet-segment-identifier/cnevpn:esi-type/cnevpn:type-0" {
    deviate not-supported;
  }
  deviation "/ncs:devices/ncs:device/ncs:config/cnevpn:evpn/cnevpn:ethernet-segments/cnevpn:ethernet-segment/cnevpn:ethernet-segment-identifier/cnevpn:esi-type/cnevpn:type-0" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-1/cnevpn:lacp-based" {
    deviate not-supported;
  }
  deviation "/ncs:devices/ncs:device/ncs:live-status/cnevpn:evpn/cnevpn:ethernet-segments/cnevpn:ethernet-segment/cnevpn:ethernet-segment-identifier/cnevpn:esi-type/cnevpn:type-1/cnevpn:lacp-based" {
    deviate not-supported;
  }
  deviation "/ncs:devices/ncs:device/ncs:config/cnevpn:evpn/cnevpn:ethernet-segments/cnevpn:ethernet-segment/cnevpn:ethernet-segment-identifier/cnevpn:esi-type/cnevpn:type-1/cnevpn:lacp-based" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-1" {
    deviate not-supported;
  }
  deviation "/ncs:devices/ncs:device/ncs:live-status/cnevpn:evpn/cnevpn:ethernet-segments/cnevpn:ethernet-segment/cnevpn:ethernet-segment-identifier/cnevpn:esi-type/cnevpn:type-1" {
    deviate not-supported;
  }
  deviation "/ncs:devices/ncs:device/ncs:config/cnevpn:evpn/cnevpn:ethernet-segments/cnevpn:ethernet-segment/cnevpn:ethernet-segment-identifier/cnevpn:esi-type/cnevpn:type-1" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-2/cnevpn:lan-based" {
    deviate not-supported;
  }
  deviation "/ncs:devices/ncs:device/ncs:live-status/cnevpn:evpn/cnevpn:ethernet-segments/cnevpn:ethernet-segment/cnevpn:ethernet-segment-identifier/cnevpn:esi-type/cnevpn:type-2/cnevpn:lan-based" {
    deviate not-supported;
  }
  deviation "/ncs:devices/ncs:device/ncs:config/cnevpn:evpn/cnevpn:ethernet-segments/cnevpn:ethernet-segment/cnevpn:ethernet-segment-identifier/cnevpn:esi-type/cnevpn:type-2/cnevpn:lan-based" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-2" {
    deviate not-supported;
  }
  deviation "/ncs:devices/ncs:device/ncs:live-status/cnevpn:evpn/cnevpn:ethernet-segments/cnevpn:ethernet-segment/cnevpn:ethernet-segment-identifier/cnevpn:esi-type/cnevpn:type-2" {
    deviate not-supported;
  }
  deviation "/ncs:devices/ncs:device/ncs:config/cnevpn:evpn/cnevpn:ethernet-segments/cnevpn:ethernet-segment/cnevpn:ethernet-segment-identifier/cnevpn:esi-type/cnevpn:type-2" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-3/cnevpn:mac-based/cnevpn:auto-derived" {
    deviate not-supported;
  }
  deviation "/ncs:devices/ncs:device/ncs:live-status/cnevpn:evpn/cnevpn:ethernet-segments/cnevpn:ethernet-segment/cnevpn:ethernet-segment-identifier/cnevpn:esi-type/cnevpn:type-3/cnevpn:mac-based/cnevpn:auto-derived" {
    deviate not-supported;
  }
  deviation "/ncs:devices/ncs:device/ncs:config/cnevpn:evpn/cnevpn:ethernet-segments/cnevpn:ethernet-segment/cnevpn:ethernet-segment-identifier/cnevpn:esi-type/cnevpn:type-3/cnevpn:mac-based/cnevpn:auto-derived" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-3/cnevpn:mac-based/cnevpn:local-discriminator" {
    deviate not-supported;
  }
  deviation "/ncs:devices/ncs:device/ncs:live-status/cnevpn:evpn/cnevpn:ethernet-segments/cnevpn:ethernet-segment/cnevpn:ethernet-segment-identifier/cnevpn:esi-type/cnevpn:type-3/cnevpn:mac-based/cnevpn:local-discriminator" {
    deviate not-supported;
  }
  deviation "/ncs:devices/ncs:device/ncs:config/cnevpn:evpn/cnevpn:ethernet-segments/cnevpn:ethernet-segment/cnevpn:ethernet-segment-identifier/cnevpn:esi-type/cnevpn:type-3/cnevpn:mac-based/cnevpn:local-discriminator" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-4/cnevpn:router-id-based" {
    deviate not-supported;
  }
  deviation "/ncs:devices/ncs:device/ncs:live-status/cnevpn:evpn/cnevpn:ethernet-segments/cnevpn:ethernet-segment/cnevpn:ethernet-segment-identifier/cnevpn:esi-type/cnevpn:type-4/cnevpn:router-id-based" {
    deviate not-supported;
  }
  deviation "/ncs:devices/ncs:device/ncs:config/cnevpn:evpn/cnevpn:ethernet-segments/cnevpn:ethernet-segment/cnevpn:ethernet-segment-identifier/cnevpn:esi-type/cnevpn:type-4/cnevpn:router-id-based" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-4" {
    deviate not-supported;
  }
  deviation "/ncs:devices/ncs:device/ncs:live-status/cnevpn:evpn/cnevpn:ethernet-segments/cnevpn:ethernet-segment/cnevpn:ethernet-segment-identifier/cnevpn:esi-type/cnevpn:type-4" {
    deviate not-supported;
  }
  deviation "/ncs:devices/ncs:device/ncs:config/cnevpn:evpn/cnevpn:ethernet-segments/cnevpn:ethernet-segment/cnevpn:ethernet-segment-identifier/cnevpn:esi-type/cnevpn:type-4" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-5/cnevpn:as-based" {
    deviate not-supported;
  }
  deviation "/ncs:devices/ncs:device/ncs:live-status/cnevpn:evpn/cnevpn:ethernet-segments/cnevpn:ethernet-segment/cnevpn:ethernet-segment-identifier/cnevpn:esi-type/cnevpn:type-5/cnevpn:as-based" {
    deviate not-supported;
  }
  deviation "/ncs:devices/ncs:device/ncs:config/cnevpn:evpn/cnevpn:ethernet-segments/cnevpn:ethernet-segment/cnevpn:ethernet-segment-identifier/cnevpn:esi-type/cnevpn:type-5/cnevpn:as-based" {
    deviate not-supported;
  }
  deviation "/ncs:devices/ncs:template/ncs:ned-id/ncs:config/cnevpn:evpn/cnevpn:ethernet-segments/cnevpn:ethernet-segment/cnevpn:ethernet-segment-identifier/cnevpn:esi-type/cnevpn:type-5" {
    deviate not-supported;
  }
  deviation "/ncs:devices/ncs:device/ncs:live-status/cnevpn:evpn/cnevpn:ethernet-segments/cnevpn:ethernet-segment/cnevpn:ethernet-segment-identifier/cnevpn:esi-type/cnevpn:type-5" {
    deviate not-supported;
  }
  deviation "/ncs:devices/ncs:device/ncs:config/cnevpn:evpn/cnevpn:ethernet-segments/cnevpn:ethernet-segment/cnevpn:ethernet-segment-identifier/cnevpn:esi-type/cnevpn:type-5" {
    deviate not-supported;
  }
  deviation "/ncs:devices/ncs:template/ncs:ned-id/ncs:config/cnevpn:evpn/cnevpn:ethernet-segments/cnevpn:ethernet-segment/cnevpn:df-election/cnevpn:select-high-preference" {
    deviate not-supported;
  }
  deviation "/ncs:devices/ncs:device/ncs:live-status/cnevpn:evpn/cnevpn:ethernet-segments/cnevpn:ethernet-segment/cnevpn:df-election/cnevpn:select-high-preference" {
    deviate not-supported;
  }
  deviation "/ncs:devices/ncs:device/ncs:config/cnevpn:evpn/cnevpn:ethernet-segments/cnevpn:ethernet-segment/cnevpn:df-election/cnevpn:select-high-preference" {
    deviate not-supported;
  }
  deviation "/ncs:devices/ncs:template/ncs:ned-id/ncs:config/cnevpn:evpn/cnevpn:ethernet-segments/cnevpn:ethernet-segment/cnevpn:es-import" {
    deviate not-supported;
  }
  deviation "/ncs:devices/ncs:device/ncs:live-status/cnevpn:evpn/cnevpn:ethernet-segments/cnevpn:ethernet-segment/cnevpn:es-import" {
    deviate not-supported;
  }
  deviation "/ncs:devices/ncs:device/ncs:config/cnevpn:evpn/cnevpn:ethernet-segments/cnevpn:ethernet-segment/cnevpn:es-import" {
    deviate not-supported;
  }
  deviation "/ncs:devices/ncs:template/ncs:ned-id/ncs:config/cnevpn:evpn/cnevpn:evpn-instances/cnevpn:evpn-instance/cnevpn:services/cnevpn:flexible-cross-connect-vlan-aware-fd/cnevpn:flexible-cross-connect-vlan-aware-fd/cnevpn:stats-collection" {
    deviate not-supported;
  }
  deviation "/ncs:devices/ncs:device/ncs:live-status/cnevpn:evpn/cnevpn:evpn-instances/cnevpn:evpn-instance/cnevpn:services/cnevpn:flexible-cross-connect-vlan-aware-fd/cnevpn:flexible-cross-connect-vlan-aware-fd/cnevpn:stats-collection" {
    deviate not-supported;
  }
  deviation "/ncs:devices/ncs:device/ncs:config/cnevpn:evpn/cnevpn:evpn-instances/cnevpn:evpn-instance/cnevpn:services/cnevpn:flexible-cross-connect-vlan-aware-fd/cnevpn:flexible-cross-connect-vlan-aware-fd/cnevpn:stats-collection" {
    deviate not-supported;
  }
  deviation "/ncs:devices/ncs:template/ncs:ned-id/ncs:config/cnevpn:evpn/cnevpn:evpn-instances/cnevpn:evpn-instance/cnevpn:services/cnevpn:point-to-point/cnevpn:flexible-cross-connect-vlan-unaware-fd" {
    deviate not-supported;
  }
  deviation "/ncs:devices/ncs:device/ncs:live-status/cnevpn:evpn/cnevpn:evpn-instances/cnevpn:evpn-instance/cnevpn:services/cnevpn:point-to-point/cnevpn:flexible-cross-connect-vlan-unaware-fd" {
    deviate not-supported;
  }
  deviation "/ncs:devices/ncs:device/ncs:config/cnevpn:evpn/cnevpn:evpn-instances/cnevpn:evpn-instance/cnevpn:services/cnevpn:point-to-point/cnevpn:flexible-cross-connect-vlan-unaware-fd" {
    deviate not-supported;
  }
  deviation "/ncs:devices/ncs:template/ncs:ned-id/ncs:config/cnevpn:evpn/cnevpn:evpn-instances/cnevpn:evpn-instance/cnevpn:services/cnevpn:point-to-point/cnevpn:vpws-cross-connect-fd/cnevpn:stats-collection" {
    deviate not-supported;
  }
  deviation "/ncs:devices/ncs:device/ncs:live-status/cnevpn:evpn/cnevpn:evpn-instances/cnevpn:evpn-instance/cnevpn:services/cnevpn:point-to-point/cnevpn:vpws-cross-connect-fd/cnevpn:stats-collection" {
    deviate not-supported;
  }
  deviation "/ncs:devices/ncs:device/ncs:config/cnevpn:evpn/cnevpn:evpn-instances/cnevpn:evpn-instance/cnevpn:services/cnevpn:point-to-point/cnevpn:vpws-cross-connect-fd/cnevpn:stats-collection" {
    deviate not-supported;
  }
  deviation "/ncs:devices/ncs:template/ncs:ned-id/ncs:config/cnevpn:evpn/cnevpn:evpn-instances/cnevpn:evpn-instance/cnevpn:services/cnevpn:vpls-fd/cnevpn:vpls-fd" {
    deviate not-supported;
  }
  deviation "/ncs:devices/ncs:device/ncs:live-status/cnevpn:evpn/cnevpn:evpn-instances/cnevpn:evpn-instance/cnevpn:services/cnevpn:vpls-fd/cnevpn:vpls-fd" {
    deviate not-supported;
  }
  deviation "/ncs:devices/ncs:device/ncs:config/cnevpn:evpn/cnevpn:evpn-instances/cnevpn:evpn-instance/cnevpn:services/cnevpn:vpls-fd/cnevpn:vpls-fd" {
    deviate not-supported;
  }
  deviation "/ncs:devices/ncs:template/ncs:ned-id/ncs:config/cnevpn:evpn/cnevpn:evpn-instances/cnevpn:evpn-instance/cnevpn:services/cnevpn:vpls-fd" {
    deviate not-supported;
  }
  deviation "/ncs:devices/ncs:device/ncs:live-status/cnevpn:evpn/cnevpn:evpn-instances/cnevpn:evpn-instance/cnevpn:services/cnevpn:vpls-fd" {
    deviate not-supported;
  }
  deviation "/ncs:devices/ncs:device/ncs:config/cnevpn:evpn/cnevpn:evpn-instances/cnevpn:evpn-instance/cnevpn:services/cnevpn:vpls-fd" {
    deviate not-supported;
  }
  deviation "/ncs:devices/ncs:template/ncs:ned-id/ncs:config/cnevpn:evpn/cnevpn:evpn-instances/cnevpn:evpn-instance/cnevpn:route-distinguisher/cnevpn:rd-type/cnevpn:type-0/cnevpn:asn-2-octet-based" {
    deviate not-supported;
  }
  deviation "/ncs:devices/ncs:device/ncs:live-status/cnevpn:evpn/cnevpn:evpn-instances/cnevpn:evpn-instance/cnevpn:route-distinguisher/cnevpn:rd-type/cnevpn:type-0/cnevpn:asn-2-octet-based" {
    deviate not-supported;
  }
  deviation "/ncs:devices/ncs:device/ncs:config/cnevpn:evpn/cnevpn:evpn-instances/cnevpn:evpn-instance/cnevpn:route-distinguisher/cnevpn:rd-type/cnevpn:type-0/cnevpn:asn-2-octet-based" {
    deviate not-supported;
  }
  deviation "/ncs:devices/ncs:template/ncs:ned-id/ncs:config/cnevpn:evpn/cnevpn:evpn-instances/cnevpn:evpn-instance/cnevpn:route-distinguisher/cnevpn:rd-type/cnevpn:type-0" {
    deviate not-supported;
  }
  deviation "/ncs:devices/ncs:device/ncs:live-status/cnevpn:evpn/cnevpn:evpn-instances/cnevpn:evpn-instance/cnevpn:route-distinguisher/cnevpn:rd-type/cnevpn:type-0" {
    deviate not-supported;
  }
  deviation "/ncs:devices/ncs:device/ncs:config/cnevpn:evpn/cnevpn:evpn-instances/cnevpn:evpn-instance/cnevpn:route-distinguisher/cnevpn:rd-type/cnevpn:type-0" {
    deviate not-supported;
  }
  deviation "/ncs:devices/ncs:template/ncs:ned-id/ncs:config/cnevpn:evpn/cnevpn:evpn-instances/cnevpn:evpn-instance/cnevpn:route-distinguisher/cnevpn:rd-type/cnevpn:type-2/cnevpn:asn-4-octet-based" {
    deviate not-supported;
  }
  deviation "/ncs:devices/ncs:device/ncs:live-status/cnevpn:evpn/cnevpn:evpn-instances/cnevpn:evpn-instance/cnevpn:route-distinguisher/cnevpn:rd-type/cnevpn:type-2/cnevpn:asn-4-octet-based" {
    deviate not-supported;
  }
  deviation "/ncs:devices/ncs:device/ncs:config/cnevpn:evpn/cnevpn:evpn-instances/cnevpn:evpn-instance/cnevpn:route-distinguisher/cnevpn:rd-type/cnevpn:type-2/cnevpn:asn-4-octet-based" {
    deviate not-supported;
  }
  deviation "/ncs:devices/ncs:template/ncs:ned-id/ncs:config/cnevpn:evpn/cnevpn:evpn-instances/cnevpn:evpn-instance/cnevpn:route-distinguisher/cnevpn:rd-type/cnevpn:type-2" {
    deviate not-supported;
  }
  deviation "/ncs:devices/ncs:device/ncs:live-status/cnevpn:evpn/cnevpn:evpn-instances/cnevpn:evpn-instance/cnevpn:route-distinguisher/cnevpn:rd-type/cnevpn:type-2" {
    deviate not-supported;
  }
  deviation "/ncs:devices/ncs:device/ncs:config/cnevpn:evpn/cnevpn:evpn-instances/cnevpn:evpn-instance/cnevpn:route-distinguisher/cnevpn:rd-type/cnevpn:type-2" {
    deviate not-supported;
  }
  deviation "/ncs:devices/ncs:device/ncs:live-status/cnevpn:evpn-state/cnevpn:evpn-instances/cnevpn:evpn-instance/cnevpn:cross-connect/cnevpn:ilm-database/cnevpn:mac-label" {
    deviate not-supported;
  }
  deviation "/ncs:devices/ncs:device/ncs:live-status/cnevpn:evpn-state/cnevpn:evpn-instances/cnevpn:evpn-instance/cnevpn:cross-connect/cnevpn:ilm-database/cnevpn:out-interface" {
    deviate not-supported;
  }
}
