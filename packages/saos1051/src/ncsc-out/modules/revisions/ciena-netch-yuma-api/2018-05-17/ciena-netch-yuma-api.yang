module ciena-netch-yuma-api {
  // Generated by yanger -t ncs
  tailf:mount-id "saos1051-nc-1.0:saos1051-nc-1.0";
  tailf:ncs-device-type "netconf";

  namespace "urn:ciena:params:xml:ns:yang:ciena-pn:ciena-netch-yuma-api";
  prefix netchyumaapi;

  import yuma-ncx {
    prefix ncx;
  }
  import yumaworks-ycontrol {
    prefix yctl;
  }
  import tailf-common {
    prefix tailf;
  }
  import tailf-ncs {
    prefix ncs;
  }

  organization
    "Ciena";
  description
    "This yang model defines Ciena defined netch-yuma-api service over Ycontrol";

  revision 2018-05-17 {
    description
      "Add authorization-request";
  }
  revision 2016-05-02 {
    description
      "Add load-bundle-request";
  }
  revision 2015-07-06 {
    description
      "Initial version";
  }

  augment "/ncs:devices/ncs:template/ncs:ned-id/ncs:config/yctl:ycontrol/yctl:message-payload/yctl:payload/yctl:payload" {
    container netch-yuma-api {
      choice message-type {
        leaf register-request {
          type empty;
          description
            "Message type: subsys-request;
             Purpose: register the NETCH-YUMA-API subsystem
             Expected Response Message: ok or error";
        }
        container edit-request {
          description
            "Message type: subsys-request;
             Purpose: Ask the main server to accept an edit request
             Expected Response Message: ok or error";
          leaf log-level {
            type string;
            description
              "Message type: subsys-request;
               Purpose: Set the server log level
               Expected Response Message: ok or error";
          }
          leaf allowed-user {
            type string;
            description
              "Message type: subsys-request;
               Purpose: Add user to yumapro server user database
               Expected Response Message: ok or error";
          }
          leaf load-bundle {
            type string;
            description
              "Message type: subsys-request;
               Purpose: Ask the yumapro server to load a bundle
               Expected Response Message: ok or error";
          }
        }
        container authorization-request {
          description
            "Message type: subsys-request;
             Purpose: Ask the main server to authorize
             path.
             Expected Response Message: authorization-response or
             error";
          leaf username {
            type string;
            description
              "The user that is being authorized.";
          }
          leaf path {
            type string;
            description
              "The xpath to the container or list that
               will checked.";
          }
        }
        container authorization-response {
          description
            "Message type: server-reply
             Purpose: Send back the nodes the user is authorized
             to access.
             Expected Response Message: none";
          leaf access-denied {
            type string;
            description
              "Is access-denied to the node.";
          }
          leaf-list access-denied-children {
            // NCS patched for predictable order
            ordered-by user;
            type string;
            description
              "The list of children nodes the user is not
               authorized to access.";
          }
        }
      }
    }
  }
  augment "/ncs:devices/ncs:device/ncs:live-status/yctl:ycontrol/yctl:message-payload/yctl:payload/yctl:payload" {
    container netch-yuma-api {
      tailf:ncs-device-type "netconf";
      tailf:display-when "not(../../../../../../ncs:module) or ../../../../../../ncs:module[ncs:name='ciena-netch-yuma-api'] or (../../../../../../ncs:live-status-protocol[not(ncs:capability)]) or (../../../../../../ncs:live-status-protocol/ncs:capability/ncs:module[.='ciena-netch-yuma-api'])";
      choice message-type {
        leaf register-request {
          type empty;
          description
            "Message type: subsys-request;
             Purpose: register the NETCH-YUMA-API subsystem
             Expected Response Message: ok or error";
        }
        container edit-request {
          description
            "Message type: subsys-request;
             Purpose: Ask the main server to accept an edit request
             Expected Response Message: ok or error";
          leaf log-level {
            type string;
            description
              "Message type: subsys-request;
               Purpose: Set the server log level
               Expected Response Message: ok or error";
          }
          leaf allowed-user {
            type string;
            description
              "Message type: subsys-request;
               Purpose: Add user to yumapro server user database
               Expected Response Message: ok or error";
          }
          leaf load-bundle {
            type string;
            description
              "Message type: subsys-request;
               Purpose: Ask the yumapro server to load a bundle
               Expected Response Message: ok or error";
          }
        }
        container authorization-request {
          description
            "Message type: subsys-request;
             Purpose: Ask the main server to authorize
             path.
             Expected Response Message: authorization-response or
             error";
          leaf username {
            type string;
            description
              "The user that is being authorized.";
          }
          leaf path {
            type string;
            description
              "The xpath to the container or list that
               will checked.";
          }
        }
        container authorization-response {
          description
            "Message type: server-reply
             Purpose: Send back the nodes the user is authorized
             to access.
             Expected Response Message: none";
          leaf access-denied {
            type boolean;
            description
              "Is access-denied to the node.";
          }
          leaf-list access-denied-children {
            type string;
            description
              "The list of children nodes the user is not
               authorized to access.";
          }
        }
      }
    }
  }
  augment "/ncs:devices/ncs:device/ncs:config/yctl:ycontrol/yctl:message-payload/yctl:payload/yctl:payload" {
    container netch-yuma-api {
      tailf:ncs-device-type "netconf";
      tailf:display-when "not(../../../../../../ncs:module) or ../../../../../../ncs:module[ncs:name='ciena-netch-yuma-api']";
      choice message-type {
        leaf register-request {
          type empty;
          description
            "Message type: subsys-request;
             Purpose: register the NETCH-YUMA-API subsystem
             Expected Response Message: ok or error";
        }
        container edit-request {
          description
            "Message type: subsys-request;
             Purpose: Ask the main server to accept an edit request
             Expected Response Message: ok or error";
          leaf log-level {
            type string;
            description
              "Message type: subsys-request;
               Purpose: Set the server log level
               Expected Response Message: ok or error";
          }
          leaf allowed-user {
            type string;
            description
              "Message type: subsys-request;
               Purpose: Add user to yumapro server user database
               Expected Response Message: ok or error";
          }
          leaf load-bundle {
            type string;
            description
              "Message type: subsys-request;
               Purpose: Ask the yumapro server to load a bundle
               Expected Response Message: ok or error";
          }
        }
        container authorization-request {
          description
            "Message type: subsys-request;
             Purpose: Ask the main server to authorize
             path.
             Expected Response Message: authorization-response or
             error";
          leaf username {
            type string;
            description
              "The user that is being authorized.";
          }
          leaf path {
            type string;
            description
              "The xpath to the container or list that
               will checked.";
          }
        }
        container authorization-response {
          description
            "Message type: server-reply
             Purpose: Send back the nodes the user is authorized
             to access.
             Expected Response Message: none";
          leaf access-denied {
            type boolean;
            description
              "Is access-denied to the node.";
          }
          leaf-list access-denied-children {
            type string;
            description
              "The list of children nodes the user is not
               authorized to access.";
          }
        }
      }
    }
  }
}
