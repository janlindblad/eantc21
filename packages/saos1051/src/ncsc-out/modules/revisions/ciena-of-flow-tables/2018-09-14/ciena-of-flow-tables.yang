module ciena-of-flow-tables {
  // Generated by yanger -t ncs
  tailf:mount-id "saos1051-nc-1.0:saos1051-nc-1.0";
  tailf:ncs-device-type "netconf";

  namespace "http://www.ciena.com/ns/yang/ciena-pn/ciena-of-flows-tables";
  prefix of-flow-tables;

  import ciena-of-types {
    prefix of-types;
  }
  import ciena-of-vfsi {
    prefix of-vfsi;
  }
  import ciena-of-group-tables {
    prefix of-group-tables;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's management data definition for the definition of
     Open Flow Flow Tables.";

  revision 2018-09-14 {
    description
      "Initial Version.";
  }

  typedef ncs_template_flow-table-ref {
    type string;
    description
      "This type is used by data models that need to reference
       configured flow tables.";
  }

  typedef ncs_template_flow-table-number-ref {
    type string;
    description
      "This type is used by data models that need to reference
       configured flow tables by table-number.";
  }

  typedef ncs_template_flow-table-entry-ref {
    type string;
    description
      "This type is used by data models that need to reference
       configured flow table entries.";
  }

  typedef ncs_rpc_notif_flow-table-ref {
    type string;
    description
      "This type is used by data models that need to reference
       configured flow tables.";
  }

  typedef ncs_rpc_notif_flow-table-number-ref {
    type string;
    description
      "This type is used by data models that need to reference
       configured flow tables by table-number.";
  }

  typedef ncs_rpc_notif_flow-table-entry-ref {
    type string;
    description
      "This type is used by data models that need to reference
       configured flow table entries.";
  }

  typedef live_ncs_flow-table-ref {
    type leafref {
      path "/ncs:devices/ncs:device/ncs:live-status/of-flow-tables:of-flow-tables/of-flow-tables:of-flow-table/of-flow-tables:name" {
        tailf:xpath-root 3;
      }
    }
    description
      "This type is used by data models that need to reference
       configured flow tables.";
  }

  typedef live_ncs_flow-table-number-ref {
    type leafref {
      path "/ncs:devices/ncs:device/ncs:live-status/of-flow-tables:of-flow-tables/of-flow-tables:of-flow-table/of-flow-tables:table-number" {
        tailf:xpath-root 3;
      }
    }
    description
      "This type is used by data models that need to reference
       configured flow tables by table-number.";
  }

  typedef live_ncs_flow-table-entry-ref {
    type leafref {
      path "/ncs:devices/ncs:device/ncs:live-status/of-flow-tables:of-flow-tables/of-flow-tables:of-flow-table-entry/of-flow-tables:entry-number" {
        tailf:xpath-root 3;
      }
    }
    description
      "This type is used by data models that need to reference
       configured flow table entries.";
  }

  typedef flow-table-ref {
    type leafref {
      path "/ncs:devices/ncs:device/ncs:config/of-flow-tables:of-flow-tables/of-flow-tables:of-flow-table/of-flow-tables:name" {
        tailf:xpath-root 3;
      }
    }
    description
      "This type is used by data models that need to reference
       configured flow tables.";
  }

  typedef flow-table-number-ref {
    type leafref {
      path "/ncs:devices/ncs:device/ncs:config/of-flow-tables:of-flow-tables/of-flow-tables:of-flow-table/of-flow-tables:table-number" {
        tailf:xpath-root 3;
      }
    }
    description
      "This type is used by data models that need to reference
       configured flow tables by table-number.";
  }

  typedef flow-table-entry-ref {
    type leafref {
      path "/ncs:devices/ncs:device/ncs:config/of-flow-tables:of-flow-tables/of-flow-tables:of-flow-table-entry/of-flow-tables:entry-number" {
        tailf:xpath-root 3;
      }
    }
    description
      "This type is used by data models that need to reference
       configured flow table entries.";
  }

  grouping ncs_template_of-match-fields {
    description
      "These are the match fields that can be used in the flow table entries.
       As in the OpenFlow protocol, packets progress through the pipeline of
       tables.  At each table, packets are associated with a particular flow based
       on the flow match criteria and the packet header and ingress port (as well
       as the priority of the flow entry).

       Each flow entry can have zero or more match criteria.  So all the leaf
       nodes below are optional.";
    leaf in-logical-port {
      type of-types:ncs_template_logical-port;
    }
    leaf in-physical-port {
      type of-types:ncs_template_physical-port;
    }
    leaf metadata {
      type of-types:ncs_template_metadata;
    }
    leaf source-mac {
      type of-types:ncs_template_mac;
    }
    leaf source-mac-mask {
      type of-types:ncs_template_mac-mask;
    }
    leaf destination-mac {
      type of-types:ncs_template_mac;
    }
    leaf destination-mac-mask {
      type of-types:ncs_template_mac-mask;
    }
    container vtag-stack {
      uses of-types:ncs_template_vtag-stack;
    }
    leaf dscp {
      type of-types:ncs_template_dscp;
    }
    leaf ecn {
      type of-types:ncs_template_ecn;
    }
    leaf ip-protocol {
      type of-types:ncs_template_ip-protocol;
    }
    leaf ip-source-prefix {
      type of-types:ncs_template_ip-address-prefix;
    }
    leaf ip-destination-prefix {
      type of-types:ncs_template_ip-address-prefix;
    }
    leaf l4-source-port {
      type of-types:ncs_template_l4-port;
    }
    leaf l4-destination-port {
      type of-types:ncs_template_l4-port;
    }
    leaf ethertype {
      type of-types:ncs_template_ethertype;
    }
    container mpls-label-stack {
      uses of-types:ncs_template_mpls-label-stack;
    }
    leaf icmpv4-type {
      type of-types:ncs_template_icmpv4-type;
    }
    leaf icmpv4-code {
      type of-types:ncs_template_icmpv4-code;
    }
    leaf icmpv6-type {
      type of-types:ncs_template_icmpv6-type;
    }
    leaf icmpv6-code {
      type of-types:ncs_template_icmpv6-code;
    }
    leaf arp-opcode {
      type of-types:ncs_template_arp-opcode;
    }
    leaf arp-source-ip-address {
      type of-types:ncs_template_ipv4-address;
    }
    leaf arp-target-ip-address {
      type of-types:ncs_template_ipv4-address;
    }
    leaf arp-source-mac-address {
      type of-types:ncs_template_mac;
    }
    leaf arp-target-mac-address {
      type of-types:ncs_template_mac;
    }
    leaf ipv6-flow-label {
      type of-types:ncs_template_ipv6-flow-label;
    }
    leaf ndp-target-ip-address {
      type of-types:ncs_template_ipv6-address;
    }
    leaf ipv6-extension-header {
      type of-types:ncs_template_ipv6-extension-header;
    }
    leaf ndp-source-mac-address {
      type of-types:ncs_template_mac;
    }
    leaf ndp-target-mac-address {
      type of-types:ncs_template_mac;
    }
    leaf tunnel-id {
      type of-types:ncs_template_tunnel-id;
    }
  }

  grouping ncs_template_of-instruction-set {
    description
      "These are the instructions that can be used in the flow table entries.
       As in the OpenFlow protocol, packets progress through the pipeline of
       tables.  At each table, packets are matched to a flow entry, and the
       instructions for that flow entry are applied to the packet.

       Each flow entry can have zero or instructions.  So all the leaf notes
       below are optional.  There can be at most one instruction of each type.";
    leaf goto-table {
      type of-flow-tables:ncs_template_flow-table-ref;
      description
        "Indicates the next table in the processing pipeline. The table must
         be a subsequent table based on the OF-DPA table definitions.";
    }
    container write-metadata {
      description
        "Each packet can have associated metadata as it traverses the pipeline.
         This instruction writes masked metadata to into the metadata field.";
      presence "Metadata Value";
      leaf metadata-value {
        type of-types:ncs_template_metadata;
        // NCS drop mandatory statement
      }
      leaf metadata_mask {
        type of-types:ncs_template_metadata;
      }
    }
    container write-actions {
      description
        "Merges the specified actions into the current action set associated
         with the packet.";
      uses of-types:ncs_template_action-set;
      leaf group-id {
        type of-group-tables:ncs_template_group-table-entry-ref;
      }
    }
    container apply-actions {
      description
        "Applies the specified actions to the packet immediately, without change
         to the action set associated with the packet.";
      uses of-types:ncs_template_action-set;
      leaf group-id {
        type of-group-tables:ncs_template_group-table-entry-ref;
      }
    }
    leaf clear-actions {
      description
        "Clears all actions in the action set associated with the packet.";
      type empty;
    }
  }

  grouping ncs_rpc_notif_of-match-fields {
    description
      "These are the match fields that can be used in the flow table entries.
       As in the OpenFlow protocol, packets progress through the pipeline of
       tables.  At each table, packets are associated with a particular flow based
       on the flow match criteria and the packet header and ingress port (as well
       as the priority of the flow entry).

       Each flow entry can have zero or more match criteria.  So all the leaf
       nodes below are optional.";
    leaf in-logical-port {
      type of-types:ncs_rpc_notif_logical-port;
    }
    leaf in-physical-port {
      type of-types:ncs_rpc_notif_physical-port;
    }
    leaf metadata {
      type of-types:ncs_rpc_notif_metadata;
    }
    leaf source-mac {
      type of-types:ncs_rpc_notif_mac;
    }
    leaf source-mac-mask {
      type of-types:ncs_rpc_notif_mac-mask;
    }
    leaf destination-mac {
      type of-types:ncs_rpc_notif_mac;
    }
    leaf destination-mac-mask {
      type of-types:ncs_rpc_notif_mac-mask;
    }
    container vtag-stack {
      uses of-types:ncs_rpc_notif_vtag-stack;
    }
    leaf dscp {
      type of-types:ncs_rpc_notif_dscp;
    }
    leaf ecn {
      type of-types:ncs_rpc_notif_ecn;
    }
    leaf ip-protocol {
      type of-types:ncs_rpc_notif_ip-protocol;
    }
    leaf ip-source-prefix {
      type of-types:ncs_rpc_notif_ip-address-prefix;
    }
    leaf ip-destination-prefix {
      type of-types:ncs_rpc_notif_ip-address-prefix;
    }
    leaf l4-source-port {
      type of-types:ncs_rpc_notif_l4-port;
    }
    leaf l4-destination-port {
      type of-types:ncs_rpc_notif_l4-port;
    }
    leaf ethertype {
      type of-types:ncs_rpc_notif_ethertype;
    }
    container mpls-label-stack {
      uses of-types:ncs_rpc_notif_mpls-label-stack;
    }
    leaf icmpv4-type {
      type of-types:ncs_rpc_notif_icmpv4-type;
    }
    leaf icmpv4-code {
      type of-types:ncs_rpc_notif_icmpv4-code;
    }
    leaf icmpv6-type {
      type of-types:ncs_rpc_notif_icmpv6-type;
    }
    leaf icmpv6-code {
      type of-types:ncs_rpc_notif_icmpv6-code;
    }
    leaf arp-opcode {
      type of-types:ncs_rpc_notif_arp-opcode;
    }
    leaf arp-source-ip-address {
      type of-types:ncs_rpc_notif_ipv4-address;
    }
    leaf arp-target-ip-address {
      type of-types:ncs_rpc_notif_ipv4-address;
    }
    leaf arp-source-mac-address {
      type of-types:ncs_rpc_notif_mac;
    }
    leaf arp-target-mac-address {
      type of-types:ncs_rpc_notif_mac;
    }
    leaf ipv6-flow-label {
      type of-types:ncs_rpc_notif_ipv6-flow-label;
    }
    leaf ndp-target-ip-address {
      type of-types:ncs_rpc_notif_ipv6-address;
    }
    leaf ipv6-extension-header {
      type of-types:ncs_rpc_notif_ipv6-extension-header;
    }
    leaf ndp-source-mac-address {
      type of-types:ncs_rpc_notif_mac;
    }
    leaf ndp-target-mac-address {
      type of-types:ncs_rpc_notif_mac;
    }
    leaf tunnel-id {
      type of-types:ncs_rpc_notif_tunnel-id;
    }
  }

  grouping ncs_rpc_notif_of-instruction-set {
    description
      "These are the instructions that can be used in the flow table entries.
       As in the OpenFlow protocol, packets progress through the pipeline of
       tables.  At each table, packets are matched to a flow entry, and the
       instructions for that flow entry are applied to the packet.

       Each flow entry can have zero or instructions.  So all the leaf notes
       below are optional.  There can be at most one instruction of each type.";
    leaf goto-table {
      type of-flow-tables:ncs_rpc_notif_flow-table-ref;
      description
        "Indicates the next table in the processing pipeline. The table must
         be a subsequent table based on the OF-DPA table definitions.";
    }
    container write-metadata {
      description
        "Each packet can have associated metadata as it traverses the pipeline.
         This instruction writes masked metadata to into the metadata field.";
      presence "Metadata Value";
      leaf metadata-value {
        type of-types:ncs_rpc_notif_metadata;
        mandatory true;
      }
      leaf metadata_mask {
        type of-types:ncs_rpc_notif_metadata;
      }
    }
    container write-actions {
      description
        "Merges the specified actions into the current action set associated
         with the packet.";
      uses of-types:ncs_rpc_notif_action-set;
      leaf group-id {
        type of-group-tables:ncs_rpc_notif_group-table-entry-ref;
      }
    }
    container apply-actions {
      description
        "Applies the specified actions to the packet immediately, without change
         to the action set associated with the packet.";
      uses of-types:ncs_rpc_notif_action-set;
      leaf group-id {
        type of-group-tables:ncs_rpc_notif_group-table-entry-ref;
      }
    }
    leaf clear-actions {
      description
        "Clears all actions in the action set associated with the packet.";
      type empty;
    }
  }

  grouping live_ncs_of-match-fields {
    description
      "These are the match fields that can be used in the flow table entries.
       As in the OpenFlow protocol, packets progress through the pipeline of
       tables.  At each table, packets are associated with a particular flow based
       on the flow match criteria and the packet header and ingress port (as well
       as the priority of the flow entry).

       Each flow entry can have zero or more match criteria.  So all the leaf
       nodes below are optional.";
    leaf in-logical-port {
      type of-types:live_ncs_logical-port;
    }
    leaf in-physical-port {
      type of-types:live_ncs_physical-port;
    }
    leaf metadata {
      type of-types:live_ncs_metadata;
    }
    leaf source-mac {
      type of-types:live_ncs_mac;
    }
    leaf source-mac-mask {
      type of-types:live_ncs_mac-mask;
    }
    leaf destination-mac {
      type of-types:live_ncs_mac;
    }
    leaf destination-mac-mask {
      type of-types:live_ncs_mac-mask;
    }
    container vtag-stack {
      uses of-types:live_ncs_vtag-stack;
    }
    leaf dscp {
      type of-types:live_ncs_dscp;
    }
    leaf ecn {
      type of-types:live_ncs_ecn;
    }
    leaf ip-protocol {
      type of-types:live_ncs_ip-protocol;
    }
    leaf ip-source-prefix {
      type of-types:live_ncs_ip-address-prefix;
    }
    leaf ip-destination-prefix {
      type of-types:live_ncs_ip-address-prefix;
    }
    leaf l4-source-port {
      type of-types:live_ncs_l4-port;
    }
    leaf l4-destination-port {
      type of-types:live_ncs_l4-port;
    }
    leaf ethertype {
      type of-types:live_ncs_ethertype;
    }
    container mpls-label-stack {
      uses of-types:live_ncs_mpls-label-stack;
    }
    leaf icmpv4-type {
      type of-types:live_ncs_icmpv4-type;
    }
    leaf icmpv4-code {
      type of-types:live_ncs_icmpv4-code;
    }
    leaf icmpv6-type {
      type of-types:live_ncs_icmpv6-type;
    }
    leaf icmpv6-code {
      type of-types:live_ncs_icmpv6-code;
    }
    leaf arp-opcode {
      type of-types:live_ncs_arp-opcode;
    }
    leaf arp-source-ip-address {
      type of-types:live_ncs_ipv4-address;
    }
    leaf arp-target-ip-address {
      type of-types:live_ncs_ipv4-address;
    }
    leaf arp-source-mac-address {
      type of-types:live_ncs_mac;
    }
    leaf arp-target-mac-address {
      type of-types:live_ncs_mac;
    }
    leaf ipv6-flow-label {
      type of-types:live_ncs_ipv6-flow-label;
    }
    leaf ndp-target-ip-address {
      type of-types:live_ncs_ipv6-address;
    }
    leaf ipv6-extension-header {
      type of-types:live_ncs_ipv6-extension-header;
    }
    leaf ndp-source-mac-address {
      type of-types:live_ncs_mac;
    }
    leaf ndp-target-mac-address {
      type of-types:live_ncs_mac;
    }
    leaf tunnel-id {
      type of-types:live_ncs_tunnel-id;
    }
  }

  grouping live_ncs_of-instruction-set {
    description
      "These are the instructions that can be used in the flow table entries.
       As in the OpenFlow protocol, packets progress through the pipeline of
       tables.  At each table, packets are matched to a flow entry, and the
       instructions for that flow entry are applied to the packet.

       Each flow entry can have zero or instructions.  So all the leaf notes
       below are optional.  There can be at most one instruction of each type.";
    leaf goto-table {
      type of-flow-tables:live_ncs_flow-table-ref;
      description
        "Indicates the next table in the processing pipeline. The table must
         be a subsequent table based on the OF-DPA table definitions.";
    }
    container write-metadata {
      description
        "Each packet can have associated metadata as it traverses the pipeline.
         This instruction writes masked metadata to into the metadata field.";
      presence "Metadata Value";
      leaf metadata-value {
        type of-types:live_ncs_metadata;
        // NCS drop mandatory statement
      }
      leaf metadata_mask {
        type of-types:live_ncs_metadata;
      }
    }
    container write-actions {
      description
        "Merges the specified actions into the current action set associated
         with the packet.";
      uses of-types:live_ncs_action-set;
      leaf group-id {
        type of-group-tables:live_ncs_group-table-entry-ref;
      }
    }
    container apply-actions {
      description
        "Applies the specified actions to the packet immediately, without change
         to the action set associated with the packet.";
      uses of-types:live_ncs_action-set;
      leaf group-id {
        type of-group-tables:live_ncs_group-table-entry-ref;
      }
    }
    leaf clear-actions {
      description
        "Clears all actions in the action set associated with the packet.";
      type empty;
    }
  }

  grouping of-match-fields {
    description
      "These are the match fields that can be used in the flow table entries.
       As in the OpenFlow protocol, packets progress through the pipeline of
       tables.  At each table, packets are associated with a particular flow based
       on the flow match criteria and the packet header and ingress port (as well
       as the priority of the flow entry).

       Each flow entry can have zero or more match criteria.  So all the leaf
       nodes below are optional.";
    leaf in-logical-port {
      type of-types:logical-port;
    }
    leaf in-physical-port {
      type of-types:physical-port;
    }
    leaf metadata {
      type of-types:metadata;
    }
    leaf source-mac {
      type of-types:mac;
    }
    leaf source-mac-mask {
      type of-types:mac-mask;
    }
    leaf destination-mac {
      type of-types:mac;
    }
    leaf destination-mac-mask {
      type of-types:mac-mask;
    }
    container vtag-stack {
      uses of-types:vtag-stack;
    }
    leaf dscp {
      type of-types:dscp;
    }
    leaf ecn {
      type of-types:ecn;
    }
    leaf ip-protocol {
      type of-types:ip-protocol;
    }
    leaf ip-source-prefix {
      type of-types:ip-address-prefix;
    }
    leaf ip-destination-prefix {
      type of-types:ip-address-prefix;
    }
    leaf l4-source-port {
      type of-types:l4-port;
    }
    leaf l4-destination-port {
      type of-types:l4-port;
    }
    leaf ethertype {
      type of-types:ethertype;
    }
    container mpls-label-stack {
      uses of-types:mpls-label-stack;
    }
    leaf icmpv4-type {
      type of-types:icmpv4-type;
    }
    leaf icmpv4-code {
      type of-types:icmpv4-code;
    }
    leaf icmpv6-type {
      type of-types:icmpv6-type;
    }
    leaf icmpv6-code {
      type of-types:icmpv6-code;
    }
    leaf arp-opcode {
      type of-types:arp-opcode;
    }
    leaf arp-source-ip-address {
      type of-types:ipv4-address;
    }
    leaf arp-target-ip-address {
      type of-types:ipv4-address;
    }
    leaf arp-source-mac-address {
      type of-types:mac;
    }
    leaf arp-target-mac-address {
      type of-types:mac;
    }
    leaf ipv6-flow-label {
      type of-types:ipv6-flow-label;
    }
    leaf ndp-target-ip-address {
      type of-types:ipv6-address;
    }
    leaf ipv6-extension-header {
      type of-types:ipv6-extension-header;
    }
    leaf ndp-source-mac-address {
      type of-types:mac;
    }
    leaf ndp-target-mac-address {
      type of-types:mac;
    }
    leaf tunnel-id {
      type of-types:tunnel-id;
    }
  }

  grouping of-instruction-set {
    description
      "These are the instructions that can be used in the flow table entries.
       As in the OpenFlow protocol, packets progress through the pipeline of
       tables.  At each table, packets are matched to a flow entry, and the
       instructions for that flow entry are applied to the packet.

       Each flow entry can have zero or instructions.  So all the leaf notes
       below are optional.  There can be at most one instruction of each type.";
    leaf goto-table {
      type of-flow-tables:flow-table-ref;
      description
        "Indicates the next table in the processing pipeline. The table must
         be a subsequent table based on the OF-DPA table definitions.";
    }
    container write-metadata {
      description
        "Each packet can have associated metadata as it traverses the pipeline.
         This instruction writes masked metadata to into the metadata field.";
      presence "Metadata Value";
      leaf metadata-value {
        type of-types:metadata;
        mandatory true;
      }
      leaf metadata_mask {
        type of-types:metadata;
      }
    }
    container write-actions {
      description
        "Merges the specified actions into the current action set associated
         with the packet.";
      uses of-types:action-set;
      leaf group-id {
        type of-group-tables:group-table-entry-ref;
      }
    }
    container apply-actions {
      description
        "Applies the specified actions to the packet immediately, without change
         to the action set associated with the packet.";
      uses of-types:action-set;
      leaf group-id {
        type of-group-tables:group-table-entry-ref;
      }
    }
    leaf clear-actions {
      description
        "Clears all actions in the action set associated with the packet.";
      type empty;
    }
  }

  augment "/ncs:devices/ncs:device/ncs:rpc" {
    container rpc-of-flow-table-entry-clear-statistics {
      tailf:ncs-device-type "netconf";
      tailf:display-when "not(../../ncs:module) or ../../ncs:module[ncs:name='ciena-of-flow-tables']";
      tailf:action of-flow-table-entry-clear-statistics {
        tailf:actionpoint ncsproxy {
          tailf:internal;
        }
        description
          "An RPC operation to clear the statistics for one or more Flow Table Entries.";
        input {
          choice clear-scope {
            case flow-table-entry {
              leaf flow-table-entry {
                type of-flow-tables:ncs_rpc_notif_flow-table-entry-ref;
              }
              leaf flow-table-entry-vfsi {
                type of-vfsi:ncs_rpc_notif_vfsi-id-ref;
              }
              description
                "Clear stats for this flow-table-entry.";
            }
            case flow-table {
              leaf flow-table {
                type of-flow-tables:ncs_rpc_notif_flow-table-ref;
              }
              leaf flow-table-vfsi {
                type of-vfsi:ncs_rpc_notif_vfsi-id-ref;
              }
              description
                "Clear stats for all flow-table-entries within a flow-table.";
            }
            case vfsi {
              leaf vfsi {
                type of-vfsi:ncs_rpc_notif_vfsi-id-ref;
              }
              description
                "Clear stats for all flow-table-entries within a vfsi.";
            }
            case all {
              leaf all {
                type empty;
              }
              description
                "Clear stats for all flow-table-entries.";
            }
          }
        }
        output {
          leaf status {
            type string;
            description
              "Status of the clear statistics operation.";
          }
        }
      }
    }
  }
  augment "/ncs:devices/ncs:device-group/ncs:ned-id/ncs:rpc" {
    container rpc-of-flow-table-entry-clear-statistics {
      tailf:ncs-device-type "netconf";
      tailf:display-when "/ncs:devices/ncs:device[ncs:name=current()/../../../ncs:member]/ncs:module[ncs:name='ciena-of-flow-tables']";
      tailf:action of-flow-table-entry-clear-statistics {
        tailf:actionpoint ncsproxy {
          tailf:internal;
        }
        description
          "An RPC operation to clear the statistics for one or more Flow Table Entries.";
        input {
          choice clear-scope {
            case flow-table-entry {
              leaf flow-table-entry {
                type of-flow-tables:ncs_rpc_notif_flow-table-entry-ref;
              }
              leaf flow-table-entry-vfsi {
                type of-vfsi:ncs_rpc_notif_vfsi-id-ref;
              }
              description
                "Clear stats for this flow-table-entry.";
            }
            case flow-table {
              leaf flow-table {
                type of-flow-tables:ncs_rpc_notif_flow-table-ref;
              }
              leaf flow-table-vfsi {
                type of-vfsi:ncs_rpc_notif_vfsi-id-ref;
              }
              description
                "Clear stats for all flow-table-entries within a flow-table.";
            }
            case vfsi {
              leaf vfsi {
                type of-vfsi:ncs_rpc_notif_vfsi-id-ref;
              }
              description
                "Clear stats for all flow-table-entries within a vfsi.";
            }
            case all {
              leaf all {
                type empty;
              }
              description
                "Clear stats for all flow-table-entries.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:rpc" {
    container rpc-of-flow-table-clear-statistics {
      tailf:ncs-device-type "netconf";
      tailf:display-when "not(../../ncs:module) or ../../ncs:module[ncs:name='ciena-of-flow-tables']";
      tailf:action of-flow-table-clear-statistics {
        tailf:actionpoint ncsproxy {
          tailf:internal;
        }
        description
          "An RPC operation to clear the statistics for one or more Flow Tables.";
        input {
          choice clear-scope {
            case flow-table {
              leaf flow-table {
                type of-flow-tables:ncs_rpc_notif_flow-table-ref;
              }
              leaf flow-table-vfsi {
                type of-vfsi:ncs_rpc_notif_vfsi-id-ref;
              }
              description
                "Clear stats for this flow-table.";
            }
            case vfsi {
              leaf vfsi {
                type of-vfsi:ncs_rpc_notif_vfsi-id-ref;
              }
              description
                "Clear stats for all flow-tables within a vfsi.";
            }
            case all {
              leaf all {
                type empty;
              }
              description
                "Clear stats for all flow-tables.";
            }
          }
        }
        output {
          leaf status {
            type string;
            description
              "Status of the clear statistics operation.";
          }
        }
      }
    }
  }
  augment "/ncs:devices/ncs:device-group/ncs:ned-id/ncs:rpc" {
    container rpc-of-flow-table-clear-statistics {
      tailf:ncs-device-type "netconf";
      tailf:display-when "/ncs:devices/ncs:device[ncs:name=current()/../../../ncs:member]/ncs:module[ncs:name='ciena-of-flow-tables']";
      tailf:action of-flow-table-clear-statistics {
        tailf:actionpoint ncsproxy {
          tailf:internal;
        }
        description
          "An RPC operation to clear the statistics for one or more Flow Tables.";
        input {
          choice clear-scope {
            case flow-table {
              leaf flow-table {
                type of-flow-tables:ncs_rpc_notif_flow-table-ref;
              }
              leaf flow-table-vfsi {
                type of-vfsi:ncs_rpc_notif_vfsi-id-ref;
              }
              description
                "Clear stats for this flow-table.";
            }
            case vfsi {
              leaf vfsi {
                type of-vfsi:ncs_rpc_notif_vfsi-id-ref;
              }
              description
                "Clear stats for all flow-tables within a vfsi.";
            }
            case all {
              leaf all {
                type empty;
              }
              description
                "Clear stats for all flow-tables.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:config" {
    container of-flow-tables {
      tailf:ncs-device-type "netconf";
      tailf:display-when "not(../../ncs:module) or ../../ncs:module[ncs:name='ciena-of-flow-tables']";
      description
        "The configuration model for flow tables include a list of pre-created
         flow tables, and a flat list of flow table entries, where each entry is
         associated to a particular flow table by a reference.";
      list of-flow-table {
        description
          "This is the list of OpenFlow-like Flow Tables.  These are automatically
           created and configured by the switch, and should not be created by the
           controller. The flow tables correspond to the Broadcom OF-DPA 2.0 tables.
           Only the table-description should be configured by the controller.

           The flow table entries in this list do not contain the actual flow
           entries.  Those are in a separate list, with each flow entry pointing
           to the table which logically containers it.";
        key "name vfsi-id";
        leaf name {
          type of-types:name;
          description
            "This object indicates the identifier and is a text string that is
             used to identify a Flow Table. Unique string values are chosen to
             uniquely identify the flow-table.  A Flow Table can be considered
             to be a stage in a Forwarding Plane Pipeline.
             This element cannot be modified by the controller.";
        }
        leaf vfsi-id {
          type of-vfsi:vfsi-id-ref;
          description
            "An identifier of a Virtual Flow Switch Instance that this Flow Table belongs to.
             This element should not be modified by the controller.";
        }
        leaf table-number {
          type of-types:table-number;
          description
            "An identifier of the Open Flow Table.  This element should not be
             modified by the controller.";
          mandatory true;
        }
        leaf table-description {
          type string {
            length "1..127";
          }
          description
            "A more detailed description that an operator can use to describe
             the Flow Table.";
        }
        // NCS drop config false leaf 'default-table'
      }
      list of-flow-table-entry {
        description
          "This is the list of OpenFlow-like flow entries.  The controller creates
           and modifies these flow entries (along with the group table entries) to
           directly control the switch forwarding plane.

           The flow table entries are in a flat list, but they are logically
           associated with a specific flow table by the flow-table reference.
           This association is important, as the packet processing proceeds through
           the pipeline table-by-table, and only the flows associated with a
           particular table are considered during each stage.

           Unlike OpenFlow flow tables, where the match criteria define the flow
           entry, these flow entries have an explicit entry-number to uniquely
           identify the flow.";
        key "entry-number vfsi-id";
        leaf entry-number {
          type of-types:entry-id;
          description
            "An identifier to uniquely identify the flow entry (unique across
             all flow tables).";
        }
        leaf vfsi-id {
          type of-vfsi:vfsi-id-ref;
          description
            "An identifier of a Virtual Flow Switch Instance that this Flow Table belongs to.";
        }
        leaf entry-description {
          type string {
            length "1..127";
          }
          description
            "A more detailed description that an operator can use to describe
             the Flow Table Entry.";
        }
        leaf flow-table {
          type of-flow-tables:flow-table-ref;
          description
            "A reference to a Flow Table.";
          mandatory true;
        }
        container match {
          uses of-match-fields;
          description
            "The match fields to classify a particular packet to this flow rule.";
        }
        leaf priority {
          type of-types:priority;
          description
            "A priority precedence for an flow entry within an Open Flow Table.
             Higher value priority value wins over a lower priority value within
             the same flow table when multiple matches could occur.";
          mandatory true;
        }
        container instruction-set {
          uses of-instruction-set;
          description
            "The instructions which are applied to the packet when it matches this
             flow entry.";
        }
        leaf idle-timeout {
          type of-types:timeout;
        }
        leaf hard-timeout {
          type of-types:timeout;
        }
        leaf cookie {
          type of-types:cookie;
        }
        leaf stats-collection {
          type of-types:stats-collection;
          description
            "Determines whether stats collection will be turned on or not for a
             flow-table-entry.";
        }
        // NCS drop config false leaf 'default-entry'
      }
    }
    // NCS drop config false container 'of-flow-tables-state'
  }
  augment "/ncs:devices/ncs:device/ncs:live-status" {
    container of-flow-tables {
      tailf:ncs-device-type "netconf";
      tailf:display-when "not(../../ncs:module) or ../../ncs:module[ncs:name='ciena-of-flow-tables'] or (../../ncs:live-status-protocol[not(ncs:capability)]) or (../../ncs:live-status-protocol/ncs:capability/ncs:module[.='ciena-of-flow-tables'])";
      description
        "The configuration model for flow tables include a list of pre-created
         flow tables, and a flat list of flow table entries, where each entry is
         associated to a particular flow table by a reference.";
      list of-flow-table {
        description
          "This is the list of OpenFlow-like Flow Tables.  These are automatically
           created and configured by the switch, and should not be created by the
           controller. The flow tables correspond to the Broadcom OF-DPA 2.0 tables.
           Only the table-description should be configured by the controller.

           The flow table entries in this list do not contain the actual flow
           entries.  Those are in a separate list, with each flow entry pointing
           to the table which logically containers it.";
        key "name vfsi-id";
        leaf name {
          type of-types:live_ncs_name;
          description
            "This object indicates the identifier and is a text string that is
             used to identify a Flow Table. Unique string values are chosen to
             uniquely identify the flow-table.  A Flow Table can be considered
             to be a stage in a Forwarding Plane Pipeline.
             This element cannot be modified by the controller.";
        }
        leaf vfsi-id {
          type of-vfsi:live_ncs_vfsi-id-ref;
          description
            "An identifier of a Virtual Flow Switch Instance that this Flow Table belongs to.
             This element should not be modified by the controller.";
        }
        leaf table-number {
          type of-types:live_ncs_table-number;
          description
            "An identifier of the Open Flow Table.  This element should not be
             modified by the controller.";
          // NCS drop mandatory statement
        }
        leaf table-description {
          type string {
            length "1..127";
          }
          description
            "A more detailed description that an operator can use to describe
             the Flow Table.";
        }
        leaf default-table {
          type empty;
          description
            "Table is a default Table. (e.g. autogenerated by a flowswitch)";
        }
      }
      list of-flow-table-entry {
        description
          "This is the list of OpenFlow-like flow entries.  The controller creates
           and modifies these flow entries (along with the group table entries) to
           directly control the switch forwarding plane.

           The flow table entries are in a flat list, but they are logically
           associated with a specific flow table by the flow-table reference.
           This association is important, as the packet processing proceeds through
           the pipeline table-by-table, and only the flows associated with a
           particular table are considered during each stage.

           Unlike OpenFlow flow tables, where the match criteria define the flow
           entry, these flow entries have an explicit entry-number to uniquely
           identify the flow.";
        key "entry-number vfsi-id";
        leaf entry-number {
          type of-types:live_ncs_entry-id;
          description
            "An identifier to uniquely identify the flow entry (unique across
             all flow tables).";
        }
        leaf vfsi-id {
          type of-vfsi:live_ncs_vfsi-id-ref;
          description
            "An identifier of a Virtual Flow Switch Instance that this Flow Table belongs to.";
        }
        leaf entry-description {
          type string {
            length "1..127";
          }
          description
            "A more detailed description that an operator can use to describe
             the Flow Table Entry.";
        }
        leaf flow-table {
          type of-flow-tables:live_ncs_flow-table-ref;
          description
            "A reference to a Flow Table.";
          // NCS drop mandatory statement
        }
        container match {
          uses live_ncs_of-match-fields;
          description
            "The match fields to classify a particular packet to this flow rule.";
        }
        leaf priority {
          type of-types:live_ncs_priority;
          description
            "A priority precedence for an flow entry within an Open Flow Table.
             Higher value priority value wins over a lower priority value within
             the same flow table when multiple matches could occur.";
          // NCS drop mandatory statement
        }
        container instruction-set {
          uses live_ncs_of-instruction-set;
          description
            "The instructions which are applied to the packet when it matches this
             flow entry.";
        }
        leaf idle-timeout {
          type of-types:live_ncs_timeout;
        }
        leaf hard-timeout {
          type of-types:live_ncs_timeout;
        }
        leaf cookie {
          type of-types:live_ncs_cookie;
        }
        leaf stats-collection {
          type of-types:live_ncs_stats-collection;
          description
            "Determines whether stats collection will be turned on or not for a
             flow-table-entry.";
        }
        leaf default-entry {
          type empty;
          description
            "Entry is a default Entry. (e.g. autogenerated by a flowswitch)";
        }
      }
    }
    container of-flow-tables-state {
      tailf:ncs-device-type "netconf";
      tailf:display-when "not(../../ncs:module) or ../../ncs:module[ncs:name='ciena-of-flow-tables'] or (../../ncs:live-status-protocol[not(ncs:capability)]) or (../../ncs:live-status-protocol/ncs:capability/ncs:module[.='ciena-of-flow-tables'])";
      list of-flow-table {
        description
          "The statistics associated with a flow table (vs. a flow entry).";
        key "name vfsi-id";
        leaf name {
          type of-types:live_ncs_name;
          description
            "An identifier of the Open Flow Table.";
        }
        leaf vfsi-id {
          type of-types:live_ncs_vfsi-id;
          description
            "An identifier of a Virtual Flow Switch Instance that this Flow Table belongs to.";
        }
        uses of-types:live_ncs_of-flow-table-statistics;
      }
      list of-flow-table-entry {
        description
          "The statistics associated with particular flow entry.";
        key "entry-number vfsi-id";
        leaf entry-number {
          type of-types:live_ncs_entry-id;
          description
            "An identifier of the Open Flow Table Entry within an Open Flow Table.";
        }
        leaf vfsi-id {
          type of-types:live_ncs_vfsi-id;
          description
            "An identifier of a Virtual Flow Switch Instance that this Flow Table belongs to.";
        }
        container statistics {
          uses of-types:live_ncs_of-flow-statistics;
        }
        leaf flow-entry-status {
          type of-types:live_ncs_entry-status;
          description
            "indicates the current status of the flow entry relative to the actual
             hardware data plane.";
        }
        leaf cookie {
          type uint64;
        }
      }
    }
  }
  augment "/ncs:devices/ncs:template/ncs:ned-id/ncs:config" {
    container of-flow-tables {
      description
        "The configuration model for flow tables include a list of pre-created
         flow tables, and a flat list of flow table entries, where each entry is
         associated to a particular flow table by a reference.";
      list of-flow-table {
        // NCS patched for predictable order
        ordered-by user;
        description
          "This is the list of OpenFlow-like Flow Tables.  These are automatically
           created and configured by the switch, and should not be created by the
           controller. The flow tables correspond to the Broadcom OF-DPA 2.0 tables.
           Only the table-description should be configured by the controller.

           The flow table entries in this list do not contain the actual flow
           entries.  Those are in a separate list, with each flow entry pointing
           to the table which logically containers it.";
        key "name vfsi-id";
        leaf name {
          type of-types:ncs_template_name;
          description
            "This object indicates the identifier and is a text string that is
             used to identify a Flow Table. Unique string values are chosen to
             uniquely identify the flow-table.  A Flow Table can be considered
             to be a stage in a Forwarding Plane Pipeline.
             This element cannot be modified by the controller.";
        }
        leaf vfsi-id {
          type of-vfsi:ncs_template_vfsi-id-ref;
          description
            "An identifier of a Virtual Flow Switch Instance that this Flow Table belongs to.
             This element should not be modified by the controller.";
        }
        leaf table-number {
          type of-types:ncs_template_table-number;
          description
            "An identifier of the Open Flow Table.  This element should not be
             modified by the controller.";
          // NCS drop mandatory statement
        }
        leaf table-description {
          type string;
          description
            "A more detailed description that an operator can use to describe
             the Flow Table.";
        }
        // NCS drop config false leaf 'default-table'
      }
      list of-flow-table-entry {
        // NCS patched for predictable order
        ordered-by user;
        description
          "This is the list of OpenFlow-like flow entries.  The controller creates
           and modifies these flow entries (along with the group table entries) to
           directly control the switch forwarding plane.

           The flow table entries are in a flat list, but they are logically
           associated with a specific flow table by the flow-table reference.
           This association is important, as the packet processing proceeds through
           the pipeline table-by-table, and only the flows associated with a
           particular table are considered during each stage.

           Unlike OpenFlow flow tables, where the match criteria define the flow
           entry, these flow entries have an explicit entry-number to uniquely
           identify the flow.";
        key "entry-number vfsi-id";
        leaf entry-number {
          type of-types:ncs_template_entry-id;
          description
            "An identifier to uniquely identify the flow entry (unique across
             all flow tables).";
        }
        leaf vfsi-id {
          type of-vfsi:ncs_template_vfsi-id-ref;
          description
            "An identifier of a Virtual Flow Switch Instance that this Flow Table belongs to.";
        }
        leaf entry-description {
          type string;
          description
            "A more detailed description that an operator can use to describe
             the Flow Table Entry.";
        }
        leaf flow-table {
          type of-flow-tables:ncs_template_flow-table-ref;
          description
            "A reference to a Flow Table.";
          // NCS drop mandatory statement
        }
        container match {
          uses ncs_template_of-match-fields;
          description
            "The match fields to classify a particular packet to this flow rule.";
        }
        leaf priority {
          type of-types:ncs_template_priority;
          description
            "A priority precedence for an flow entry within an Open Flow Table.
             Higher value priority value wins over a lower priority value within
             the same flow table when multiple matches could occur.";
          // NCS drop mandatory statement
        }
        container instruction-set {
          uses ncs_template_of-instruction-set;
          description
            "The instructions which are applied to the packet when it matches this
             flow entry.";
        }
        leaf idle-timeout {
          type of-types:ncs_template_timeout;
        }
        leaf hard-timeout {
          type of-types:ncs_template_timeout;
        }
        leaf cookie {
          type of-types:ncs_template_cookie;
        }
        leaf stats-collection {
          type of-types:ncs_template_stats-collection;
          description
            "Determines whether stats collection will be turned on or not for a
             flow-table-entry.";
        }
        // NCS drop config false leaf 'default-entry'
      }
    }
    // NCS drop config false container 'of-flow-tables-state'
  }
}
