module ciena-packet-ptp {
  // Generated by yanger -t ncs
  tailf:mount-id "saos1051-nc-1.0:saos1051-nc-1.0";
  tailf:ncs-device-type "netconf";

  namespace "http://www.ciena.com/ns/yang/ciena-packet-ptp";
  prefix ciena-ptp;

  import ciena-packet-typedefs {
    prefix cntypes;
  }
  import ciena-packet-xcvr {
    prefix xcvr;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";
  description
    "Physical Termination Point. This module models the physical characteristics
     of the signal. This base module contains generic definitions for all PTPs.
     Specific characteristics of PTPs can augment this model to provide more
     detail. PTPs are automatically provisioned by the system.";

  revision 2020-04-22 {
    description
      "Removing max-elements from list lane";
  }
  revision 2019-10-14 {
    description
      "Change ptp->xcvr-id mapping from operational to config";
  }
  revision 2018-05-17 {
    description
      "Based off of ciena-waveserver-ptp.yang";
  }

  typedef ncs_template_ptp-op-enum {
    type string;
    description
      "PTP operational state.";
  }

  typedef ncs_rpc_notif_ptp-op-enum {
    type enumeration {
      enum "up" {
        description
          "The PTP is enabled/operational and capable of carrying traffic.";
      }
      enum "down" {
        description
          "The PTP is disabled.";
      }
      enum "tuning" {
        description
          "Wavelength or CDR tuning in progress.";
      }
      enum "fault" {
        description
          "There is an active alarm associated with the PTP.";
      }
      enum "lower-layer-down" {
        description
          "The PTP is enabled, but a parent object is faulted.";
      }
    }
    description
      "PTP operational state.";
  }

  typedef live_ncs_ptp-op-enum {
    type enumeration {
      enum "up" {
        description
          "The PTP is enabled/operational and capable of carrying traffic.";
      }
      enum "down" {
        description
          "The PTP is disabled.";
      }
      enum "tuning" {
        description
          "Wavelength or CDR tuning in progress.";
      }
      enum "fault" {
        description
          "There is an active alarm associated with the PTP.";
      }
      enum "lower-layer-down" {
        description
          "The PTP is enabled, but a parent object is faulted.";
      }
    }
    description
      "PTP operational state.";
  }

  typedef ptp-op-enum {
    type enumeration {
      enum "up" {
        description
          "The PTP is enabled/operational and capable of carrying traffic.";
      }
      enum "down" {
        description
          "The PTP is disabled.";
      }
      enum "tuning" {
        description
          "Wavelength or CDR tuning in progress.";
      }
      enum "fault" {
        description
          "There is an active alarm associated with the PTP.";
      }
      enum "lower-layer-down" {
        description
          "The PTP is enabled, but a parent object is faulted.";
      }
    }
    description
      "PTP operational state.";
  }

  augment "/ncs:devices/ncs:device/ncs:config" {
    container ptps {
      tailf:ncs-device-type "netconf";
      tailf:display-when "not(../../ncs:module) or ../../ncs:module[ncs:name='ciena-packet-ptp']";
      description
        "Physical Termination Point (PTP) configuration and operational data.";
      list ptp {
        key "ptp-id";
        description
          "List of PTP objects.";
        leaf ptp-id {
          type cntypes:name-string;
          mandatory true;
          description
            "Unique, access identifier string of the PTP (e.g., '1/1'). Key value for the PTP list. Read-only attribute.";
        }
        // NCS drop config false container id
        container state {
          description
            "State information of this PTP instance.";
          leaf admin-state {
            type cntypes:enabled-disabled-enum;
            description
              "Administrative state (enabled or disabled) of the PTP. Intended for future use.";
          }
          // NCS drop config false leaf 'operational-state'
          leaf spli-management {
            when "../../properties/xcvr-type = 'WaveLogic Ai'" {
              tailf:xpath-root 3;
              description
                "SPLI management supported on line-side PTPs only.";
            }
            type cntypes:enabled-disabled-enum;
            description
              "Whether or not Service Photonic Layer Interoperations management
               protocol is enabled on this PTP.";
          }
          // NCS drop config false leaf 'spli-management-status'
        }
        container properties {
          description
            "All the configurable and operational data of this PTP instance.";
          leaf xcvr-type {
            type cntypes:xcvr-type;
            description
              "Transceiver type of the XCVR that's associated with this PTP. Type depends on what is physically plugged in. Read only attribute.";
          }
          leaf parent-id {
            type leafref {
              path "/ncs:devices/ncs:device/ncs:config/xcvr:xcvrs/xcvr:xcvr/xcvr:xcvr-id" {
                tailf:xpath-root 3;
              }
            }
            // NCS dropped explicit config true
            description
              "Reference to the name of the transceiver (XCVR) associated with the PTP. Read-only attribute.";
          }
          // NCS drop config false leaf 'nominal-bit-rate'
          leaf forward-error-correction {
            type cntypes:enabled-disabled-enum;
            description
              "Forward error correction.";
          }
          container thresholds {
            description
              "Common container for PTP threshold configuration data.";
            leaf pre-fec-sf-dbq {
              type decimal64 {
                fraction-digits 2;
                range "-1.00 .. 1.00";
              }
              units "dBQ";
              description
                "Pre-FEC Signal Fail threshold value, expressed in dBQ notation.";
            }
            leaf pre-fec-sd-dbq {
              type decimal64 {
                fraction-digits 2;
                range "-1.00 .. 3.50";
              }
              units "dBQ";
              description
                "Pre-FEC Signal Degrade threshold value, expressed in dBQ notation.";
            }
            // NCS drop config false leaf 'pre-fec-sf-ber'
            // NCS drop config false leaf 'pre-fec-sd-ber'
          }
          container transmitter {
            description
              "PTP transmitter related config and operational data fields.";
            leaf state {
              type cntypes:enabled-disabled-na-enum;
              description
                "Transmitter state (enabled or disabled) of the PTP. PTP Admin State cannot be changed to enabled unless the transmitter state is enabled.";
            }
            // NCS drop config false container wavelength
          }
          // NCS drop config false container lanes
        }
      }
    }
  }
  augment "/ncs:devices/ncs:device/ncs:live-status" {
    container ptps {
      tailf:ncs-device-type "netconf";
      tailf:display-when "not(../../ncs:module) or ../../ncs:module[ncs:name='ciena-packet-ptp'] or (../../ncs:live-status-protocol[not(ncs:capability)]) or (../../ncs:live-status-protocol/ncs:capability/ncs:module[.='ciena-packet-ptp'])";
      description
        "Physical Termination Point (PTP) configuration and operational data.";
      list ptp {
        key "ptp-id";
        description
          "List of PTP objects.";
        leaf ptp-id {
          type cntypes:live_ncs_name-string;
          // NCS drop mandatory statement
          description
            "Unique, access identifier string of the PTP (e.g., '1/1'). Key value for the PTP list. Read-only attribute.";
        }
        container id {
          description
            "Identification information of this PTP instance.";
          leaf name {
            type cntypes:live_ncs_name-string;
            description
              "Name of the PTP instance. Read only attribute.";
          }
        }
        container state {
          description
            "State information of this PTP instance.";
          leaf admin-state {
            type cntypes:live_ncs_enabled-disabled-enum;
            description
              "Administrative state (enabled or disabled) of the PTP. Intended for future use.";
          }
          leaf operational-state {
            type live_ncs_ptp-op-enum;
            description
              "Operational state of the PTP. Read-only attribute.";
          }
          leaf spli-management {
            // NCS drop when statement
            type cntypes:live_ncs_enabled-disabled-enum;
            description
              "Whether or not Service Photonic Layer Interoperations management
               protocol is enabled on this PTP.";
          }
          leaf spli-management-status {
            // NCS drop when statement
            type enumeration {
              enum "matched" {
                description
                  "SPLI is in matched state.";
              }
              enum "mismatched" {
                description
                  "SPLI is in mismatched state.";
              }
              enum "unavailable" {
                description
                  "SPLI state is unknown or SPLI management is disabled.";
              }
            }
            description
              "The operational status of the SPLI management subsystem.";
          }
        }
        container properties {
          description
            "All the configurable and operational data of this PTP instance.";
          leaf xcvr-type {
            type cntypes:live_ncs_xcvr-type;
            description
              "Transceiver type of the XCVR that's associated with this PTP. Type depends on what is physically plugged in. Read only attribute.";
          }
          leaf parent-id {
            type leafref {
              path "/ncs:devices/ncs:device/ncs:live-status/xcvr:xcvrs/xcvr:xcvr/xcvr:xcvr-id" {
                tailf:xpath-root 3;
              }
            }
            description
              "Reference to the name of the transceiver (XCVR) associated with the PTP. Read-only attribute.";
          }
          leaf nominal-bit-rate {
            type cntypes:live_ncs_string-maxl-16;
            units "Gbps";
            description
              "Bit rate, nominal, in Gbps.";
          }
          leaf forward-error-correction {
            type cntypes:live_ncs_enabled-disabled-enum;
            description
              "Forward error correction.";
          }
          container thresholds {
            description
              "Common container for PTP threshold configuration data.";
            leaf pre-fec-sf-dbq {
              type decimal64 {
                fraction-digits 2;
                range "-1.00 .. 1.00";
              }
              units "dBQ";
              description
                "Pre-FEC Signal Fail threshold value, expressed in dBQ notation.";
            }
            leaf pre-fec-sd-dbq {
              type decimal64 {
                fraction-digits 2;
                range "-1.00 .. 3.50";
              }
              units "dBQ";
              description
                "Pre-FEC Signal Degrade threshold value, expressed in dBQ notation.";
            }
            leaf pre-fec-sf-ber {
              type cntypes:live_ncs_string-sci;
              units "errored-bits / bit";
              description
                "Pre-FEC Signal Fail threshold value, expressed in exponential
                 notation, e.g. '1E-06' to '1E-09'.";
            }
            leaf pre-fec-sd-ber {
              type cntypes:live_ncs_string-sci;
              units "errored-bits / bit";
              description
                "Pre-FEC Signal Degrade threshold value, expressed in exponential
                 notation, e.g. '1E-06' to '1E-09'.";
            }
          }
          container transmitter {
            description
              "PTP transmitter related config and operational data fields.";
            leaf state {
              type cntypes:live_ncs_enabled-disabled-na-enum;
              description
                "Transmitter state (enabled or disabled) of the PTP. PTP Admin State cannot be changed to enabled unless the transmitter state is enabled.";
            }
            container wavelength {
              description
                "PTP tx wavelength related operational data fields.";
              leaf value {
                type cntypes:live_ncs_decimal-2-dig;
                units "nm";
                description
                  "Wavelength value setting of the PTP, in nm. Read-only attribute.";
              }
              leaf min-value {
                description
                  "XCVR min-value supported on line-side PTPs only.";
                type cntypes:live_ncs_decimal-2-dig-small;
                units "nm";
              }
              leaf max-value {
                description
                  "XCVR max-value supported on line-side PTPs only.";
                type cntypes:live_ncs_decimal-2-dig-small;
                units "nm";
              }
              leaf actual {
                type cntypes:live_ncs_decimal-2-dig;
                units "nm";
                description
                  "Actual wavelength value of the PTP, in nm. Read-only attribute.";
              }
            }
          }
          container lanes {
            description
              "PTP lanes related operational data fields.";
            leaf number-of-lanes {
              type cntypes:live_ncs_lanes-number;
              description
                "Number of lanes this PTP has.";
            }
            list lane {
              key "lane-number";
              description
                "Operational data of a specific PTP lane.";
              leaf lane-number {
                type cntypes:live_ncs_lanes-number;
                description
                  "Lane number of the PTP being queried.";
              }
              leaf actual-wavelength {
                type cntypes:live_ncs_decimal-2-dig;
                units "nm";
                description
                  "Actual wavelength value for the lane, in nm.";
              }
              container rx {
                description
                  "Lane Rx attributes.";
                container power {
                  description
                    "Lane Rx Power operational attributes (actual power, min/max recorded power, etc.).";
                  uses xcvr:live_ncs_optical-power-group;
                }
                container status {
                  description
                    "Lane Rx Power high/low alarm/warning status/thresholds, where applicable for the XCVR type.";
                  uses xcvr:live_ncs_optical-power-status-group;
                  uses xcvr:live_ncs_optical-power-threshold-group;
                  leaf loss-of-signal {
                    type boolean;
                    description
                      "Rx Loss of Signal.";
                  }
                  leaf loss-of-lock {
                    // NCS drop when statement
                    type boolean;
                    description
                      "Rx Loss of Lock.";
                  }
                }
              }
              container tx {
                description
                  "Lane Tx attributes.";
                container power {
                  description
                    "Lane Tx Power operational attributes (actual power, min/max recorded power, etc.).";
                  uses xcvr:live_ncs_optical-power-group;
                }
                container status {
                  description
                    "Lane Tx Power high/low alarm/warning status/thresholds, where applicable for the XCVR type.";
                  uses xcvr:live_ncs_optical-power-status-group;
                  uses xcvr:live_ncs_optical-power-threshold-group;
                  leaf loss-of-signal {
                    // NCS drop when statement
                    type boolean;
                    description
                      "Tx Loss of Signal.";
                  }
                  leaf loss-of-lock {
                    // NCS drop when statement
                    type boolean;
                    description
                      "Tx Loss of Lock.";
                  }
                }
              }
            }
          }
        }
      }
    }
  }
  augment "/ncs:devices/ncs:template/ncs:ned-id/ncs:config" {
    container ptps {
      description
        "Physical Termination Point (PTP) configuration and operational data.";
      list ptp {
        // NCS patched for predictable order
        ordered-by user;
        key "ptp-id";
        description
          "List of PTP objects.";
        leaf ptp-id {
          type cntypes:ncs_template_name-string;
          // NCS drop mandatory statement
          description
            "Unique, access identifier string of the PTP (e.g., '1/1'). Key value for the PTP list. Read-only attribute.";
        }
        // NCS drop config false container id
        container state {
          description
            "State information of this PTP instance.";
          leaf admin-state {
            type cntypes:ncs_template_enabled-disabled-enum;
            description
              "Administrative state (enabled or disabled) of the PTP. Intended for future use.";
          }
          // NCS drop config false leaf 'operational-state'
          leaf spli-management {
            // NCS drop when statement
            type cntypes:ncs_template_enabled-disabled-enum;
            description
              "Whether or not Service Photonic Layer Interoperations management
               protocol is enabled on this PTP.";
          }
          // NCS drop config false leaf 'spli-management-status'
        }
        container properties {
          description
            "All the configurable and operational data of this PTP instance.";
          leaf xcvr-type {
            type cntypes:ncs_template_xcvr-type;
            description
              "Transceiver type of the XCVR that's associated with this PTP. Type depends on what is physically plugged in. Read only attribute.";
          }
          leaf parent-id {
            type string;
            // NCS dropped explicit config true
            description
              "Reference to the name of the transceiver (XCVR) associated with the PTP. Read-only attribute.";
          }
          // NCS drop config false leaf 'nominal-bit-rate'
          leaf forward-error-correction {
            type cntypes:ncs_template_enabled-disabled-enum;
            description
              "Forward error correction.";
          }
          container thresholds {
            description
              "Common container for PTP threshold configuration data.";
            leaf pre-fec-sf-dbq {
              type string;
              units "dBQ";
              description
                "Pre-FEC Signal Fail threshold value, expressed in dBQ notation.";
            }
            leaf pre-fec-sd-dbq {
              type string;
              units "dBQ";
              description
                "Pre-FEC Signal Degrade threshold value, expressed in dBQ notation.";
            }
            // NCS drop config false leaf 'pre-fec-sf-ber'
            // NCS drop config false leaf 'pre-fec-sd-ber'
          }
          container transmitter {
            description
              "PTP transmitter related config and operational data fields.";
            leaf state {
              type cntypes:ncs_template_enabled-disabled-na-enum;
              description
                "Transmitter state (enabled or disabled) of the PTP. PTP Admin State cannot be changed to enabled unless the transmitter state is enabled.";
            }
            // NCS drop config false container wavelength
          }
          // NCS drop config false container lanes
        }
      }
    }
  }
}
