module yumaworks-yang-api {
  // Generated by yanger -t ncs
  tailf:mount-id "saos1051-nc-1.0:saos1051-nc-1.0";
  tailf:ncs-device-type "netconf";

  namespace "http://yumaworks.com/ns/yumaworks-yang-api";
  prefix yapi;

  import ietf-inet-types {
    prefix inet;
  }
  import yuma-ncx {
    prefix ncx;
  }
  import yumaworks-extensions {
    prefix ywx;
  }
  import tailf-common {
    prefix tailf;
  }
  import tailf-ncs {
    prefix ncs;
  }

  organization
    "YumaWorks, Inc.";
  contact
    "Support <support@yumaworks.com>";
  description
    "This module contains abstract object definitions for
     the YANG-API protocol.";

  revision 2015-06-19 {
    description
      "Add yang leaf for root of schema retrieval for YANG-API";
  }
  revision 2013-12-14 {
    description
      "Remove unimplemented YANG extension";
  }
  revision 2013-10-14 {
    description
      "Add /yang-api/events to provide test SSE hook";
  }
  revision 2013-02-06 {
    description
      "Rewrite to match draft-bierman-netconf-yang-api-01.txt";
  }
  revision 2012-06-28 {
    description
      "Initial version";
  }

  augment "/ncs:devices/ncs:device/ncs:config" {
    container yang-api {
      tailf:ncs-device-type "netconf";
      tailf:display-when "not(../../ncs:module) or ../../ncs:module[ncs:name='yumaworks-yang-api']";
      ncx:abstract;
      ncx:hidden;
      container datastore {
        ncx:root;
      }
      container modules {
        leaf-list module {
          type inet:uri;
        }
      }
      container operations {
        ywx:rpc-root;
      }
      leaf events {
        type empty;
      }
      leaf version {
        type string;
      }
      leaf yang {
        type empty;
      }
    }
    container query {
      tailf:ncs-device-type "netconf";
      tailf:display-when "not(../../ncs:module) or ../../ncs:module[ncs:name='yumaworks-yang-api']";
      ncx:abstract;
      ncx:hidden;
      description
        "YANG-API Query String Parameters";
      leaf config {
        type boolean;
        default "true";
        description
          "Get config true or config false nodes.";
      }
      leaf depth {
        type union {
          type enumeration {
            enum "unbounded";
          }
          type uint32 {
            range "1..max";
          }
        }
        default "unbounded";
        description
          "Resource retrieval depth requested";
      }
      leaf format {
        type enumeration {
          enum "xml";
          enum "json";
        }
        default "json";
        description
          "Response encoding requested";
      }
      leaf insert {
        type enumeration {
          enum "first";
          enum "last";
          enum "before";
          enum "after";
        }
        default "last";
        description
          "Insert mode for an edit operation";
      }
      leaf point {
        ywx:urlpath;
        type string {
          length "1 .. max";
        }
        description
          "YANG-API instance identifier for the insertion point
           node for the edit operation.";
      }
      leaf select {
        type string {
          length "1 .. max";
        }
        description
          "An XPath expression that will be evaluated using the
           target resource instance as the context node and the
           document root. It is expected to return a node-set
           result representing the descendants within the context
           node that should be returned in a GET response.";
      }
      leaf test {
        type string {
          length "1 .. max";
        }
      }
    }
  }
  augment "/ncs:devices/ncs:device/ncs:live-status" {
    container yang-api {
      tailf:ncs-device-type "netconf";
      tailf:display-when "not(../../ncs:module) or ../../ncs:module[ncs:name='yumaworks-yang-api'] or (../../ncs:live-status-protocol[not(ncs:capability)]) or (../../ncs:live-status-protocol/ncs:capability/ncs:module[.='yumaworks-yang-api'])";
      ncx:abstract;
      ncx:hidden;
      container datastore {
        ncx:root;
      }
      container modules {
        leaf-list module {
          type inet:uri;
        }
      }
      container operations {
        ywx:rpc-root;
      }
      leaf events {
        type empty;
      }
      leaf version {
        type string;
      }
      leaf yang {
        type empty;
      }
    }
    container query {
      tailf:ncs-device-type "netconf";
      tailf:display-when "not(../../ncs:module) or ../../ncs:module[ncs:name='yumaworks-yang-api'] or (../../ncs:live-status-protocol[not(ncs:capability)]) or (../../ncs:live-status-protocol/ncs:capability/ncs:module[.='yumaworks-yang-api'])";
      ncx:abstract;
      ncx:hidden;
      description
        "YANG-API Query String Parameters";
      leaf config {
        type boolean;
        // NCS drop default statement
        description
          "Get config true or config false nodes.";
      }
      leaf depth {
        type union {
          type enumeration {
            enum "unbounded";
          }
          type uint32 {
            range "1..max";
          }
        }
        // NCS drop default statement
        description
          "Resource retrieval depth requested";
      }
      leaf format {
        type enumeration {
          enum "xml";
          enum "json";
        }
        // NCS drop default statement
        description
          "Response encoding requested";
      }
      leaf insert {
        type enumeration {
          enum "first";
          enum "last";
          enum "before";
          enum "after";
        }
        // NCS drop default statement
        description
          "Insert mode for an edit operation";
      }
      leaf point {
        ywx:urlpath;
        type string {
          length "1 .. max";
        }
        description
          "YANG-API instance identifier for the insertion point
           node for the edit operation.";
      }
      leaf select {
        type string {
          length "1 .. max";
        }
        description
          "An XPath expression that will be evaluated using the
           target resource instance as the context node and the
           document root. It is expected to return a node-set
           result representing the descendants within the context
           node that should be returned in a GET response.";
      }
      leaf test {
        type string {
          length "1 .. max";
        }
      }
    }
  }
  augment "/ncs:devices/ncs:template/ncs:ned-id/ncs:config" {
    container yang-api {
      ncx:abstract;
      ncx:hidden;
      container datastore {
        ncx:root;
      }
      container modules {
        leaf-list module {
          // NCS patched for predictable order
          ordered-by user;
          type string;
        }
      }
      container operations {
        ywx:rpc-root;
      }
      leaf events {
        type empty;
      }
      leaf version {
        type string;
      }
      leaf yang {
        type empty;
      }
    }
    container query {
      ncx:abstract;
      ncx:hidden;
      description
        "YANG-API Query String Parameters";
      leaf config {
        type string;
        // NCS drop default statement
        description
          "Get config true or config false nodes.";
      }
      leaf depth {
        type string;
        // NCS drop default statement
        description
          "Resource retrieval depth requested";
      }
      leaf format {
        type string;
        // NCS drop default statement
        description
          "Response encoding requested";
      }
      leaf insert {
        type string;
        // NCS drop default statement
        description
          "Insert mode for an edit operation";
      }
      leaf point {
        ywx:urlpath;
        type string;
        description
          "YANG-API instance identifier for the insertion point
           node for the edit operation.";
      }
      leaf select {
        type string;
        description
          "An XPath expression that will be evaluated using the
           target resource instance as the context node and the
           document root. It is expected to return a node-set
           result representing the descendants within the context
           node that should be returned in a GET response.";
      }
      leaf test {
        type string;
      }
    }
  }
}
