module ciena-pseudowires {
  // Generated by yanger -t ncs
  tailf:mount-id "saos1051-nc-1.0:saos1051-nc-1.0";
  tailf:ncs-device-type "netconf";

  namespace "http://ciena.com/ns/yang/ciena-pseudowires";
  prefix cnoper;

  import ietf-inet-types {
    prefix inet;
  }
  import ietf-pseudowires {
    prefix pw;
  }
  import ciena-l3-types {
    prefix cn-l3-types;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This module contains the Ciena proprietary YANG deviations
     of the standard pseudowire YANG module.
     Copyright (c) 2019 Ciena Corporation.  All rights reserved.

     All information contained herein is, and remains
     the property of Ciena Corporation. Dissemination of this
     information or reproduction of this material is strictly
     forbidden unless prior written permission is obtained from
     Ciena Corporation.";

  revision 2020-02-25 {
    description
      "1. Added Tunnel name,type,source-ip
          destination-ip
       2. Added leaf operational fat";
  }
  revision 2019-03-03 {
    description
      "Initial version";
  }

  typedef ncs_template_pseudowire-status-type {
    type string;
    description
      "Pseudowire status type, as registered in the IANA Pseudowire Status Code Registry";
  }

  typedef ncs_rpc_notif_pseudowire-status-type {
    type enumeration {
      enum "pseudowire-forwarding" {
        value 0;
        description
          "Pseudowire is forwarding";
      }
      enum "pseudowire-not-forwarding" {
        value 1;
        description
          "Pseudowire is not forwarding";
      }
      enum "local-attachment-circuit-receive-fault" {
        value 2;
        description
          "Local attachment circuit (ingress) receive fault";
      }
      enum "local-attachment-circuit-transmit-fault" {
        value 3;
        description
          "Local attachment circuit (egress) transmit fault";
      }
      enum "local-PSN-facing-PW-receive-fault" {
        value 4;
        description
          "Local PSN-facing PW (ingress) receive fault";
      }
      enum "local-PSN-facing-PW-transmit-fault" {
        value 5;
        description
          "Local PSN-facing PW (egress) transmit fault";
      }
      enum "PW-preferential-forwarding-status" {
        value 6;
        description
          "Pseudowire preferential forwarding status";
      }
      enum "PW-request-switchover-status" {
        value 7;
        description
          "Pseudowire request switchover status";
      }
    }
    description
      "Pseudowire status type, as registered in the IANA Pseudowire Status Code Registry";
  }

  typedef live_ncs_pseudowire-status-type {
    type enumeration {
      enum "pseudowire-forwarding" {
        value 0;
        description
          "Pseudowire is forwarding";
      }
      enum "pseudowire-not-forwarding" {
        value 1;
        description
          "Pseudowire is not forwarding";
      }
      enum "local-attachment-circuit-receive-fault" {
        value 2;
        description
          "Local attachment circuit (ingress) receive fault";
      }
      enum "local-attachment-circuit-transmit-fault" {
        value 3;
        description
          "Local attachment circuit (egress) transmit fault";
      }
      enum "local-PSN-facing-PW-receive-fault" {
        value 4;
        description
          "Local PSN-facing PW (ingress) receive fault";
      }
      enum "local-PSN-facing-PW-transmit-fault" {
        value 5;
        description
          "Local PSN-facing PW (egress) transmit fault";
      }
      enum "PW-preferential-forwarding-status" {
        value 6;
        description
          "Pseudowire preferential forwarding status";
      }
      enum "PW-request-switchover-status" {
        value 7;
        description
          "Pseudowire request switchover status";
      }
    }
    description
      "Pseudowire status type, as registered in the IANA Pseudowire Status Code Registry";
  }

  typedef pseudowire-status-type {
    type enumeration {
      enum "pseudowire-forwarding" {
        value 0;
        description
          "Pseudowire is forwarding";
      }
      enum "pseudowire-not-forwarding" {
        value 1;
        description
          "Pseudowire is not forwarding";
      }
      enum "local-attachment-circuit-receive-fault" {
        value 2;
        description
          "Local attachment circuit (ingress) receive fault";
      }
      enum "local-attachment-circuit-transmit-fault" {
        value 3;
        description
          "Local attachment circuit (egress) transmit fault";
      }
      enum "local-PSN-facing-PW-receive-fault" {
        value 4;
        description
          "Local PSN-facing PW (ingress) receive fault";
      }
      enum "local-PSN-facing-PW-transmit-fault" {
        value 5;
        description
          "Local PSN-facing PW (egress) transmit fault";
      }
      enum "PW-preferential-forwarding-status" {
        value 6;
        description
          "Pseudowire preferential forwarding status";
      }
      enum "PW-request-switchover-status" {
        value 7;
        description
          "Pseudowire request switchover status";
      }
    }
    description
      "Pseudowire status type, as registered in the IANA Pseudowire Status Code Registry";
  }

  grouping ncs_template_tx-stats-collection-grouping {
    description
      "counters for tx statistics";
    leaf tx-bytes {
      type string;
      description
        "the number of bytes sent on the pseudowire";
    }
    leaf tx-packets {
      type string;
      description
        "the number of packets sent on the pseudowire";
    }
    leaf dropped-tx-bytes {
      type string;
      description
        "the number of bytes sent on the pseudowire that were chosen to be dropped";
    }
    leaf dropped-tx-packets {
      type string;
      description
        "the number of packets sent on the pseudowire that were chosen to be dropped";
    }
  }

  grouping ncs_template_rx-stats-collection-grouping {
    description
      "counters for rx statistics";
    leaf rx-bytes {
      type string;
      description
        "the number of bytes received on the pseudowire";
    }
    leaf rx-packets {
      type string;
      description
        "the number of packets received on the pseudowire";
    }
    leaf dropped-rx-bytes {
      type string;
      description
        "the number of bytes received on the pseudowire that were chosen to be dropped";
    }
    leaf dropped-rx-packets {
      type string;
      description
        "the number of packets received on the pseudowire that were chosen to be dropped";
    }
  }

  grouping ncs_rpc_notif_tx-stats-collection-grouping {
    description
      "counters for tx statistics";
    leaf tx-bytes {
      type yang:counter64;
      description
        "the number of bytes sent on the pseudowire";
    }
    leaf tx-packets {
      type yang:counter64;
      description
        "the number of packets sent on the pseudowire";
    }
    leaf dropped-tx-bytes {
      type yang:counter64;
      description
        "the number of bytes sent on the pseudowire that were chosen to be dropped";
    }
    leaf dropped-tx-packets {
      type yang:counter64;
      description
        "the number of packets sent on the pseudowire that were chosen to be dropped";
    }
  }

  grouping ncs_rpc_notif_rx-stats-collection-grouping {
    description
      "counters for rx statistics";
    leaf rx-bytes {
      type yang:counter64;
      description
        "the number of bytes received on the pseudowire";
    }
    leaf rx-packets {
      type yang:counter64;
      description
        "the number of packets received on the pseudowire";
    }
    leaf dropped-rx-bytes {
      type yang:counter64;
      description
        "the number of bytes received on the pseudowire that were chosen to be dropped";
    }
    leaf dropped-rx-packets {
      type yang:counter64;
      description
        "the number of packets received on the pseudowire that were chosen to be dropped";
    }
  }

  grouping live_ncs_tx-stats-collection-grouping {
    description
      "counters for tx statistics";
    leaf tx-bytes {
      type yang:counter64;
      description
        "the number of bytes sent on the pseudowire";
    }
    leaf tx-packets {
      type yang:counter64;
      description
        "the number of packets sent on the pseudowire";
    }
    leaf dropped-tx-bytes {
      type yang:counter64;
      description
        "the number of bytes sent on the pseudowire that were chosen to be dropped";
    }
    leaf dropped-tx-packets {
      type yang:counter64;
      description
        "the number of packets sent on the pseudowire that were chosen to be dropped";
    }
  }

  grouping live_ncs_rx-stats-collection-grouping {
    description
      "counters for rx statistics";
    leaf rx-bytes {
      type yang:counter64;
      description
        "the number of bytes received on the pseudowire";
    }
    leaf rx-packets {
      type yang:counter64;
      description
        "the number of packets received on the pseudowire";
    }
    leaf dropped-rx-bytes {
      type yang:counter64;
      description
        "the number of bytes received on the pseudowire that were chosen to be dropped";
    }
    leaf dropped-rx-packets {
      type yang:counter64;
      description
        "the number of packets received on the pseudowire that were chosen to be dropped";
    }
  }

  grouping tx-stats-collection-grouping {
    description
      "counters for tx statistics";
    leaf tx-bytes {
      type yang:counter64;
      description
        "the number of bytes sent on the pseudowire";
    }
    leaf tx-packets {
      type yang:counter64;
      description
        "the number of packets sent on the pseudowire";
    }
    leaf dropped-tx-bytes {
      type yang:counter64;
      description
        "the number of bytes sent on the pseudowire that were chosen to be dropped";
    }
    leaf dropped-tx-packets {
      type yang:counter64;
      description
        "the number of packets sent on the pseudowire that were chosen to be dropped";
    }
  }

  grouping rx-stats-collection-grouping {
    description
      "counters for rx statistics";
    leaf rx-bytes {
      type yang:counter64;
      description
        "the number of bytes received on the pseudowire";
    }
    leaf rx-packets {
      type yang:counter64;
      description
        "the number of packets received on the pseudowire";
    }
    leaf dropped-rx-bytes {
      type yang:counter64;
      description
        "the number of bytes received on the pseudowire that were chosen to be dropped";
    }
    leaf dropped-rx-packets {
      type yang:counter64;
      description
        "the number of packets received on the pseudowire that were chosen to be dropped";
    }
  }

  augment "/ncs:devices/ncs:device/ncs:rpc" {
    container rpc-pseudowire-clear-statistics {
      tailf:ncs-device-type "netconf";
      tailf:display-when "not(../../ncs:module) or ../../ncs:module[ncs:name='ciena-pseudowires']";
      tailf:action pseudowire-clear-statistics {
        tailf:actionpoint ncsproxy {
          tailf:internal;
        }
        input {
          choice clear-stats {
            case pseudowire-name {
              leaf pseudowire-name {
                type string;
              }
              description
                "Clear stats for this pseudowire.";
            }
            case all {
              leaf all {
                type empty;
              }
              description
                "Clear stats for all pseudowires.";
            }
          }
        }
        output {
          leaf response {
            type string;
            description
              "The response could be 'success', or the reason for pseudowire-clear-statistics failure";
          }
        }
      }
    }
  }
  augment "/ncs:devices/ncs:device-group/ncs:ned-id/ncs:rpc" {
    container rpc-pseudowire-clear-statistics {
      tailf:ncs-device-type "netconf";
      tailf:display-when "/ncs:devices/ncs:device[ncs:name=current()/../../../ncs:member]/ncs:module[ncs:name='ciena-pseudowires']";
      tailf:action pseudowire-clear-statistics {
        tailf:actionpoint ncsproxy {
          tailf:internal;
        }
        input {
          choice clear-stats {
            case pseudowire-name {
              leaf pseudowire-name {
                type string;
              }
              description
                "Clear stats for this pseudowire.";
            }
            case all {
              leaf all {
                type empty;
              }
              description
                "Clear stats for all pseudowires.";
            }
          }
        }
        output {
          container "device" {
            leaf "name" {
              type string;
            }
            leaf "info" {
              type string;
            }
            container "result" {
              leaf response {
                type string;
                description
                  "The response could be 'success', or the reason for pseudowire-clear-statistics failure";
              }
            }
          }
        }
      }
    }
  }
  augment "/ncs:devices/ncs:device/ncs:config" {
    // NCS drop config false container 'pseudowires-state'
  }
  augment "/ncs:devices/ncs:device/ncs:live-status" {
    container pseudowires-state {
      tailf:ncs-device-type "netconf";
      tailf:display-when "not(../../ncs:module) or ../../ncs:module[ncs:name='ciena-pseudowires'] or (../../ncs:live-status-protocol[not(ncs:capability)]) or (../../ncs:live-status-protocol/ncs:capability/ncs:module[.='ciena-pseudowires'])";
      description
        "Pseudowire State Information.";
      list pseudowire {
        key "name";
        description
          "Operational data for pseudowire";
        leaf name {
          type leafref {
            path "/ncs:devices/ncs:device/ncs:live-status/pw:pseudowires/pw:pseudowire/pw:name" {
              tailf:xpath-root 3;
            }
          }
          description
            "Pseudowire name";
        }
        leaf index {
          type uint32;
          description
            "Index value of pseudowire";
        }
        leaf peer-ip {
          type inet:ipv4-address;
          description
            "peer IP address";
        }
        leaf oper-status {
          type string;
          description
            "Pseudowire operation status";
        }
        leaf in-label {
          type uint32;
          description
            "pseudowire inlabel value";
        }
        leaf out-label {
          type uint32;
          description
            "pseudowire outlabel value";
        }
        leaf mode {
          type string;
          description
            "pseudowire mode as mesh or spoke";
        }
        leaf service-type {
          type cn-l3-types:live_ncs_mpls-vpls-type;
          description
            "service type value such as vlan or ethernet";
        }
        leaf protection-state {
          type cn-l3-types:live_ncs_l2vpn-protection-type;
          description
            "protection-state value for pseudowire";
        }
        leaf remote-pw-status {
          type live_ncs_pseudowire-status-type;
          description
            "status of remote pseudowire";
        }
        leaf local-pw-status {
          type live_ncs_pseudowire-status-type;
          description
            "pseudowire status of local node";
        }
        leaf remote-refresh-timer {
          type uint32;
          units "seconds";
          description
            "Refresh timer value for remote pseudowire";
        }
        leaf role {
          type string;
          description
            "Pseudowire role as primary or backup";
        }
        leaf type {
          type string;
          description
            "Pseudowire type as static or dynamic";
        }
        leaf stats-collection {
          type string;
          description
            "Pseudowire statistics are on/off per pseudowire";
        }
        leaf operational-cw {
          type string;
          description
            "Pseudowire operational control-word";
        }
        leaf operational-cc {
          type string;
          description
            "Pseudowire operational cc-type";
        }
        leaf tunnel-type {
          type string;
          description
            "This defines different tunnel types";
        }
        leaf tunnel-name {
          type string;
          description
            "User provided tunnel name over which pw was created";
        }
        leaf tunnel-source-ip {
          type inet:ipv4-address;
          description
            "User provided tunnel source-ip";
        }
        leaf tunnel-destination-ip {
          type inet:ipv4-address;
          description
            "User provided tunnel destination-ip";
        }
        leaf operational-fat {
          type string;
          description
            "Pseudowire operational fat";
        }
        container statistics {
          description
            "pseudowire statistics";
          uses live_ncs_tx-stats-collection-grouping;
          uses live_ncs_rx-stats-collection-grouping;
        }
      }
      container pseudowire-count {
        description
          "Pseudowires Count Information";
        leaf total-vpls {
          type uint32;
          description
            "Total count of VPLS pseudowires";
        }
        leaf active-vpls {
          type uint32;
          description
            "Active count of VPLS pseudowires";
        }
        leaf inactive-vpls {
          type uint32;
          description
            "Inactive count of VPLS pseudowires";
        }
        leaf total-vpws {
          type uint32;
          description
            "Total count of VPWS pseudowires";
        }
        leaf active-vpws {
          type uint32;
          description
            "Active count of VPWS pseudowires";
        }
        leaf inactive-vpws {
          type uint32;
          description
            "Inactive count of VPWS pseudowires";
        }
      }
    }
  }
  augment "/ncs:devices/ncs:template/ncs:ned-id/ncs:config" {
    // NCS drop config false container 'pseudowires-state'
  }
}
