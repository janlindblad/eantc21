module ietf-pseudowires {
  // Generated by yanger -t ncs
  tailf:mount-id "saos1051-nc-1.0:saos1051-nc-1.0";
  tailf:ncs-device-type "netconf";

  namespace "urn:ietf:params:xml:ns:yang:ietf-pseudowires";
  prefix pw;

  import ietf-inet-types {
    prefix inet;
  }
  import ietf-routing-types {
    prefix rt-types;
  }
  import tailf-common {
    prefix tailf;
  }
  import tailf-ncs {
    prefix ncs;
  }

  organization
    "ietf";
  contact
    "ietf";
  description
    "Pseudowire YANG model";

  revision 2017-06-26 {
    description
      "Initial revision  - Created a new model for pseudowires, which used  to be defined within the L2VPN model ";
    reference "";
  }

  typedef ncs_template_pseudowire-ref {
    type string;
    description
      "A type that is a reference to a pseudowire";
  }

  typedef ncs_template_pw-template-ref {
    type string;
    description
      "A type that is a reference to a pw-template";
  }

  typedef ncs_template_cw-negotiation-type {
    type string;
    description
      "control-word negotiation preference type";
  }

  typedef ncs_template_pseudowire-status-type {
    type string;
    description
      "Pseudowire status type, as registered in the IANA Pseudowire Status Code Registry";
  }

  typedef ncs_rpc_notif_pseudowire-ref {
    type string;
    description
      "A type that is a reference to a pseudowire";
  }

  typedef ncs_rpc_notif_pw-template-ref {
    type string;
    description
      "A type that is a reference to a pw-template";
  }

  typedef ncs_rpc_notif_cw-negotiation-type {
    type enumeration {
      enum "non-preferred" {
        description
          "No preference for control-word";
      }
      enum "preferred" {
        description
          "Prefer to have control-word negotiation";
      }
    }
    description
      "control-word negotiation preference type";
  }

  typedef ncs_rpc_notif_pseudowire-status-type {
    type bits {
      bit pseudowire-forwarding {
        position 0;
        description
          "Pseudowire is forwarding";
      }
      bit pseudowire-not-forwarding {
        position 1;
        description
          "Pseudowire is not forwarding";
      }
      bit local-attachment-circuit-receive-fault {
        position 2;
        description
          "Local attachment circuit (ingress) receive fault";
      }
      bit local-attachment-circuit-transmit-fault {
        position 3;
        description
          "Local attachment circuit (egress) transmit fault";
      }
      bit local-PSN-facing-PW-receive-fault {
        position 4;
        description
          "Local PSN-facing PW (ingress) receive fault";
      }
      bit local-PSN-facing-PW-transmit-fault {
        position 5;
        description
          "Local PSN-facing PW (egress) transmit fault";
      }
      bit PW-preferential-forwarding-status {
        position 6;
        description
          "Pseudowire preferential forwarding status";
      }
      bit PW-request-switchover-status {
        position 7;
        description
          "Pseudowire request switchover status";
      }
    }
    description
      "Pseudowire status type, as registered in the IANA Pseudowire Status Code Registry";
  }

  typedef live_ncs_pseudowire-ref {
    type leafref {
      path "/ncs:devices/ncs:device/ncs:live-status/pw:pseudowires/pw:pseudowire/pw:name" {
        tailf:xpath-root 3;
      }
    }
    description
      "A type that is a reference to a pseudowire";
  }

  typedef live_ncs_pw-template-ref {
    type leafref {
      path "/ncs:devices/ncs:device/ncs:live-status/pw:pseudowires/pw:pw-templates/pw:pw-template/pw:name" {
        tailf:xpath-root 3;
      }
    }
    description
      "A type that is a reference to a pw-template";
  }

  typedef live_ncs_cw-negotiation-type {
    type enumeration {
      enum "non-preferred" {
        description
          "No preference for control-word";
      }
      enum "preferred" {
        description
          "Prefer to have control-word negotiation";
      }
    }
    description
      "control-word negotiation preference type";
  }

  typedef live_ncs_pseudowire-status-type {
    type bits {
      bit pseudowire-forwarding {
        position 0;
        description
          "Pseudowire is forwarding";
      }
      bit pseudowire-not-forwarding {
        position 1;
        description
          "Pseudowire is not forwarding";
      }
      bit local-attachment-circuit-receive-fault {
        position 2;
        description
          "Local attachment circuit (ingress) receive fault";
      }
      bit local-attachment-circuit-transmit-fault {
        position 3;
        description
          "Local attachment circuit (egress) transmit fault";
      }
      bit local-PSN-facing-PW-receive-fault {
        position 4;
        description
          "Local PSN-facing PW (ingress) receive fault";
      }
      bit local-PSN-facing-PW-transmit-fault {
        position 5;
        description
          "Local PSN-facing PW (egress) transmit fault";
      }
      bit PW-preferential-forwarding-status {
        position 6;
        description
          "Pseudowire preferential forwarding status";
      }
      bit PW-request-switchover-status {
        position 7;
        description
          "Pseudowire request switchover status";
      }
    }
    description
      "Pseudowire status type, as registered in the IANA Pseudowire Status Code Registry";
  }

  typedef pseudowire-ref {
    type leafref {
      path "/ncs:devices/ncs:device/ncs:config/pw:pseudowires/pw:pseudowire/pw:name" {
        tailf:xpath-root 3;
      }
    }
    description
      "A type that is a reference to a pseudowire";
  }

  typedef pw-template-ref {
    type leafref {
      path "/ncs:devices/ncs:device/ncs:config/pw:pseudowires/pw:pw-templates/pw:pw-template/pw:name" {
        tailf:xpath-root 3;
      }
    }
    description
      "A type that is a reference to a pw-template";
  }

  typedef cw-negotiation-type {
    type enumeration {
      enum "non-preferred" {
        description
          "No preference for control-word";
      }
      enum "preferred" {
        description
          "Prefer to have control-word negotiation";
      }
    }
    description
      "control-word negotiation preference type";
  }

  typedef pseudowire-status-type {
    type bits {
      bit pseudowire-forwarding {
        position 0;
        description
          "Pseudowire is forwarding";
      }
      bit pseudowire-not-forwarding {
        position 1;
        description
          "Pseudowire is not forwarding";
      }
      bit local-attachment-circuit-receive-fault {
        position 2;
        description
          "Local attachment circuit (ingress) receive fault";
      }
      bit local-attachment-circuit-transmit-fault {
        position 3;
        description
          "Local attachment circuit (egress) transmit fault";
      }
      bit local-PSN-facing-PW-receive-fault {
        position 4;
        description
          "Local PSN-facing PW (ingress) receive fault";
      }
      bit local-PSN-facing-PW-transmit-fault {
        position 5;
        description
          "Local PSN-facing PW (egress) transmit fault";
      }
      bit PW-preferential-forwarding-status {
        position 6;
        description
          "Pseudowire preferential forwarding status";
      }
      bit PW-request-switchover-status {
        position 7;
        description
          "Pseudowire request switchover status";
      }
    }
    description
      "Pseudowire status type, as registered in the IANA Pseudowire Status Code Registry";
  }

  grouping ncs_template_pw-type-grp {
    description
      "pseudowire type grouping";
    choice pw-type {
      description
        "A choice of pseudowire type";
      case ldp-or-static-pw {
        leaf peer-ip {
          type string;
          description
            "peer IP address";
        }
        leaf pw-id {
          type string;
          description
            "pseudowire id";
        }
        leaf icb {
          type string;
          description
            "inter-chassis backup";
        }
        leaf transmit-label {
          type rt-types:ncs_template_mpls-label;
          description
            "transmit lable";
        }
        leaf receive-label {
          type rt-types:ncs_template_mpls-label;
          description
            "receive label";
        }
      }
      case bgp-pw {
        leaf remote-pe-id {
          type string;
          description
            "remote pe id";
        }
      }
      case bgp-ad-pw {
        leaf remote-ve-id {
          type string;
          description
            "remote ve id";
        }
      }
    }
  }

  grouping ncs_rpc_notif_pw-type-grp {
    description
      "pseudowire type grouping";
    choice pw-type {
      description
        "A choice of pseudowire type";
      case ldp-or-static-pw {
        leaf peer-ip {
          type inet:ip-address;
          description
            "peer IP address";
        }
        leaf pw-id {
          type uint32;
          description
            "pseudowire id";
        }
        leaf icb {
          type boolean;
          description
            "inter-chassis backup";
        }
        leaf transmit-label {
          type rt-types:ncs_rpc_notif_mpls-label;
          description
            "transmit lable";
        }
        leaf receive-label {
          type rt-types:ncs_rpc_notif_mpls-label;
          description
            "receive label";
        }
      }
      case bgp-pw {
        leaf remote-pe-id {
          type inet:ip-address;
          description
            "remote pe id";
        }
      }
      case bgp-ad-pw {
        leaf remote-ve-id {
          type uint16;
          description
            "remote ve id";
        }
      }
    }
  }

  grouping live_ncs_pw-type-grp {
    description
      "pseudowire type grouping";
    choice pw-type {
      description
        "A choice of pseudowire type";
      case ldp-or-static-pw {
        leaf peer-ip {
          type inet:ip-address;
          description
            "peer IP address";
        }
        leaf pw-id {
          type uint32;
          description
            "pseudowire id";
        }
        leaf icb {
          type boolean;
          description
            "inter-chassis backup";
        }
        leaf transmit-label {
          type rt-types:live_ncs_mpls-label;
          description
            "transmit lable";
        }
        leaf receive-label {
          type rt-types:live_ncs_mpls-label;
          description
            "receive label";
        }
      }
      case bgp-pw {
        leaf remote-pe-id {
          type inet:ip-address;
          description
            "remote pe id";
        }
      }
      case bgp-ad-pw {
        leaf remote-ve-id {
          type uint16;
          description
            "remote ve id";
        }
      }
    }
  }

  grouping pw-type-grp {
    description
      "pseudowire type grouping";
    choice pw-type {
      description
        "A choice of pseudowire type";
      case ldp-or-static-pw {
        leaf peer-ip {
          type inet:ip-address;
          description
            "peer IP address";
        }
        leaf pw-id {
          type uint32;
          description
            "pseudowire id";
        }
        leaf icb {
          type boolean;
          description
            "inter-chassis backup";
        }
        leaf transmit-label {
          type rt-types:mpls-label;
          description
            "transmit lable";
        }
        leaf receive-label {
          type rt-types:mpls-label;
          description
            "receive label";
        }
      }
      case bgp-pw {
        leaf remote-pe-id {
          type inet:ip-address;
          description
            "remote pe id";
        }
      }
      case bgp-ad-pw {
        leaf remote-ve-id {
          type uint16;
          description
            "remote ve id";
        }
      }
    }
  }

  augment "/ncs:devices/ncs:device/ncs:config" {
    container pseudowires {
      tailf:ncs-device-type "netconf";
      tailf:display-when "not(../../ncs:module) or ../../ncs:module[ncs:name='ietf-pseudowires']";
      description
        "Configuration management of pseudowires";
      list pseudowire {
        key "name";
        description
          "A pseudowire";
        leaf name {
          type string;
          description
            "pseudowire name";
        }
        // NCS drop config false leaf state
        leaf template {
          type pw-template-ref;
          description
            "pseudowire template";
        }
        leaf mtu {
          type uint16;
          description
            "PW MTU";
        }
        leaf mac-withdraw {
          type boolean;
          default "false";
          description
            "Enable (true) or disable (false) MAC withdraw";
        }
        leaf cw-negotiation {
          type cw-negotiation-type;
          description
            "cw-negotiation";
        }
        leaf tunnel-policy {
          type string;
          description
            "tunnel policy name";
        }
        choice pw-type {
          description
            "A choice of pseudowire type";
          case configured-pw {
            container configured-pw {
              description
                "LDP or static pseudowire that requires manual configuration";
              leaf peer-ip {
                type inet:ip-address;
                description
                  "peer IP address";
              }
              leaf pw-id {
                type uint32;
                description
                  "pseudowire id";
              }
              leaf icb {
                type boolean;
                description
                  "inter-chassis backup";
              }
              leaf transmit-label {
                type rt-types:mpls-label;
                description
                  "transmit lable";
              }
              leaf receive-label {
                type rt-types:mpls-label;
                description
                  "receive label";
              }
            }
          }
        }
      }
      container pw-templates {
        description
          "pw-templates";
        list pw-template {
          key "name";
          description
            "pw-template";
          leaf name {
            type string;
            description
              "name";
          }
          leaf mtu {
            type uint16;
            description
              "pseudowire mtu";
          }
          leaf cw-negotiation {
            type cw-negotiation-type;
            default "preferred";
            description
              "control-word negotiation preference";
          }
          leaf tunnel-policy {
            type string;
            description
              "tunnel policy name";
          }
        }
      }
    }
  }
  augment "/ncs:devices/ncs:device/ncs:live-status" {
    container pseudowires {
      tailf:ncs-device-type "netconf";
      tailf:display-when "not(../../ncs:module) or ../../ncs:module[ncs:name='ietf-pseudowires'] or (../../ncs:live-status-protocol[not(ncs:capability)]) or (../../ncs:live-status-protocol/ncs:capability/ncs:module[.='ietf-pseudowires'])";
      description
        "Configuration management of pseudowires";
      list pseudowire {
        key "name";
        description
          "A pseudowire";
        leaf name {
          type string;
          description
            "pseudowire name";
        }
        leaf state {
          type live_ncs_pseudowire-status-type;
          description
            "pseudowire operation status";
          reference "RFC 4446 and IANA Pseudowire Status Codes Registery";
        }
        leaf template {
          type live_ncs_pw-template-ref;
          description
            "pseudowire template";
        }
        leaf mtu {
          type uint16;
          description
            "PW MTU";
        }
        leaf mac-withdraw {
          type boolean;
          // NCS drop default statement
          description
            "Enable (true) or disable (false) MAC withdraw";
        }
        leaf cw-negotiation {
          type live_ncs_cw-negotiation-type;
          description
            "cw-negotiation";
        }
        leaf tunnel-policy {
          type string;
          description
            "tunnel policy name";
        }
        choice pw-type {
          description
            "A choice of pseudowire type";
          case configured-pw {
            container configured-pw {
              description
                "LDP or static pseudowire that requires manual configuration";
              leaf peer-ip {
                type inet:ip-address;
                description
                  "peer IP address";
              }
              leaf pw-id {
                type uint32;
                description
                  "pseudowire id";
              }
              leaf icb {
                type boolean;
                description
                  "inter-chassis backup";
              }
              leaf transmit-label {
                type rt-types:live_ncs_mpls-label;
                description
                  "transmit lable";
              }
              leaf receive-label {
                type rt-types:live_ncs_mpls-label;
                description
                  "receive label";
              }
            }
          }
        }
      }
      container pw-templates {
        description
          "pw-templates";
        list pw-template {
          key "name";
          description
            "pw-template";
          leaf name {
            type string;
            description
              "name";
          }
          leaf mtu {
            type uint16;
            description
              "pseudowire mtu";
          }
          leaf cw-negotiation {
            type live_ncs_cw-negotiation-type;
            // NCS drop default statement
            description
              "control-word negotiation preference";
          }
          leaf tunnel-policy {
            type string;
            description
              "tunnel policy name";
          }
        }
      }
    }
  }
  augment "/ncs:devices/ncs:template/ncs:ned-id/ncs:config" {
    container pseudowires {
      description
        "Configuration management of pseudowires";
      list pseudowire {
        // NCS patched for predictable order
        ordered-by user;
        key "name";
        description
          "A pseudowire";
        leaf name {
          type string;
          description
            "pseudowire name";
        }
        // NCS drop config false leaf state
        leaf template {
          type ncs_template_pw-template-ref;
          description
            "pseudowire template";
        }
        leaf mtu {
          type string;
          description
            "PW MTU";
        }
        leaf mac-withdraw {
          type string;
          // NCS drop default statement
          description
            "Enable (true) or disable (false) MAC withdraw";
        }
        leaf cw-negotiation {
          type ncs_template_cw-negotiation-type;
          description
            "cw-negotiation";
        }
        leaf tunnel-policy {
          type string;
          description
            "tunnel policy name";
        }
        choice pw-type {
          description
            "A choice of pseudowire type";
          case configured-pw {
            container configured-pw {
              description
                "LDP or static pseudowire that requires manual configuration";
              leaf peer-ip {
                type string;
                description
                  "peer IP address";
              }
              leaf pw-id {
                type string;
                description
                  "pseudowire id";
              }
              leaf icb {
                type string;
                description
                  "inter-chassis backup";
              }
              leaf transmit-label {
                type rt-types:ncs_template_mpls-label;
                description
                  "transmit lable";
              }
              leaf receive-label {
                type rt-types:ncs_template_mpls-label;
                description
                  "receive label";
              }
            }
          }
        }
      }
      container pw-templates {
        description
          "pw-templates";
        list pw-template {
          // NCS patched for predictable order
          ordered-by user;
          key "name";
          description
            "pw-template";
          leaf name {
            type string;
            description
              "name";
          }
          leaf mtu {
            type string;
            description
              "pseudowire mtu";
          }
          leaf cw-negotiation {
            type ncs_template_cw-negotiation-type;
            // NCS drop default statement
            description
              "control-word negotiation preference";
          }
          leaf tunnel-policy {
            type string;
            description
              "tunnel policy name";
          }
        }
      }
    }
  }
}
