module yumaworks-internal {
  // Generated by yanger -t ncs
  tailf:mount-id "saos1051-nc-1.0:saos1051-nc-1.0";
  tailf:ncs-device-type "netconf";

  namespace "http://yumaworks.com/ns/yumaworks-internal";
  prefix yint;

  import yuma-ncx {
    prefix ncx;
  }
  import tailf-common {
    prefix tailf;
  }
  import tailf-ncs {
    prefix ncs;
  }

  organization
    "YumaWorks, Inc.";
  contact
    "Support <support at yumaworks.com>";
  description
    "Internal definitions used by the netconfd-pro server.

     Copyright (c) 2019, YumaWorks, Inc. All rights reserved.

     Redistribution and use in source and binary forms, with or
     without modification, is permitted pursuant to, and subject
     to the license terms contained in, the BSD 3-Clause License
     http://opensource.org/licenses/BSD-3-Clause";

  revision 2019-01-22 {
    description
      "Initial version";
  }

  augment "/ncs:devices/ncs:device/ncs:rpc" {
    container rpc-replay-config {
      tailf:ncs-device-type "netconf";
      tailf:display-when "not(../../ncs:module) or ../../ncs:module[ncs:name='yumaworks-internal']";
      tailf:action replay-config {
        tailf:actionpoint ncsproxy {
          tailf:internal;
        }
        ncx:hidden;
        ncx:abstract;
        description
          "Replay the running config for SIL components that have
           reset during operation.";
      }
    }
  }
  augment "/ncs:devices/ncs:device-group/ncs:ned-id/ncs:rpc" {
    container rpc-replay-config {
      tailf:ncs-device-type "netconf";
      tailf:display-when "/ncs:devices/ncs:device[ncs:name=current()/../../../ncs:member]/ncs:module[ncs:name='yumaworks-internal']";
      tailf:action replay-config {
        tailf:actionpoint ncsproxy {
          tailf:internal;
        }
        ncx:hidden;
        ncx:abstract;
        description
          "Replay the running config for SIL components that have
           reset during operation.";
      }
    }
  }
}
