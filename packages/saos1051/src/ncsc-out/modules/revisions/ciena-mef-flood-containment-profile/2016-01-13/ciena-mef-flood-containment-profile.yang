module ciena-mef-flood-containment-profile {
  // Generated by yanger -t ncs
  tailf:mount-id "saos1051-nc-1.0:saos1051-nc-1.0";
  tailf:ncs-device-type "netconf";

  namespace "urn:ciena:params:xml:ns:yang:ciena-pn:ciena-mef-flood-containment-profile";
  prefix mef-fc;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's configuration of
     the Flood Containment Profile.";

  revision 2016-01-13 {
    description
      "Initial revision";
  }

  typedef ncs_template_flood-containment-profile-ref {
    type string;
    description
      "This type is used by the data models that need to reference
       configured Flood Containment Profiles.";
  }

  typedef ncs_rpc_notif_flood-containment-profile-ref {
    type string;
    description
      "This type is used by the data models that need to reference
       configured Flood Containment Profiles.";
  }

  typedef live_ncs_flood-containment-profile-ref {
    type leafref {
      path "/ncs:devices/ncs:device/ncs:live-status/mef-fc:flood-containment-profiles/mef-fc:flood-containment-profile/mef-fc:name" {
        tailf:xpath-root 3;
      }
    }
    description
      "This type is used by the data models that need to reference
       configured Flood Containment Profiles.";
  }

  typedef flood-containment-profile-ref {
    type leafref {
      path "/ncs:devices/ncs:device/ncs:config/mef-fc:flood-containment-profiles/mef-fc:flood-containment-profile/mef-fc:name" {
        tailf:xpath-root 3;
      }
    }
    description
      "This type is used by the data models that need to reference
       configured Flood Containment Profiles.";
  }

  augment "/ncs:devices/ncs:device/ncs:config" {
    container flood-containment-profiles {
      tailf:ncs-device-type "netconf";
      tailf:display-when "not(../../ncs:module) or ../../ncs:module[ncs:name='ciena-mef-flood-containment-profile']";
      description
        "List of flood-containment-profile templates. Flood containment profiles can be referenced by various entities (flow-point/logical-port etc.)
         to instantiate flood containment meters based on traffic type.";
      list flood-containment-profile {
        key "name";
        leaf name {
          type string {
            length "1..1024";
          }
          description
            "An administratively assigned string, which may be used
             to identify the profile.";
        }
        leaf description {
          type string;
          description
            "This is a user-defined string used to describe the profile.";
        }
        list containment {
          key "frame-type";
          leaf frame-type {
            type bits {
              bit unknown-unicast;
              bit unknown-l2-multicast;
              bit unknown-ip-multicast;
              bit known-multicast;
              bit broadcast;
            }
            description
              "The frame types to be contained with the given rate.";
          }
          leaf rate {
            type uint64;
            description
              "Data rate in kbps.";
          }
        }
      }
    }
  }
  augment "/ncs:devices/ncs:device/ncs:live-status" {
    container flood-containment-profiles {
      tailf:ncs-device-type "netconf";
      tailf:display-when "not(../../ncs:module) or ../../ncs:module[ncs:name='ciena-mef-flood-containment-profile'] or (../../ncs:live-status-protocol[not(ncs:capability)]) or (../../ncs:live-status-protocol/ncs:capability/ncs:module[.='ciena-mef-flood-containment-profile'])";
      description
        "List of flood-containment-profile templates. Flood containment profiles can be referenced by various entities (flow-point/logical-port etc.)
         to instantiate flood containment meters based on traffic type.";
      list flood-containment-profile {
        key "name";
        leaf name {
          type string {
            length "1..1024";
          }
          description
            "An administratively assigned string, which may be used
             to identify the profile.";
        }
        leaf description {
          type string;
          description
            "This is a user-defined string used to describe the profile.";
        }
        list containment {
          key "frame-type";
          leaf frame-type {
            type bits {
              bit unknown-unicast;
              bit unknown-l2-multicast;
              bit unknown-ip-multicast;
              bit known-multicast;
              bit broadcast;
            }
            description
              "The frame types to be contained with the given rate.";
          }
          leaf rate {
            type uint64;
            description
              "Data rate in kbps.";
          }
        }
      }
    }
  }
  augment "/ncs:devices/ncs:template/ncs:ned-id/ncs:config" {
    container flood-containment-profiles {
      description
        "List of flood-containment-profile templates. Flood containment profiles can be referenced by various entities (flow-point/logical-port etc.)
         to instantiate flood containment meters based on traffic type.";
      list flood-containment-profile {
        // NCS patched for predictable order
        ordered-by user;
        key "name";
        leaf name {
          type string;
          description
            "An administratively assigned string, which may be used
             to identify the profile.";
        }
        leaf description {
          type string;
          description
            "This is a user-defined string used to describe the profile.";
        }
        list containment {
          // NCS patched for predictable order
          ordered-by user;
          key "frame-type";
          leaf frame-type {
            type string;
            description
              "The frame types to be contained with the given rate.";
          }
          leaf rate {
            type string;
            description
              "Data rate in kbps.";
          }
        }
      }
    }
  }
}
