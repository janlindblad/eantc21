module ciena-packet-xcvr-modem {
  // Generated by yanger -t ncs
  tailf:mount-id "saos1051-nc-1.0:saos1051-nc-1.0";
  tailf:ncs-device-type "netconf";

  namespace "http://www.ciena.com/ns/yang/ciena-packet-xcvr-modem";
  prefix xcvr-modem;

  import ciena-packet-typedefs {
    prefix cntypes;
  }
  import ciena-packet-xcvr {
    prefix xcvr;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's XCVR modem specific data for the NETCONF protocol. It will augment the ciena-packet-xcvr module.";

  revision 2018-05-17 {
    description
      "Based off of ciena-waveserver-xcvr-modem.yang";
  }

  augment "/ncs:devices/ncs:device/ncs:live-status/xcvr:xcvrs/xcvr:xcvr/xcvr:properties/xcvr:vendor-data/xcvr:properties/xcvr:diagnostic-monitoring" {
    // NCS drop when statement
    description
      "XCVR vendor diagnostic-monitoring properties specific to modem XCVRs.";
    leaf diagnostic-support {
      tailf:ncs-device-type "netconf";
      tailf:display-when "not(../../../../../../../../ncs:module) or ../../../../../../../../ncs:module[ncs:name='ciena-packet-xcvr-modem'] or (../../../../../../../../ncs:live-status-protocol[not(ncs:capability)]) or (../../../../../../../../ncs:live-status-protocol/ncs:capability/ncs:module[.='ciena-packet-xcvr-modem'])";
      type cntypes:live_ncs_yes-no-enum;
      description
        "Diagnostic Monitoring, is Diagnostic Support turned on.";
    }
    leaf dispersion-measurement {
      tailf:ncs-device-type "netconf";
      tailf:display-when "not(../../../../../../../../ncs:module) or ../../../../../../../../ncs:module[ncs:name='ciena-packet-xcvr-modem'] or (../../../../../../../../ncs:live-status-protocol[not(ncs:capability)]) or (../../../../../../../../ncs:live-status-protocol/ncs:capability/ncs:module[.='ciena-packet-xcvr-modem'])";
      type cntypes:live_ncs_yes-no-enum;
      description
        "Diagnostic Monitoring, is Dispersion Measurement turned on.";
    }
  }
  augment "/ncs:devices/ncs:device/ncs:live-status/xcvr:xcvrs/xcvr:xcvr/xcvr:properties/xcvr:vendor-data/xcvr:properties" {
    description
      "XCVR vendor properties specific to modem XCVRs.";
    container transmitter-technology {
      tailf:ncs-device-type "netconf";
      tailf:display-when "not(../../../../../../../ncs:module) or ../../../../../../../ncs:module[ncs:name='ciena-packet-xcvr-modem'] or (../../../../../../../ncs:live-status-protocol[not(ncs:capability)]) or (../../../../../../../ncs:live-status-protocol/ncs:capability/ncs:module[.='ciena-packet-xcvr-modem'])";
      description
        "Modem Transmitter Technology properties/capabilities.";
      leaf tunable {
        type cntypes:live_ncs_yes-no-enum;
        description
          "Modem Transmitter Technology, Tunable.";
      }
      leaf wavelength-min {
        type cntypes:live_ncs_decimal-2-dig;
        units "nm";
        description
          "Modem Transmitter Technology, Wavelength Min value, in nanometers.";
      }
      leaf wavelength-max {
        type cntypes:live_ncs_decimal-2-dig;
        units "nm";
        description
          "Modem Transmitter Technology, Wavelength Max value, in nanometers.";
      }
      leaf frequency-min {
        type cntypes:live_ncs_modem-frequency;
        units "GHz";
        description
          "Modem Transmitter Technology, minimum supported frequency, in GHz.";
      }
      leaf frequency-max {
        type cntypes:live_ncs_modem-frequency;
        units "GHz";
        description
          "Modem Transmitter Technology, maximum supported frequency, in GHz.";
      }
      leaf frequency-resolution {
        type uint32;
        units "MHz";
        description
          "Modem Transmitter Technology, frequency resolution, in MHz.";
      }
      leaf tx-dispersion-min {
        type int32;
        units "ps/nm";
        description
          "Modem Transmitter Technology, Tx Dispersion Min (ps/nm).";
      }
      leaf tx-dispersion-max {
        type int32;
        units "ps/nm";
        description
          "Modem Transmitter Technology, Tx Dispersion Max (ps/nm).";
      }
      leaf edfa {
        type cntypes:live_ncs_yes-no-enum;
        description
          "Whether this modem is an EDFA modem.";
      }
      leaf c-band {
        type cntypes:live_ncs_yes-no-enum;
        description
          "Whether this modem supports C-Band frequencies.";
      }
      leaf l-band {
        type cntypes:live_ncs_yes-no-enum;
        description
          "Whether this modem supports L-Band frequencies.";
      }
    }
  }
  augment "/ncs:devices/ncs:device/ncs:live-status/xcvr:xcvrs/xcvr:xcvr/xcvr:properties/xcvr:vendor-data/xcvr:properties/xcvr:supported-modes" {
    // NCS drop when statement
    description
      "XCVR supported-mode properties specific to modem XCVRs.";
    leaf default-link-optimization-mode {
      tailf:ncs-device-type "netconf";
      tailf:display-when "not(../../../../../../../../ncs:module) or ../../../../../../../../ncs:module[ncs:name='ciena-packet-xcvr-modem'] or (../../../../../../../../ncs:live-status-protocol[not(ncs:capability)]) or (../../../../../../../../ncs:live-status-protocol/ncs:capability/ncs:module[.='ciena-packet-xcvr-modem'])";
      type cntypes:live_ncs_link-optimization-mode;
      description
        "The default link optimization mode for this XCVR mode.";
    }
    leaf supported-link-optimization-modes {
      tailf:ncs-device-type "netconf";
      tailf:display-when "not(../../../../../../../../ncs:module) or ../../../../../../../../ncs:module[ncs:name='ciena-packet-xcvr-modem'] or (../../../../../../../../ncs:live-status-protocol[not(ncs:capability)]) or (../../../../../../../../ncs:live-status-protocol/ncs:capability/ncs:module[.='ciena-packet-xcvr-modem'])";
      type cntypes:live_ncs_supported-link-optimization-modes;
      description
        "The set of supported link optimization modes for this XCVR mode.";
    }
  }
  augment "/ncs:devices/ncs:device/ncs:live-status/xcvr:xcvrs/xcvr:xcvr/xcvr:properties/xcvr:diagnostics/xcvr:device" {
    description
      "XCVR device diagnostic properties specific to modem XCVRs.";
    container equipment-status {
      tailf:ncs-device-type "netconf";
      tailf:display-when "not(../../../../../../../ncs:module) or ../../../../../../../ncs:module[ncs:name='ciena-packet-xcvr-modem'] or (../../../../../../../ncs:live-status-protocol[not(ncs:capability)]) or (../../../../../../../ncs:live-status-protocol/ncs:capability/ncs:module[.='ciena-packet-xcvr-modem'])";
      description
        "XCVR modem equipment status properties.";
      leaf transmitter-state {
        type cntypes:live_ncs_enabled-disabled-enum;
        description
          "Transmitter State of the Modem.";
      }
      leaf equipment-out-of-spec {
        type cntypes:live_ncs_yes-no-enum;
        description
          "Is the alarm associated with Equipment Out of Spec raised.";
      }
      leaf temperature-critical {
        type cntypes:live_ncs_yes-no-enum;
        description
          "Is there a critical temperature alarm currently raised.";
      }
      leaf temperature-warning {
        type cntypes:live_ncs_yes-no-enum;
        description
          "Is there a temperature warning currently raised.";
      }
      leaf equipment-failure {
        type cntypes:live_ncs_yes-no-enum;
        description
          "Is the alarm associated with Equipment Failure raised.";
      }
      leaf data-link-suspect {
        type cntypes:live_ncs_yes-no-enum;
        description
          "Is the alarm associated with Data Link Suspect raised.";
      }
      leaf comms-link-suspect {
        type cntypes:live_ncs_yes-no-enum;
        description
          "Is the alarm associated with Comms Link Suspect raised.";
      }
      leaf clock-suspect {
        type cntypes:live_ncs_yes-no-enum;
        description
          "Is the alarm associated with Clock Suspect raised.";
      }
      leaf loss-of-synchronization-tick {
        type cntypes:live_ncs_yes-no-enum;
        description
          "Is the alarm associated with Loss of Synchronization Tick raised.";
      }
    }
  }
}
