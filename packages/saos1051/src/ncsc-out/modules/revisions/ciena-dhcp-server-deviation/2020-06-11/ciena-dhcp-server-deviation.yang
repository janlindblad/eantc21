module ciena-dhcp-server-deviation {
  // Generated by yanger -t ncs
  tailf:mount-id "saos1051-nc-1.0:saos1051-nc-1.0";
  tailf:ncs-device-type "netconf";

  namespace "http://www.ciena.com/dhcpServer/yang/ciena-dhcp-server-dev";
  prefix cds-dev;

  import ciena-dhcp-server {
    prefix cds;
  }
  import tailf-common {
    prefix tailf;
  }
  import tailf-ncs {
    prefix ncs;
  }

  revision 2020-06-11 {
    description
      "Initial Revision";
  }

  deviation "/ncs:devices/ncs:template/ncs:ned-id/ncs:config/cds:dhcp-server/cds:dhcp-ip-pool/cds:lease-time" {
    deviate not-supported;
  }
  deviation "/ncs:devices/ncs:device/ncs:live-status/cds:dhcp-server/cds:dhcp-ip-pool/cds:lease-time" {
    deviate not-supported;
  }
  deviation "/ncs:devices/ncs:device/ncs:config/cds:dhcp-server/cds:dhcp-ip-pool/cds:lease-time" {
    deviate not-supported;
  }
  deviation "/ncs:devices/ncs:template/ncs:ned-id/ncs:config/cds:dhcp-server/cds:dhcp-ip-pool/cds:manual-allocation" {
    deviate not-supported;
  }
  deviation "/ncs:devices/ncs:device/ncs:live-status/cds:dhcp-server/cds:dhcp-ip-pool/cds:manual-allocation" {
    deviate not-supported;
  }
  deviation "/ncs:devices/ncs:device/ncs:config/cds:dhcp-server/cds:dhcp-ip-pool/cds:manual-allocation" {
    deviate not-supported;
  }
  deviation "/ncs:devices/ncs:template/ncs:ned-id/ncs:config/cds:dhcp-server/cds:dhcp-ip-pool/cds:option" {
    deviate not-supported;
  }
  deviation "/ncs:devices/ncs:device/ncs:live-status/cds:dhcp-server/cds:dhcp-ip-pool/cds:option" {
    deviate not-supported;
  }
  deviation "/ncs:devices/ncs:device/ncs:config/cds:dhcp-server/cds:dhcp-ip-pool/cds:option" {
    deviate not-supported;
  }
  deviation "/ncs:devices/ncs:device/ncs:live-status/cds:dhcp-server-state/cds:dhcp-ip-pool/cds:packet-statistics" {
    deviate not-supported;
  }
  deviation "/ncs:devices/ncs:device/ncs:rpc/cds:rpc-clean-dhcp-server-statistics/cds:clean-dhcp-server-statistics" {
    deviate not-supported;
  }
}
