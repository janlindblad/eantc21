module ciena-evpn {
  // Generated by yanger -t ncs
  tailf:mount-id "saos1051-nc-1.0:saos1051-nc-1.0";
  tailf:ncs-device-type "netconf";

  namespace "http://ciena.com/ns/yang/ciena-evpn";
  prefix cnevpn;

  import ietf-inet-types {
    prefix inet;
  }
  import ietf-routing-types {
    prefix rt-types;
  }
  import ietf-ethernet-segment {
    prefix es;
  }
  import ietf-yang-types {
    prefix yang;
  }
  import ciena-mef-fd {
    prefix mef-fd;
  }
  import ciena-mef-logical-port {
    prefix mef-logical-port;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This module contains the Ciena proprietary EVPN YANG module.
     Copyright (c) 2020 Ciena Corporation.  All rights reserved.

     All information contained herein is, and remains
     the property of Ciena Corporation. Dissemination of this
     information or reproduction of this material is strictly
     forbidden unless prior written permission is obtained from
     Ciena Corporation.";

  revision 2020-02-20 {
    description
      "Merged with Ethernet Segment and FXC Yang models.";
    reference "";
  }
  revision 2019-03-21 {
    description
      "Initial version";
    reference "";
  }

  typedef ncs_template_cn-service-type {
    type string;
    description
      "Indicates the service type of the evpn instance";
  }

  typedef ncs_template_fxc-service-type {
    type string;
    description
      "Indicates the service type of the flexible cross-connect";
  }

  typedef ncs_template_stats-collection-type {
    type string;
  }

  typedef ncs_template_ciena-route-distinguisher-type-0 {
    type string;
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       0:2-octet-asn:4-octet-number

       Valid example is: 0:100:100.";
    reference "RFC4364: BGP/MPLS IP Virtual Private Networks (VPNs).";
  }

  typedef ncs_template_ciena-route-distinguisher-type-1 {
    type string;
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       1:4-octet-ipv4addr:2-octet-number
       2:4-octet-asn:2-octet-number.

       Currently we only support type 1, valid example is: 1:1.1.1.1:100.
       Invalid examples are: 0:100:100 and 2:1234567890:203.";
    reference "RFC4364: BGP/MPLS IP Virtual Private Networks (VPNs).";
  }

  typedef ncs_template_ciena-route-distinguisher-type-2 {
    type string;
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       2:4-octet-asn:2-octet-number.

       Valid example is: 2:1234567890:203.";
    reference "RFC4364: BGP/MPLS IP Virtual Private Networks (VPNs).";
  }

  typedef ncs_template_ciena-ethernet-segment-identifier-type {
    type string;
    description
      "The 9-octet Ethernet Segment Identifier (ESI) Value,
       ex: 5a:5a:5a:5a:5a:5a:5a:5a:5a
       The header indicating the type will be appended
       separately for the user.
       ex: 03:5a:5a:5a:5a:5a:5a:5a:5a:5a";
    reference "RFC7432: BGP MPLS-Based Ethernet VPN.";
  }

  typedef ncs_template_oper-status-type {
    type string;
    description
      "Indicates the oper status of the instance";
  }

  typedef ncs_template_active-mode-type {
    type string;
    description
      "Indicates the active-mode-type of the ethernet segment instance";
  }

  typedef ncs_template_ethernet-segment-identifier-auto-derive-type {
    type string;
  }

  typedef ncs_rpc_notif_cn-service-type {
    type enumeration {
      enum "vlan-based" {
        value 1;
        description
          "VLAN based service.";
      }
      enum "vlan-bundle" {
        value 2;
        description
          "VLAN bundle based service";
      }
      enum "port-based" {
        value 3;
        description
          "Port based service.";
      }
    }
    description
      "Indicates the service type of the evpn instance";
  }

  typedef ncs_rpc_notif_fxc-service-type {
    type enumeration {
      enum "vlan-unaware" {
        value 0;
        description
          "VLAN unaware service.";
      }
      enum "vlan-aware" {
        value 1;
        description
          "VLAN aware service";
      }
      enum "vpws" {
        value 2;
        description
          "EVPN Virtual Private Wire Service (VPWS)";
      }
    }
    description
      "Indicates the service type of the flexible cross-connect";
  }

  typedef ncs_rpc_notif_stats-collection-type {
    type enumeration {
      enum "enable" {
        value 0;
        description
          "Enable Statistics Collection";
      }
      enum "disable" {
        value 1;
        description
          "Disable Statistics Collection";
      }
    }
  }

  typedef ncs_rpc_notif_ciena-route-distinguisher-type-0 {
    type string {
      pattern '((6553[0-5]|655[0-2]\d|65[0-4]\d{2}|6[0-4]\d{3}|[0-5]?\d{0,3}\d):(429496729[0-5]|42949672[0-8]\d|4294967[01]\d{2}|429496[0-6]\d{3}|42949[0-5]\d{4}|4294[0-8]\d{5}|429[0-3]\d{6}|42[0-8]\d{7}|4[01]\d{8}|[0-3]?\d{0,8}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       0:2-octet-asn:4-octet-number

       Valid example is: 0:100:100.";
    reference "RFC4364: BGP/MPLS IP Virtual Private Networks (VPNs).";
  }

  typedef ncs_rpc_notif_ciena-route-distinguisher-type-1 {
    type string {
      pattern '(((([0-9]|[1-9][0-9]|1[0-9]{2}|2[0-4][0-9]|25[0-5])\.){3}([0-9]|[1-9][0-9]|1[0-9]{2}|2[0-4][0-9]|25[0-5])):(6553[0-5]|655[0-2][0-9]|65[0-4][0-9]{2}|6[0-4][0-9]{3}|[1-5][0-9]{4}|[1-9][0-9]{0,3}|0))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       1:4-octet-ipv4addr:2-octet-number
       2:4-octet-asn:2-octet-number.

       Currently we only support type 1, valid example is: 1:1.1.1.1:100.
       Invalid examples are: 0:100:100 and 2:1234567890:203.";
    reference "RFC4364: BGP/MPLS IP Virtual Private Networks (VPNs).";
  }

  typedef ncs_rpc_notif_ciena-route-distinguisher-type-2 {
    type string {
      pattern '((429496729[0-5]|42949672[0-8]\d|4294967[01]\d{2}|429496[0-6]\d{3}|42949[0-5]\d{4}|4294[0-8]\d{5}|429[0-3]\d{6}|42[0-8]\d{7}|4[01]\d{8}|[0-3]?\d{0,8}\d):(6553[0-5]|655[0-2]\d|65[0-4]\d{2}|6[0-4]\d{3}|[0-5]?\d{0,3}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       2:4-octet-asn:2-octet-number.

       Valid example is: 2:1234567890:203.";
    reference "RFC4364: BGP/MPLS IP Virtual Private Networks (VPNs).";
  }

  typedef ncs_rpc_notif_ciena-ethernet-segment-identifier-type {
    type string {
      pattern '(([0-9a-fA-F]{2}:){8}([0-9a-fA-F]{2}))';
    }
    description
      "The 9-octet Ethernet Segment Identifier (ESI) Value,
       ex: 5a:5a:5a:5a:5a:5a:5a:5a:5a
       The header indicating the type will be appended
       separately for the user.
       ex: 03:5a:5a:5a:5a:5a:5a:5a:5a:5a";
    reference "RFC7432: BGP MPLS-Based Ethernet VPN.";
  }

  typedef ncs_rpc_notif_oper-status-type {
    type enumeration {
      enum "up" {
        value 0;
        description
          "Instance is up.";
      }
      enum "down" {
        value 1;
        description
          "Instance is down";
      }
    }
    description
      "Indicates the oper status of the instance";
  }

  typedef ncs_rpc_notif_active-mode-type {
    type enumeration {
      enum "single-active-mode" {
        value 0;
        description
          "single-active-mode";
      }
      enum "all-active-mode" {
        value 1;
        description
          "all-active-mode";
      }
    }
    description
      "Indicates the active-mode-type of the ethernet segment instance";
  }

  typedef ncs_rpc_notif_ethernet-segment-identifier-auto-derive-type {
    type enumeration {
      enum "true" {
        value 1;
      }
    }
  }

  typedef live_ncs_cn-service-type {
    type enumeration {
      enum "vlan-based" {
        value 1;
        description
          "VLAN based service.";
      }
      enum "vlan-bundle" {
        value 2;
        description
          "VLAN bundle based service";
      }
      enum "port-based" {
        value 3;
        description
          "Port based service.";
      }
    }
    description
      "Indicates the service type of the evpn instance";
  }

  typedef live_ncs_fxc-service-type {
    type enumeration {
      enum "vlan-unaware" {
        value 0;
        description
          "VLAN unaware service.";
      }
      enum "vlan-aware" {
        value 1;
        description
          "VLAN aware service";
      }
      enum "vpws" {
        value 2;
        description
          "EVPN Virtual Private Wire Service (VPWS)";
      }
    }
    description
      "Indicates the service type of the flexible cross-connect";
  }

  typedef live_ncs_stats-collection-type {
    type enumeration {
      enum "enable" {
        value 0;
        description
          "Enable Statistics Collection";
      }
      enum "disable" {
        value 1;
        description
          "Disable Statistics Collection";
      }
    }
  }

  typedef live_ncs_ciena-route-distinguisher-type-0 {
    type string {
      pattern '((6553[0-5]|655[0-2]\d|65[0-4]\d{2}|6[0-4]\d{3}|[0-5]?\d{0,3}\d):(429496729[0-5]|42949672[0-8]\d|4294967[01]\d{2}|429496[0-6]\d{3}|42949[0-5]\d{4}|4294[0-8]\d{5}|429[0-3]\d{6}|42[0-8]\d{7}|4[01]\d{8}|[0-3]?\d{0,8}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       0:2-octet-asn:4-octet-number

       Valid example is: 0:100:100.";
    reference "RFC4364: BGP/MPLS IP Virtual Private Networks (VPNs).";
  }

  typedef live_ncs_ciena-route-distinguisher-type-1 {
    type string {
      pattern '(((([0-9]|[1-9][0-9]|1[0-9]{2}|2[0-4][0-9]|25[0-5])\.){3}([0-9]|[1-9][0-9]|1[0-9]{2}|2[0-4][0-9]|25[0-5])):(6553[0-5]|655[0-2][0-9]|65[0-4][0-9]{2}|6[0-4][0-9]{3}|[1-5][0-9]{4}|[1-9][0-9]{0,3}|0))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       1:4-octet-ipv4addr:2-octet-number
       2:4-octet-asn:2-octet-number.

       Currently we only support type 1, valid example is: 1:1.1.1.1:100.
       Invalid examples are: 0:100:100 and 2:1234567890:203.";
    reference "RFC4364: BGP/MPLS IP Virtual Private Networks (VPNs).";
  }

  typedef live_ncs_ciena-route-distinguisher-type-2 {
    type string {
      pattern '((429496729[0-5]|42949672[0-8]\d|4294967[01]\d{2}|429496[0-6]\d{3}|42949[0-5]\d{4}|4294[0-8]\d{5}|429[0-3]\d{6}|42[0-8]\d{7}|4[01]\d{8}|[0-3]?\d{0,8}\d):(6553[0-5]|655[0-2]\d|65[0-4]\d{2}|6[0-4]\d{3}|[0-5]?\d{0,3}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       2:4-octet-asn:2-octet-number.

       Valid example is: 2:1234567890:203.";
    reference "RFC4364: BGP/MPLS IP Virtual Private Networks (VPNs).";
  }

  typedef live_ncs_ciena-ethernet-segment-identifier-type {
    type string {
      pattern '(([0-9a-fA-F]{2}:){8}([0-9a-fA-F]{2}))';
    }
    description
      "The 9-octet Ethernet Segment Identifier (ESI) Value,
       ex: 5a:5a:5a:5a:5a:5a:5a:5a:5a
       The header indicating the type will be appended
       separately for the user.
       ex: 03:5a:5a:5a:5a:5a:5a:5a:5a:5a";
    reference "RFC7432: BGP MPLS-Based Ethernet VPN.";
  }

  typedef live_ncs_oper-status-type {
    type enumeration {
      enum "up" {
        value 0;
        description
          "Instance is up.";
      }
      enum "down" {
        value 1;
        description
          "Instance is down";
      }
    }
    description
      "Indicates the oper status of the instance";
  }

  typedef live_ncs_active-mode-type {
    type enumeration {
      enum "single-active-mode" {
        value 0;
        description
          "single-active-mode";
      }
      enum "all-active-mode" {
        value 1;
        description
          "all-active-mode";
      }
    }
    description
      "Indicates the active-mode-type of the ethernet segment instance";
  }

  typedef live_ncs_ethernet-segment-identifier-auto-derive-type {
    type enumeration {
      enum "true" {
        value 1;
      }
    }
  }

  typedef cn-service-type {
    type enumeration {
      enum "vlan-based" {
        value 1;
        description
          "VLAN based service.";
      }
      enum "vlan-bundle" {
        value 2;
        description
          "VLAN bundle based service";
      }
      enum "port-based" {
        value 3;
        description
          "Port based service.";
      }
    }
    description
      "Indicates the service type of the evpn instance";
  }

  typedef fxc-service-type {
    type enumeration {
      enum "vlan-unaware" {
        value 0;
        description
          "VLAN unaware service.";
      }
      enum "vlan-aware" {
        value 1;
        description
          "VLAN aware service";
      }
      enum "vpws" {
        value 2;
        description
          "EVPN Virtual Private Wire Service (VPWS)";
      }
    }
    description
      "Indicates the service type of the flexible cross-connect";
  }

  typedef stats-collection-type {
    type enumeration {
      enum "enable" {
        value 0;
        description
          "Enable Statistics Collection";
      }
      enum "disable" {
        value 1;
        description
          "Disable Statistics Collection";
      }
    }
  }

  typedef ciena-route-distinguisher-type-0 {
    type string {
      pattern '((6553[0-5]|655[0-2]\d|65[0-4]\d{2}|6[0-4]\d{3}|[0-5]?\d{0,3}\d):(429496729[0-5]|42949672[0-8]\d|4294967[01]\d{2}|429496[0-6]\d{3}|42949[0-5]\d{4}|4294[0-8]\d{5}|429[0-3]\d{6}|42[0-8]\d{7}|4[01]\d{8}|[0-3]?\d{0,8}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       0:2-octet-asn:4-octet-number

       Valid example is: 0:100:100.";
    reference "RFC4364: BGP/MPLS IP Virtual Private Networks (VPNs).";
  }

  typedef ciena-route-distinguisher-type-1 {
    type string {
      pattern '(((([0-9]|[1-9][0-9]|1[0-9]{2}|2[0-4][0-9]|25[0-5])\.){3}([0-9]|[1-9][0-9]|1[0-9]{2}|2[0-4][0-9]|25[0-5])):(6553[0-5]|655[0-2][0-9]|65[0-4][0-9]{2}|6[0-4][0-9]{3}|[1-5][0-9]{4}|[1-9][0-9]{0,3}|0))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       1:4-octet-ipv4addr:2-octet-number
       2:4-octet-asn:2-octet-number.

       Currently we only support type 1, valid example is: 1:1.1.1.1:100.
       Invalid examples are: 0:100:100 and 2:1234567890:203.";
    reference "RFC4364: BGP/MPLS IP Virtual Private Networks (VPNs).";
  }

  typedef ciena-route-distinguisher-type-2 {
    type string {
      pattern '((429496729[0-5]|42949672[0-8]\d|4294967[01]\d{2}|429496[0-6]\d{3}|42949[0-5]\d{4}|4294[0-8]\d{5}|429[0-3]\d{6}|42[0-8]\d{7}|4[01]\d{8}|[0-3]?\d{0,8}\d):(6553[0-5]|655[0-2]\d|65[0-4]\d{2}|6[0-4]\d{3}|[0-5]?\d{0,3}\d))';
    }
    description
      "A route distinguisher is an 8-octet value used to distinguish
       routes from different BGP VPNs (RFC 4364). A route
       distinguisher consists of three fields: A 2-octet type field,
       an administrator field, and an assigned number field.
       According to the data formats for type 0, 1, and 2 defined in
       RFC4364, the encoding pattern is defined as:

       2:4-octet-asn:2-octet-number.

       Valid example is: 2:1234567890:203.";
    reference "RFC4364: BGP/MPLS IP Virtual Private Networks (VPNs).";
  }

  typedef ciena-ethernet-segment-identifier-type {
    type string {
      pattern '(([0-9a-fA-F]{2}:){8}([0-9a-fA-F]{2}))';
    }
    description
      "The 9-octet Ethernet Segment Identifier (ESI) Value,
       ex: 5a:5a:5a:5a:5a:5a:5a:5a:5a
       The header indicating the type will be appended
       separately for the user.
       ex: 03:5a:5a:5a:5a:5a:5a:5a:5a:5a";
    reference "RFC7432: BGP MPLS-Based Ethernet VPN.";
  }

  typedef oper-status-type {
    type enumeration {
      enum "up" {
        value 0;
        description
          "Instance is up.";
      }
      enum "down" {
        value 1;
        description
          "Instance is down";
      }
    }
    description
      "Indicates the oper status of the instance";
  }

  typedef active-mode-type {
    type enumeration {
      enum "single-active-mode" {
        value 0;
        description
          "single-active-mode";
      }
      enum "all-active-mode" {
        value 1;
        description
          "all-active-mode";
      }
    }
    description
      "Indicates the active-mode-type of the ethernet segment instance";
  }

  typedef ethernet-segment-identifier-auto-derive-type {
    type enumeration {
      enum "true" {
        value 1;
      }
    }
  }

  grouping ncs_template_cross-connect-cfg {
    description
      "Grouping for cross connect configuration.";
    leaf local-service-id {
      // NCS drop mandatory statement
      type string;
      description
        "Service ID of locally connected CE.";
    }
    leaf remote-service-id {
      type string;
      description
        "Service ID of remote CE or host behind remote CE";
    }
  }

  grouping ncs_rpc_notif_cross-connect-cfg {
    description
      "Grouping for cross connect configuration.";
    leaf local-service-id {
      mandatory true;
      type uint32 {
        range "1..16777216";
      }
      description
        "Service ID of locally connected CE.";
    }
    leaf remote-service-id {
      type uint32 {
        range "1..16777216";
      }
      description
        "Service ID of remote CE or host behind remote CE";
    }
  }

  grouping live_ncs_cross-connect-cfg {
    description
      "Grouping for cross connect configuration.";
    leaf local-service-id {
      // NCS drop mandatory statement
      type uint32 {
        range "1..16777216";
      }
      description
        "Service ID of locally connected CE.";
    }
    leaf remote-service-id {
      type uint32 {
        range "1..16777216";
      }
      description
        "Service ID of remote CE or host behind remote CE";
    }
  }

  grouping cross-connect-cfg {
    description
      "Grouping for cross connect configuration.";
    leaf local-service-id {
      mandatory true;
      type uint32 {
        range "1..16777216";
      }
      description
        "Service ID of locally connected CE.";
    }
    leaf remote-service-id {
      type uint32 {
        range "1..16777216";
      }
      description
        "Service ID of remote CE or host behind remote CE";
    }
  }

  augment "/ncs:devices/ncs:device/ncs:config" {
    container evpn {
      tailf:ncs-device-type "netconf";
      tailf:display-when "not(../../ncs:module) or ../../ncs:module[ncs:name='ciena-evpn']";
      description
        "Evpn";
      container global-route-distinguisher {
        description
          "Default Global Route Distinguisher";
        leaf route-distinguisher {
          type rt-types:route-distinguisher;
          description
            "Global Route Distinguisher";
        }
      }
      container ethernet-segments {
        description
          "Ethernet segment";
        list ethernet-segment {
          key "name";
          description
            "An ethernet segment";
          leaf name {
            type string;
            description
              "Name of the ethernet segment";
          }
          leaf logical-port {
            mandatory true;
            type mef-logical-port:logical-port-ref;
            description
              "Logical port of the ethernet segment";
          }
          leaf evlag {
            type boolean;
            default "false";
            description
              "Enable/disable EvLag on the AGG port";
          }
          container ethernet-segment-identifier {
            description
              "Ethernet Segment Identifier (ESI)";
            choice esi-type {
              mandatory true;
              description
                "Choice between different types of Ethernet Segment Identifiers (ESI)";
              case type-0 {
                container arbitrary {
                  description
                    "Ethernet Segment Identifier (ESI) that is managed and configured by user";
                  leaf arbitrary {
                    type ciena-ethernet-segment-identifier-type;
                    description
                      "9-octet arbitrary value";
                  }
                }
              }
              case type-1 {
                container lacp-based {
                  description
                    "Auto-generated ESI value determined from LACP.
                     MAC address (6 octets) + port key (2 octets) +
                     0x00 (1 octet)";
                  leaf auto-derived {
                    type ethernet-segment-identifier-auto-derive-type;
                    description
                      "Set to 'true' for auto-derived ESI.";
                  }
                }
              }
              case type-2 {
                container lan-based {
                  description
                    "Auto-generated if CE-PE connected via bridged forwarding-domain.
                     Root bridge MAC (6 octets) + priority (2 octets) +
                     0x00 (1 octet)";
                  leaf auto-derived {
                    type ethernet-segment-identifier-auto-derive-type;
                    description
                      "Set to 'true' for auto-derived ESI.";
                  }
                }
              }
              case type-3 {
                container mac-based {
                  description
                    "MAC based ESI – can be auto-generated/configured.
                     System MAC (6 octets) + Local discriminator (3 octets)";
                  leaf auto-derived {
                    type boolean;
                    description
                      "Set to 'true' for auto-derived ESI.
                       Set to 'false' for user configuration.";
                  }
                  leaf system-mac-address {
                    mandatory true;
                    type yang:mac-address;
                    description
                      "ESI System MAC (6 octets)";
                  }
                  leaf local-discriminator {
                    mandatory true;
                    type uint32;
                    description
                      "Local discriminator (3 octets)";
                  }
                }
              }
              case type-4 {
                container router-id-based {
                  description
                    "Router-ID based ESI – can be auto-generated/configured.
                     Router ID (4 octets) + Local discriminator (4 octets) + 0x00 (1 octet)";
                  leaf auto-derived {
                    type boolean;
                    description
                      "Set to 'true' for auto-derived ESI.
                       Set to 'false' for user configuration.";
                  }
                  leaf router-id {
                    type inet:ipv4-address;
                    description
                      "Router ID (4 octets)";
                  }
                  leaf local-discriminator {
                    mandatory true;
                    type uint32;
                    description
                      "Local discriminator (4 octets)";
                  }
                }
              }
              case type-5 {
                container as-based {
                  description
                    "Autonomous System (AS) based – can be auto-generated/configured.
                     AS number (4 octets) + local discriminator (4 octets) + 0x00 (1 octet)";
                  leaf auto-derived {
                    type boolean;
                    description
                      "Set to 'true' for auto-derived ESI.
                       Set to 'false' for user configuration.";
                  }
                  leaf router-id {
                    type inet:as-number;
                    description
                      "AS number (4 octets)";
                  }
                  leaf local-discriminator {
                    mandatory true;
                    type uint32;
                    description
                      "Local discriminator (4 octets)";
                  }
                }
              }
            }
          }
          leaf active-mode {
            type active-mode-type;
            default "single-active-mode";
            description
              "Choice of active mode";
          }
          container df-election {
            description
              "df-election";
            leaf df-election-method {
              type es:df-election-method-type;
              default "default";
              description
                "The DF election method";
            }
            leaf preference {
              type uint16;
              default "32767";
              description
                "The DF preference";
            }
            leaf revertive {
              type boolean;
              default "true";
              description
                "The 'preempt' or 'revertive' behavior";
            }
            leaf election-wait-time {
              type uint32 {
                range "3..max";
              }
              default "3";
              units "seconds";
              description
                "Wait time for DF election";
            }
            leaf select-high-preference {
              type boolean;
              default "true";
              description
                "Preference with higher value will be selected first";
            }
            leaf reversion-hold-time {
              type uint32 {
                range "3..max";
              }
              default "3";
              units "seconds";
              description
                "Duration before reversion";
            }
          }
          container es-import {
            leaf route-distinguisher {
              type rt-types:route-distinguisher;
              description
                "Route Distinguisher configured on EVPN";
            }
            leaf route-target {
              type rt-types:route-target;
              description
                "Route Target configured on EVPN";
            }
          }
        }
      }
      container evpn-instances {
        description
          "evpn-instances";
        list evpn-instance {
          key "id";
          description
            "An EVPN instance";
          leaf id {
            type uint32 {
              range "1..65536";
            }
            description
              "ID of EVPN instance";
          }
          choice services {
            mandatory true;
            description
              "flexible-cross-connect, vpws, vpls services";
            case flexible-cross-connect-vlan-aware-fd {
              list flexible-cross-connect-vlan-aware-fd {
                key "forwarding-domain";
                max-elements 1;
                description
                  "Forwarding-domain vlan-aware evpn-fxc service";
                leaf forwarding-domain {
                  type leafref {
                    path "/ncs:devices/ncs:device/ncs:config/mef-fd:fds/mef-fd:fd/mef-fd:name" {
                      tailf:xpath-root 3;
                    }
                  }
                  must "(/mef-fd:fds/mef-fd:fd[mef-fd:name=current()]/mef-fd:mode='fxc')" {
                    tailf:xpath-root 3;
                    error-message "Forwarding Domain mode must be set to fxc/resource is currently in use";
                  }
                  description
                    "Name of the forwarding domain";
                }
                leaf control-word {
                  type boolean;
                  default "true";
                  description
                    "The attribute enables or disables the control-word for an FXC Instance.
                     By default, the value is true.";
                }
                leaf l2mtu {
                  type uint32 {
                    range "64..65536";
                  }
                  default "1500";
                  description
                    "This attribute sets the Maximum Transmission Unit(MTU) for an FXC Instance
                     By default, the value is set to 1500.";
                }
                leaf stats-collection {
                  type stats-collection-type;
                  default "disable";
                  description
                    "Evpn Statistic Collection";
                }
              }
            }
            case point-to-point {
              list vpws-cross-connect-fd {
                key "forwarding-domain";
                description
                  "Forwarding-domain for evpn vpws service";
                leaf forwarding-domain {
                  type leafref {
                    path "/ncs:devices/ncs:device/ncs:config/mef-fd:fds/mef-fd:fd/mef-fd:name" {
                      tailf:xpath-root 3;
                    }
                  }
                  must "(/mef-fd:fds/mef-fd:fd[mef-fd:name=current()]/mef-fd:mode='evpn-vpws')" {
                    tailf:xpath-root 3;
                    error-message "Forwarding Domain mode must be set to vpws/resource is currently in use";
                  }
                  description
                    "Name of the forwarding domain";
                }
                leaf control-word {
                  type boolean;
                  default "true";
                  description
                    "The attribute enables or disables the control-word for an FXC Instance.
                     By default, the value is true.";
                }
                leaf l2mtu {
                  type uint32 {
                    range "64..65536";
                  }
                  default "1500";
                  description
                    "This attribute sets the Maximum Transmission Unit(MTU) for an FXC Instance
                     By default, the value is set to 1500.";
                }
                leaf stats-collection {
                  type stats-collection-type;
                  default "disable";
                  description
                    "Evpn Statistic Collection";
                }
                uses cross-connect-cfg;
              }
              list flexible-cross-connect-vlan-unaware-fd {
                key "forwarding-domain";
                description
                  "Vlan Unaware";
                leaf forwarding-domain {
                  type leafref {
                    path "/ncs:devices/ncs:device/ncs:config/mef-fd:fds/mef-fd:fd/mef-fd:name" {
                      tailf:xpath-root 3;
                    }
                  }
                  must "(/mef-fd:fds/mef-fd:fd[mef-fd:name=current()]/mef-fd:mode='fxc')" {
                    tailf:xpath-root 3;
                    error-message "Forwarding Domain mode must be set to fxc/resource is currently in use";
                  }
                  description
                    "Name of the forwarding domain";
                }
                leaf control-word {
                  type boolean;
                  default "true";
                  description
                    "The attribute enables or disables the control-word for an FXC Instance.
                     By default, the value is true.";
                }
                leaf l2mtu {
                  type uint32 {
                    range "64..65536";
                  }
                  default "1500";
                  description
                    "This attribute sets the Maximum Transmission Unit(MTU) for an FXC Instance
                     By default, the value is set to 1500.";
                }
                uses cnevpn:cross-connect-cfg;
              }
            }
            case vpls-fd {
              list vpls-fd {
                key "forwarding-domain";
                leaf forwarding-domain {
                  type leafref {
                    path "/ncs:devices/ncs:device/ncs:config/mef-fd:fds/mef-fd:fd/mef-fd:name" {
                      tailf:xpath-root 3;
                    }
                  }
                  must "(/mef-fd:fds/mef-fd:fd[mef-fd:name=current()]/mef-fd:mode='evpn-vpls')" {
                    tailf:xpath-root 3;
                    error-message "Forwarding Domain mode must be set to vpls/resource is currently in use";
                  }
                  description
                    "Name of the forwarding domain";
                }
              }
            }
          }
          container route-distinguisher {
            description
              "A route distinguisher is an 8-octet value used to distinguish
               routes from different BGP VPNs (RFC 4364). A route
               distinguisher consists of three fields: A 2-octet type field,
               an administrator field, and an assigned number field.
               According to the data formats for type 0, 1, and 2 defined in
               RFC4364, the encoding pattern is defined as:

               0:2-octet-asn:4-octet-number
               1:4-octet-ipv4addr:2-octet-number
               2:4-octet-asn:2-octet-number.
               2-octet-other-hex-number:6-octet-hex-number

               Some valid examples are: 100:100, 1.1.1.1:100, and 1234567890:203";
            choice rd-type {
              description
                "Choice between different types of Route Distinguishers";
              case type-0 {
                container asn-2-octet-based {
                  leaf value {
                    type ciena-route-distinguisher-type-0;
                    description
                      "2-octet-asn:4-octet-number Route Distinguisher,
                       ex: 100:100";
                  }
                }
              }
              case type-1 {
                container ip-based {
                  leaf value {
                    type ciena-route-distinguisher-type-1;
                    description
                      "4-octet-ipv4addr:2-octet-number Route Distinguisher,
                       ex: 1.1.1.1:100";
                  }
                }
              }
              case type-2 {
                container asn-4-octet-based {
                  leaf value {
                    type ciena-route-distinguisher-type-2;
                    description
                      "4-octet-asn:2-octet-number Route Distinguisher,
                       ex: 1234567890:203";
                  }
                }
              }
            }
          }
          uses rt-types:vpn-route-targets;
        }
      }
    }
    // NCS drop config false container 'evpn-ethernet-segment-state'
    // NCS drop config false container 'evpn-state'
  }
  augment "/ncs:devices/ncs:device/ncs:live-status" {
    container evpn {
      tailf:ncs-device-type "netconf";
      tailf:display-when "not(../../ncs:module) or ../../ncs:module[ncs:name='ciena-evpn'] or (../../ncs:live-status-protocol[not(ncs:capability)]) or (../../ncs:live-status-protocol/ncs:capability/ncs:module[.='ciena-evpn'])";
      description
        "Evpn";
      container global-route-distinguisher {
        description
          "Default Global Route Distinguisher";
        leaf route-distinguisher {
          type rt-types:live_ncs_route-distinguisher;
          description
            "Global Route Distinguisher";
        }
      }
      container ethernet-segments {
        description
          "Ethernet segment";
        list ethernet-segment {
          key "name";
          description
            "An ethernet segment";
          leaf name {
            type string;
            description
              "Name of the ethernet segment";
          }
          leaf logical-port {
            // NCS drop mandatory statement
            type mef-logical-port:live_ncs_logical-port-ref;
            description
              "Logical port of the ethernet segment";
          }
          leaf evlag {
            type boolean;
            // NCS drop default statement
            description
              "Enable/disable EvLag on the AGG port";
          }
          container ethernet-segment-identifier {
            description
              "Ethernet Segment Identifier (ESI)";
            choice esi-type {
              // NCS drop mandatory statement
              description
                "Choice between different types of Ethernet Segment Identifiers (ESI)";
              case type-0 {
                container arbitrary {
                  description
                    "Ethernet Segment Identifier (ESI) that is managed and configured by user";
                  leaf arbitrary {
                    type live_ncs_ciena-ethernet-segment-identifier-type;
                    description
                      "9-octet arbitrary value";
                  }
                }
              }
              case type-1 {
                container lacp-based {
                  description
                    "Auto-generated ESI value determined from LACP.
                     MAC address (6 octets) + port key (2 octets) +
                     0x00 (1 octet)";
                  leaf auto-derived {
                    type live_ncs_ethernet-segment-identifier-auto-derive-type;
                    description
                      "Set to 'true' for auto-derived ESI.";
                  }
                }
              }
              case type-2 {
                container lan-based {
                  description
                    "Auto-generated if CE-PE connected via bridged forwarding-domain.
                     Root bridge MAC (6 octets) + priority (2 octets) +
                     0x00 (1 octet)";
                  leaf auto-derived {
                    type live_ncs_ethernet-segment-identifier-auto-derive-type;
                    description
                      "Set to 'true' for auto-derived ESI.";
                  }
                }
              }
              case type-3 {
                container mac-based {
                  description
                    "MAC based ESI – can be auto-generated/configured.
                     System MAC (6 octets) + Local discriminator (3 octets)";
                  leaf auto-derived {
                    type boolean;
                    description
                      "Set to 'true' for auto-derived ESI.
                       Set to 'false' for user configuration.";
                  }
                  leaf system-mac-address {
                    // NCS drop mandatory statement
                    type yang:mac-address;
                    description
                      "ESI System MAC (6 octets)";
                  }
                  leaf local-discriminator {
                    // NCS drop mandatory statement
                    type uint32;
                    description
                      "Local discriminator (3 octets)";
                  }
                }
              }
              case type-4 {
                container router-id-based {
                  description
                    "Router-ID based ESI – can be auto-generated/configured.
                     Router ID (4 octets) + Local discriminator (4 octets) + 0x00 (1 octet)";
                  leaf auto-derived {
                    type boolean;
                    description
                      "Set to 'true' for auto-derived ESI.
                       Set to 'false' for user configuration.";
                  }
                  leaf router-id {
                    type inet:ipv4-address;
                    description
                      "Router ID (4 octets)";
                  }
                  leaf local-discriminator {
                    // NCS drop mandatory statement
                    type uint32;
                    description
                      "Local discriminator (4 octets)";
                  }
                }
              }
              case type-5 {
                container as-based {
                  description
                    "Autonomous System (AS) based – can be auto-generated/configured.
                     AS number (4 octets) + local discriminator (4 octets) + 0x00 (1 octet)";
                  leaf auto-derived {
                    type boolean;
                    description
                      "Set to 'true' for auto-derived ESI.
                       Set to 'false' for user configuration.";
                  }
                  leaf router-id {
                    type inet:as-number;
                    description
                      "AS number (4 octets)";
                  }
                  leaf local-discriminator {
                    // NCS drop mandatory statement
                    type uint32;
                    description
                      "Local discriminator (4 octets)";
                  }
                }
              }
            }
          }
          leaf active-mode {
            type live_ncs_active-mode-type;
            // NCS drop default statement
            description
              "Choice of active mode";
          }
          container df-election {
            description
              "df-election";
            leaf df-election-method {
              type es:live_ncs_df-election-method-type;
              // NCS drop default statement
              description
                "The DF election method";
            }
            leaf preference {
              type uint16;
              // NCS drop default statement
              description
                "The DF preference";
            }
            leaf revertive {
              type boolean;
              // NCS drop default statement
              description
                "The 'preempt' or 'revertive' behavior";
            }
            leaf election-wait-time {
              type uint32 {
                range "3..max";
              }
              // NCS drop default statement
              units "seconds";
              description
                "Wait time for DF election";
            }
            leaf select-high-preference {
              type boolean;
              // NCS drop default statement
              description
                "Preference with higher value will be selected first";
            }
            leaf reversion-hold-time {
              type uint32 {
                range "3..max";
              }
              // NCS drop default statement
              units "seconds";
              description
                "Duration before reversion";
            }
          }
          container es-import {
            leaf route-distinguisher {
              type rt-types:live_ncs_route-distinguisher;
              description
                "Route Distinguisher configured on EVPN";
            }
            leaf route-target {
              type rt-types:live_ncs_route-target;
              description
                "Route Target configured on EVPN";
            }
          }
        }
      }
      container evpn-instances {
        description
          "evpn-instances";
        list evpn-instance {
          key "id";
          description
            "An EVPN instance";
          leaf id {
            type uint32 {
              range "1..65536";
            }
            description
              "ID of EVPN instance";
          }
          choice services {
            // NCS drop mandatory statement
            description
              "flexible-cross-connect, vpws, vpls services";
            case flexible-cross-connect-vlan-aware-fd {
              list flexible-cross-connect-vlan-aware-fd {
                key "forwarding-domain";
                // NCS drop max-elements statement
                description
                  "Forwarding-domain vlan-aware evpn-fxc service";
                leaf forwarding-domain {
                  type leafref {
                    path "/ncs:devices/ncs:device/ncs:live-status/mef-fd:fds/mef-fd:fd/mef-fd:name" {
                      tailf:xpath-root 3;
                    }
                  }
                  // NCS drop must statement
                  description
                    "Name of the forwarding domain";
                }
                leaf control-word {
                  type boolean;
                  // NCS drop default statement
                  description
                    "The attribute enables or disables the control-word for an FXC Instance.
                     By default, the value is true.";
                }
                leaf l2mtu {
                  type uint32 {
                    range "64..65536";
                  }
                  // NCS drop default statement
                  description
                    "This attribute sets the Maximum Transmission Unit(MTU) for an FXC Instance
                     By default, the value is set to 1500.";
                }
                leaf stats-collection {
                  type live_ncs_stats-collection-type;
                  // NCS drop default statement
                  description
                    "Evpn Statistic Collection";
                }
              }
            }
            case point-to-point {
              list vpws-cross-connect-fd {
                key "forwarding-domain";
                description
                  "Forwarding-domain for evpn vpws service";
                leaf forwarding-domain {
                  type leafref {
                    path "/ncs:devices/ncs:device/ncs:live-status/mef-fd:fds/mef-fd:fd/mef-fd:name" {
                      tailf:xpath-root 3;
                    }
                  }
                  // NCS drop must statement
                  description
                    "Name of the forwarding domain";
                }
                leaf control-word {
                  type boolean;
                  // NCS drop default statement
                  description
                    "The attribute enables or disables the control-word for an FXC Instance.
                     By default, the value is true.";
                }
                leaf l2mtu {
                  type uint32 {
                    range "64..65536";
                  }
                  // NCS drop default statement
                  description
                    "This attribute sets the Maximum Transmission Unit(MTU) for an FXC Instance
                     By default, the value is set to 1500.";
                }
                leaf stats-collection {
                  type live_ncs_stats-collection-type;
                  // NCS drop default statement
                  description
                    "Evpn Statistic Collection";
                }
                uses live_ncs_cross-connect-cfg;
              }
              list flexible-cross-connect-vlan-unaware-fd {
                key "forwarding-domain";
                description
                  "Vlan Unaware";
                leaf forwarding-domain {
                  type leafref {
                    path "/ncs:devices/ncs:device/ncs:live-status/mef-fd:fds/mef-fd:fd/mef-fd:name" {
                      tailf:xpath-root 3;
                    }
                  }
                  // NCS drop must statement
                  description
                    "Name of the forwarding domain";
                }
                leaf control-word {
                  type boolean;
                  // NCS drop default statement
                  description
                    "The attribute enables or disables the control-word for an FXC Instance.
                     By default, the value is true.";
                }
                leaf l2mtu {
                  type uint32 {
                    range "64..65536";
                  }
                  // NCS drop default statement
                  description
                    "This attribute sets the Maximum Transmission Unit(MTU) for an FXC Instance
                     By default, the value is set to 1500.";
                }
                uses cnevpn:live_ncs_cross-connect-cfg;
              }
            }
            case vpls-fd {
              list vpls-fd {
                key "forwarding-domain";
                leaf forwarding-domain {
                  type leafref {
                    path "/ncs:devices/ncs:device/ncs:live-status/mef-fd:fds/mef-fd:fd/mef-fd:name" {
                      tailf:xpath-root 3;
                    }
                  }
                  // NCS drop must statement
                  description
                    "Name of the forwarding domain";
                }
              }
            }
          }
          container route-distinguisher {
            description
              "A route distinguisher is an 8-octet value used to distinguish
               routes from different BGP VPNs (RFC 4364). A route
               distinguisher consists of three fields: A 2-octet type field,
               an administrator field, and an assigned number field.
               According to the data formats for type 0, 1, and 2 defined in
               RFC4364, the encoding pattern is defined as:

               0:2-octet-asn:4-octet-number
               1:4-octet-ipv4addr:2-octet-number
               2:4-octet-asn:2-octet-number.
               2-octet-other-hex-number:6-octet-hex-number

               Some valid examples are: 100:100, 1.1.1.1:100, and 1234567890:203";
            choice rd-type {
              description
                "Choice between different types of Route Distinguishers";
              case type-0 {
                container asn-2-octet-based {
                  leaf value {
                    type live_ncs_ciena-route-distinguisher-type-0;
                    description
                      "2-octet-asn:4-octet-number Route Distinguisher,
                       ex: 100:100";
                  }
                }
              }
              case type-1 {
                container ip-based {
                  leaf value {
                    type live_ncs_ciena-route-distinguisher-type-1;
                    description
                      "4-octet-ipv4addr:2-octet-number Route Distinguisher,
                       ex: 1.1.1.1:100";
                  }
                }
              }
              case type-2 {
                container asn-4-octet-based {
                  leaf value {
                    type live_ncs_ciena-route-distinguisher-type-2;
                    description
                      "4-octet-asn:2-octet-number Route Distinguisher,
                       ex: 1234567890:203";
                  }
                }
              }
            }
          }
          uses rt-types:live_ncs_vpn-route-targets;
        }
      }
    }
    container evpn-ethernet-segment-state {
      tailf:ncs-device-type "netconf";
      tailf:display-when "not(../../ncs:module) or ../../ncs:module[ncs:name='ciena-evpn'] or (../../ncs:live-status-protocol[not(ncs:capability)]) or (../../ncs:live-status-protocol/ncs:capability/ncs:module[.='ciena-evpn'])";
      container ethernet-segments {
        description
          "ethernet-segment";
        list ethernet-segment {
          key "name";
          description
            "An ethernet segment";
          leaf name {
            type leafref {
              path "/ncs:devices/ncs:device/ncs:live-status/evpn/ethernet-segments/ethernet-segment/name" {
                tailf:xpath-root 3;
              }
            }
            description
              "Name of the ethernet segment";
          }
          leaf logical-port {
            type mef-logical-port:live_ncs_logical-port-ref;
            description
              "Logical port of the ethernet segment";
          }
          leaf ethernet-segment-identifier {
            type string;
            description
              "Ethernet segment identifier (ESI)";
          }
          leaf ethernet-segment-identifier-label {
            type uint32;
            description
              "Ethernet segment identifier label";
          }
          leaf multi-homing {
            type boolean;
            description
              "Multi-homing";
          }
          leaf active-mode {
            type live_ncs_active-mode-type;
            description
              "Single-Active or All-Active";
          }
          leaf interface-status {
            type live_ncs_oper-status-type;
            description
              "interface status: Up or Down";
          }
          leaf evlag {
            type boolean;
            description
              "Evlag status";
          }
          leaf election-wait-time {
            type uint32;
            units "seconds";
            description
              "Wait time for DF election";
          }
          leaf reversion-hold-time {
            type uint32;
            description
              "Duration before reversion";
          }
          leaf local-df-election-method {
            type string;
            description
              "The locally configured DF election method -
               default, highest random weight, or preference-based";
          }
          leaf local-df-election-method-in-use {
            type string;
            description
              "The locally in-use dynamic DF election method -
               default, highest random weight, or preference-based";
          }
          leaf local-preference {
            type uint16;
            description
              "The locally configured DF preference";
          }
          leaf local-preference-in-use {
            type uint16;
            description
              "The locally in-use dynamic DF preference";
          }
          leaf local-revertive {
            type boolean;
            description
              "The locally configured 'preempt' or 'revertive' behavior";
          }
          leaf local-revertive-in-use {
            type boolean;
            description
              "The locally in-use dynamic 'preempt' or 'revertive' behavior";
          }
          container es-import {
            leaf route-distinguisher {
              type string;
              description
                "Route Distinguisher configured on EVPN";
            }
            leaf route-target {
              type rt-types:live_ncs_route-target;
              description
                "Route Target configured on EVPN";
            }
          }
          list df {
            key "peer-ip";
            description
              "df of an evpn instance's vlan";
            leaf peer-ip {
              type inet:ip-address;
              description
                "Peer IP-address";
            }
            leaf peer-df-election-method {
              type string;
              description
                "The peer DF election method - default, highest
                 random weight, or preference-based";
            }
            leaf peer-preference {
              type uint16;
              description
                "The peer DF preference";
            }
            leaf peer-revertive {
              type boolean;
              description
                "The 'preempt' or 'revertive' behavior of the peer";
            }
          }
          list mapped-evi {
            key "evi-id";
            description
              "Mapped EVPN Instance to Ethernet Segment";
            leaf evi-id {
              type uint32;
              description
                "EVPN Instance Id";
            }
            leaf designated-forwarder {
              type string;
              description
                "Designated forwarder";
            }
            leaf local-switching-label {
              type uint32;
              description
                "Local switching label";
            }
            leaf service-type {
              type live_ncs_fxc-service-type;
              description
                "Service type of attached EVPN instance";
            }
          }
        }
      }
    }
    container evpn-state {
      tailf:ncs-device-type "netconf";
      tailf:display-when "not(../../ncs:module) or ../../ncs:module[ncs:name='ciena-evpn'] or (../../ncs:live-status-protocol[not(ncs:capability)]) or (../../ncs:live-status-protocol/ncs:capability/ncs:module[.='ciena-evpn'])";
      container evpn-instances {
        list evpn-instance {
          key "id";
          description
            "Evpn attributes";
          leaf id {
            type uint32;
            description
              "EVPN instance ID";
          }
          leaf route-distinguisher {
            type string;
            description
              "Route Distinguisher";
          }
          list vpn-target {
            key "route-target";
            description
              "Route Targets";
            leaf route-target {
              type rt-types:live_ncs_route-target;
              description
                "Route Target value";
            }
            leaf route-target-type {
              type rt-types:live_ncs_route-target-type;
              description
                "Import/export type of the route target.";
            }
          }
          list cross-connect {
            key "forwarding-domain";
            description
              "Flexible Cross Connect State";
            leaf forwarding-domain {
              type leafref {
                path "/ncs:devices/ncs:device/ncs:live-status/mef-fd:fds/mef-fd:fd/mef-fd:name" {
                  tailf:xpath-root 3;
                }
              }
              description
                "Name of the forwarding domain";
            }
            leaf service-type {
              type live_ncs_fxc-service-type;
              description
                "Service type of EVPN instance";
            }
            leaf oper-status {
              type live_ncs_oper-status-type;
              description
                "Up or Down status for EVPN Instance";
            }
            list forwarding-database {
              key "prefix next-hop-address ethernet-segment-identifier";
              description
                "Forwarding Database for EVPN";
              leaf prefix {
                type string;
                description
                  "Ethernet Tag ID";
              }
              leaf next-hop-address {
                type inet:ip-address;
                description
                  "Next hop IP address";
              }
              leaf ethernet-segment-identifier {
                type string;
                description
                  "Ethernet Segment Identifier (ESI)";
              }
              leaf out-label {
                type uint32;
                description
                  "Out label";
              }
              leaf control-word {
                type boolean;
                // NCS drop default statement
                description
                  "The attribute enables or disables the control-word for an FXC Instance.
                   By default, the value is true.";
              }
              leaf l2mtu {
                type uint32 {
                  range "64..65536";
                }
                // NCS drop default statement
                description
                  "This attribute sets the Maximum Transmission Unit(MTU) for an FXC Instance
                   By default, the value is set to 1500.";
              }
              leaf flags {
                type string;
                description
                  "(L) or (R)  -- local or remote VID
                   (P) or (B) or empty -- Primary, Backup or none
                   (C) - Control Word - set or none
                   (M)  -- Learnt from Multi-home peer or not";
              }
              leaf interface {
                type mef-logical-port:live_ncs_logical-port-ref;
                description
                  "Logical port interface";
              }
              leaf route-distinguisher {
                type string;
                description
                  "Route distinguisher";
              }
            }
            container ilm-database {
              description
                "List of FXC Incoming Label Map (ILM)";
              leaf service-label {
                type uint32;
                description
                  "Service label";
              }
              list esi-label {
                key "label";
                description
                  "List of ESI labels";
                leaf label {
                  type uint32;
                  description
                    "Ethernet segment identifier label";
                }
              }
              list local-switching-label {
                key "label";
                description
                  "List of local-switching labels";
                leaf label {
                  type uint32;
                  description
                    "Local switching label";
                }
                leaf ethernet-segment-identifier {
                  type string;
                  description
                    "Ethernet segment identifier (ESI)";
                }
                leaf logical-port {
                  type mef-logical-port:live_ncs_logical-port-ref;
                  description
                    "Logical port of the ethernet segment";
                }
              }
              leaf mac-label {
                type uint32;
                description
                  "In label";
              }
              leaf out-interface {
                type string;
                description
                  "Out interface";
              }
            }
            list service-tunnel {
              key "index";
              description
                "List of service tunnels";
              leaf index {
                type uint32;
                description
                  "Service tunnel index";
              }
              leaf next-hop-address {
                type inet:ip-address;
                description
                  "Next hop IP address";
              }
              leaf out-label {
                type uint32;
                description
                  "Service tunnel out-label";
              }
              leaf transport-lsp {
                type string;
                description
                  "Transport LSP";
              }
              leaf transport-lsp-index {
                type uint32;
                description
                  "Transport LSP index";
              }
              leaf oper-status {
                type live_ncs_oper-status-type;
                description
                  "Up or Down status for service tunnel";
              }
            }
            uses live_ncs_cross-connect-cfg;
          }
        }
      }
    }
  }
  augment "/ncs:devices/ncs:template/ncs:ned-id/ncs:config" {
    container evpn {
      description
        "Evpn";
      container global-route-distinguisher {
        description
          "Default Global Route Distinguisher";
        leaf route-distinguisher {
          type rt-types:ncs_template_route-distinguisher;
          description
            "Global Route Distinguisher";
        }
      }
      container ethernet-segments {
        description
          "Ethernet segment";
        list ethernet-segment {
          // NCS patched for predictable order
          ordered-by user;
          key "name";
          description
            "An ethernet segment";
          leaf name {
            type string;
            description
              "Name of the ethernet segment";
          }
          leaf logical-port {
            // NCS drop mandatory statement
            type mef-logical-port:ncs_template_logical-port-ref;
            description
              "Logical port of the ethernet segment";
          }
          leaf evlag {
            type string;
            // NCS drop default statement
            description
              "Enable/disable EvLag on the AGG port";
          }
          container ethernet-segment-identifier {
            description
              "Ethernet Segment Identifier (ESI)";
            choice esi-type {
              // NCS drop mandatory statement
              description
                "Choice between different types of Ethernet Segment Identifiers (ESI)";
              case type-0 {
                container arbitrary {
                  description
                    "Ethernet Segment Identifier (ESI) that is managed and configured by user";
                  leaf arbitrary {
                    type ncs_template_ciena-ethernet-segment-identifier-type;
                    description
                      "9-octet arbitrary value";
                  }
                }
              }
              case type-1 {
                container lacp-based {
                  description
                    "Auto-generated ESI value determined from LACP.
                     MAC address (6 octets) + port key (2 octets) +
                     0x00 (1 octet)";
                  leaf auto-derived {
                    type ncs_template_ethernet-segment-identifier-auto-derive-type;
                    description
                      "Set to 'true' for auto-derived ESI.";
                  }
                }
              }
              case type-2 {
                container lan-based {
                  description
                    "Auto-generated if CE-PE connected via bridged forwarding-domain.
                     Root bridge MAC (6 octets) + priority (2 octets) +
                     0x00 (1 octet)";
                  leaf auto-derived {
                    type ncs_template_ethernet-segment-identifier-auto-derive-type;
                    description
                      "Set to 'true' for auto-derived ESI.";
                  }
                }
              }
              case type-3 {
                container mac-based {
                  description
                    "MAC based ESI – can be auto-generated/configured.
                     System MAC (6 octets) + Local discriminator (3 octets)";
                  leaf auto-derived {
                    type string;
                    description
                      "Set to 'true' for auto-derived ESI.
                       Set to 'false' for user configuration.";
                  }
                  leaf system-mac-address {
                    // NCS drop mandatory statement
                    type string;
                    description
                      "ESI System MAC (6 octets)";
                  }
                  leaf local-discriminator {
                    // NCS drop mandatory statement
                    type string;
                    description
                      "Local discriminator (3 octets)";
                  }
                }
              }
              case type-4 {
                container router-id-based {
                  description
                    "Router-ID based ESI – can be auto-generated/configured.
                     Router ID (4 octets) + Local discriminator (4 octets) + 0x00 (1 octet)";
                  leaf auto-derived {
                    type string;
                    description
                      "Set to 'true' for auto-derived ESI.
                       Set to 'false' for user configuration.";
                  }
                  leaf router-id {
                    type string;
                    description
                      "Router ID (4 octets)";
                  }
                  leaf local-discriminator {
                    // NCS drop mandatory statement
                    type string;
                    description
                      "Local discriminator (4 octets)";
                  }
                }
              }
              case type-5 {
                container as-based {
                  description
                    "Autonomous System (AS) based – can be auto-generated/configured.
                     AS number (4 octets) + local discriminator (4 octets) + 0x00 (1 octet)";
                  leaf auto-derived {
                    type string;
                    description
                      "Set to 'true' for auto-derived ESI.
                       Set to 'false' for user configuration.";
                  }
                  leaf router-id {
                    type string;
                    description
                      "AS number (4 octets)";
                  }
                  leaf local-discriminator {
                    // NCS drop mandatory statement
                    type string;
                    description
                      "Local discriminator (4 octets)";
                  }
                }
              }
            }
          }
          leaf active-mode {
            type ncs_template_active-mode-type;
            // NCS drop default statement
            description
              "Choice of active mode";
          }
          container df-election {
            description
              "df-election";
            leaf df-election-method {
              type es:ncs_template_df-election-method-type;
              // NCS drop default statement
              description
                "The DF election method";
            }
            leaf preference {
              type string;
              // NCS drop default statement
              description
                "The DF preference";
            }
            leaf revertive {
              type string;
              // NCS drop default statement
              description
                "The 'preempt' or 'revertive' behavior";
            }
            leaf election-wait-time {
              type string;
              // NCS drop default statement
              units "seconds";
              description
                "Wait time for DF election";
            }
            leaf select-high-preference {
              type string;
              // NCS drop default statement
              description
                "Preference with higher value will be selected first";
            }
            leaf reversion-hold-time {
              type string;
              // NCS drop default statement
              units "seconds";
              description
                "Duration before reversion";
            }
          }
          container es-import {
            leaf route-distinguisher {
              type rt-types:ncs_template_route-distinguisher;
              description
                "Route Distinguisher configured on EVPN";
            }
            leaf route-target {
              type rt-types:ncs_template_route-target;
              description
                "Route Target configured on EVPN";
            }
          }
        }
      }
      container evpn-instances {
        description
          "evpn-instances";
        list evpn-instance {
          // NCS patched for predictable order
          ordered-by user;
          key "id";
          description
            "An EVPN instance";
          leaf id {
            type string;
            description
              "ID of EVPN instance";
          }
          choice services {
            // NCS drop mandatory statement
            description
              "flexible-cross-connect, vpws, vpls services";
            case flexible-cross-connect-vlan-aware-fd {
              list flexible-cross-connect-vlan-aware-fd {
                // NCS patched for predictable order
                ordered-by user;
                key "forwarding-domain";
                // NCS drop max-elements statement
                description
                  "Forwarding-domain vlan-aware evpn-fxc service";
                leaf forwarding-domain {
                  type string;
                  // NCS drop must statement
                  description
                    "Name of the forwarding domain";
                }
                leaf control-word {
                  type string;
                  // NCS drop default statement
                  description
                    "The attribute enables or disables the control-word for an FXC Instance.
                     By default, the value is true.";
                }
                leaf l2mtu {
                  type string;
                  // NCS drop default statement
                  description
                    "This attribute sets the Maximum Transmission Unit(MTU) for an FXC Instance
                     By default, the value is set to 1500.";
                }
                leaf stats-collection {
                  type ncs_template_stats-collection-type;
                  // NCS drop default statement
                  description
                    "Evpn Statistic Collection";
                }
              }
            }
            case point-to-point {
              list vpws-cross-connect-fd {
                // NCS patched for predictable order
                ordered-by user;
                key "forwarding-domain";
                description
                  "Forwarding-domain for evpn vpws service";
                leaf forwarding-domain {
                  type string;
                  // NCS drop must statement
                  description
                    "Name of the forwarding domain";
                }
                leaf control-word {
                  type string;
                  // NCS drop default statement
                  description
                    "The attribute enables or disables the control-word for an FXC Instance.
                     By default, the value is true.";
                }
                leaf l2mtu {
                  type string;
                  // NCS drop default statement
                  description
                    "This attribute sets the Maximum Transmission Unit(MTU) for an FXC Instance
                     By default, the value is set to 1500.";
                }
                leaf stats-collection {
                  type ncs_template_stats-collection-type;
                  // NCS drop default statement
                  description
                    "Evpn Statistic Collection";
                }
                uses ncs_template_cross-connect-cfg;
              }
              list flexible-cross-connect-vlan-unaware-fd {
                // NCS patched for predictable order
                ordered-by user;
                key "forwarding-domain";
                description
                  "Vlan Unaware";
                leaf forwarding-domain {
                  type string;
                  // NCS drop must statement
                  description
                    "Name of the forwarding domain";
                }
                leaf control-word {
                  type string;
                  // NCS drop default statement
                  description
                    "The attribute enables or disables the control-word for an FXC Instance.
                     By default, the value is true.";
                }
                leaf l2mtu {
                  type string;
                  // NCS drop default statement
                  description
                    "This attribute sets the Maximum Transmission Unit(MTU) for an FXC Instance
                     By default, the value is set to 1500.";
                }
                uses cnevpn:ncs_template_cross-connect-cfg;
              }
            }
            case vpls-fd {
              list vpls-fd {
                // NCS patched for predictable order
                ordered-by user;
                key "forwarding-domain";
                leaf forwarding-domain {
                  type string;
                  // NCS drop must statement
                  description
                    "Name of the forwarding domain";
                }
              }
            }
          }
          container route-distinguisher {
            description
              "A route distinguisher is an 8-octet value used to distinguish
               routes from different BGP VPNs (RFC 4364). A route
               distinguisher consists of three fields: A 2-octet type field,
               an administrator field, and an assigned number field.
               According to the data formats for type 0, 1, and 2 defined in
               RFC4364, the encoding pattern is defined as:

               0:2-octet-asn:4-octet-number
               1:4-octet-ipv4addr:2-octet-number
               2:4-octet-asn:2-octet-number.
               2-octet-other-hex-number:6-octet-hex-number

               Some valid examples are: 100:100, 1.1.1.1:100, and 1234567890:203";
            choice rd-type {
              description
                "Choice between different types of Route Distinguishers";
              case type-0 {
                container asn-2-octet-based {
                  leaf value {
                    type ncs_template_ciena-route-distinguisher-type-0;
                    description
                      "2-octet-asn:4-octet-number Route Distinguisher,
                       ex: 100:100";
                  }
                }
              }
              case type-1 {
                container ip-based {
                  leaf value {
                    type ncs_template_ciena-route-distinguisher-type-1;
                    description
                      "4-octet-ipv4addr:2-octet-number Route Distinguisher,
                       ex: 1.1.1.1:100";
                  }
                }
              }
              case type-2 {
                container asn-4-octet-based {
                  leaf value {
                    type ncs_template_ciena-route-distinguisher-type-2;
                    description
                      "4-octet-asn:2-octet-number Route Distinguisher,
                       ex: 1234567890:203";
                  }
                }
              }
            }
          }
          uses rt-types:ncs_template_vpn-route-targets;
        }
      }
    }
    // NCS drop config false container 'evpn-ethernet-segment-state'
    // NCS drop config false container 'evpn-state'
  }

  identity static-MAC-move-detected {
    base evpn-notification-state;
    description
      "Static MAC move is detected";
  }

  identity mass-withdraw-received {
    base evpn-notification-state;
    description
      "Mass withdraw received";
  }

  identity MAC-duplication-detected {
    base evpn-notification-state;
    description
      "MAC duplication is detected";
  }

  identity evpn-notification-state {
    description
      "The base identity on which EVPN notification states are based";
  }

  feature evpn-pbb-params {
    description
      "EVPN's PBB parameters";
  }

  feature evpn-bgp-params {
    description
      "EVPN's BGP parameters";
  }
}
