module ciena-sync-gnss {
  // Generated by yanger -t ncs
  tailf:mount-id "saos1051-nc-1.0:saos1051-nc-1.0";
  tailf:ncs-device-type "netconf";

  namespace "http://www.ciena.com/ns/yang/ciena-sync-gnss";
  prefix gnss;

  import ietf-yang-types {
    prefix yang;
  }
  import ciena-sync {
    prefix sync;
  }
  import ciena-types {
    prefix ciena-types;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data model for the management of clock
     synchronization in packet networks specific to integrated GNSS receiver.

     Copyright (c) 2020 Ciena Corporation. All rights reserved.

     All information contained herein is, and remains the property of Ciena
     Corporation. Dissemination of this information or reproduction of this
     material is strictly forbidden unless prior written permission is obtained
     from Ciena Corporation.";

  revision 2020-02-18 {
    description
      "Add yang support for integrated GNSS receiver configuration and state.";
    reference "IS-GPS-200: GPS Interface Specification";
  }

  typedef ncs_template_string-type {
    type string;
    description
      "String type.";
  }

  typedef ncs_template_gnss-oper-state-type {
    type string;
    description
      "GNSS operational state identityref type.";
  }

  typedef ncs_template_gnss-antenna-input-leafref-type {
    type string;
    description
      "GNSS antenna input leafref type.";
  }

  typedef ncs_template_gnss-input-oper-state-leafref-type {
    type string;
    description
      "GNSS input operational state leafref type.";
  }

  typedef ncs_template_almanac-status-leafref-type {
    type string;
    description
      "GNSS almanac status leafref type.";
  }

  typedef ncs_template_antenna-cable-status-leafref-type {
    type string;
    description
      "GNSS antenna cable status leafref type.";
  }

  typedef ncs_template_antenna-signal-condition-leafref-type {
    type string;
    description
      "GNSS antenna signal condition leafref type.";
  }

  typedef ncs_template_time-standard-type {
    type string;
    description
      "Time standard type used when displaying the current time.";
  }

  typedef ncs_template_constellation-type {
    type string;
    description
      "Satellite constellation type used by configuration.";
  }

  typedef ncs_template_antenna-cable-status-type {
    type string;
    description
      "Antenna cable status.";
  }

  typedef ncs_template_antenna-signal-condition-type {
    type string;
    description
      "Antenna signal condition.";
  }

  typedef ncs_template_almanac-status-type {
    type string;
    description
      "Almanac status.";
  }

  typedef ncs_template_sv-type {
    type string;
    description
      "GNSS constellation type used in sync-state.";
  }

  typedef ncs_template_acquired-type {
    type string;
    description
      "Satellite acquisition status.";
  }

  typedef ncs_template_float {
    type string;
    description
      "Float type with 7 decimal places";
  }

  typedef ncs_template_float-2dp {
    type string;
    description
      "Float type with 2 decimal place";
  }

  typedef ncs_template_float-3dp {
    type string;
    description
      "Float type with 3 decimal places";
  }

  typedef ncs_rpc_notif_string-type {
    type string {
      length "1..32";
    }
    description
      "String type.";
  }

  typedef ncs_rpc_notif_gnss-oper-state-type {
    type identityref {
      base gnss:sync-gnss-oper-state-identity;
    }
    description
      "GNSS operational state identityref type.";
  }

  typedef ncs_rpc_notif_gnss-antenna-input-leafref-type {
    type string;
    description
      "GNSS antenna input leafref type.";
  }

  typedef ncs_rpc_notif_gnss-input-oper-state-leafref-type {
    type string;
    description
      "GNSS input operational state leafref type.";
  }

  typedef ncs_rpc_notif_almanac-status-leafref-type {
    type string;
    description
      "GNSS almanac status leafref type.";
  }

  typedef ncs_rpc_notif_antenna-cable-status-leafref-type {
    type string;
    description
      "GNSS antenna cable status leafref type.";
  }

  typedef ncs_rpc_notif_antenna-signal-condition-leafref-type {
    type string;
    description
      "GNSS antenna signal condition leafref type.";
  }

  typedef ncs_rpc_notif_time-standard-type {
    type enumeration {
      enum "utc" {
        description
          "Coordinated Universal Time (UTC).";
      }
    }
    description
      "Time standard type used when displaying the current time.";
  }

  typedef ncs_rpc_notif_constellation-type {
    type enumeration {
      enum "gps" {
        description
          "Global Positioning System (GPS)";
      }
      enum "galileo" {
        description
          "GNSS constellation";
      }
    }
    description
      "Satellite constellation type used by configuration.";
  }

  typedef ncs_rpc_notif_antenna-cable-status-type {
    type enumeration {
      enum "detected" {
        description
          "Antenna cable is plugged and detected.";
      }
      enum "not-detected" {
        description
          "Antenna cable is either not plugged or not detected.";
      }
    }
    description
      "Antenna cable status.";
  }

  typedef ncs_rpc_notif_antenna-signal-condition-type {
    type enumeration {
      enum "normal" {
        description
          "Antenna signal is normal when more satellites than the satellite visibility threshold are visible.";
      }
      enum "degrade" {
        description
          "Antenna signal is degraded when less satellites than the satellite visibility threshold are visible.";
      }
      enum "fault" {
        description
          "Antenna signal is faulted when no satellites are visible.";
      }
    }
    description
      "Antenna signal condition.";
  }

  typedef ncs_rpc_notif_almanac-status-type {
    type enumeration {
      enum "not-available" {
        description
          "Almanac is not available. This can occur during initial configuration or non-configuration of GNSS antenna-input.";
      }
      enum "acquiring" {
        description
          "GNSS antenna input is configured and is reciving a signal. Almanac is currently being built.";
      }
      enum "complete" {
        description
          "GNSS almanac is now complete after all satellites are acquired.";
      }
    }
    description
      "Almanac status.";
  }

  typedef ncs_rpc_notif_sv-type {
    type enumeration {
      enum "gps" {
        description
          "Global Positioning System (GPS).";
      }
      enum "galileo" {
        description
          "GNSS constellation.";
      }
      enum "glonass" {
        description
          "GLObal NAvigation Satellite System (GLONASS).";
      }
      enum "beidou" {
        description
          "GNSS constellation.";
      }
      enum "qzss" {
        description
          "Quasi-Zenith Satellite System (QZSS).";
      }
    }
    description
      "GNSS constellation type used in sync-state.";
  }

  typedef ncs_rpc_notif_acquired-type {
    type enumeration {
      enum "never-acquired" {
        description
          "GNSS satellite signal was never acquired.";
      }
      enum "acquired" {
        description
          "GNSS satellite signal is acquired.";
      }
      enum "reopened-search" {
        description
          "GNSS satellite signal was lost and signal search has commenced.";
      }
    }
    description
      "Satellite acquisition status.";
  }

  typedef ncs_rpc_notif_float {
    type decimal64 {
      fraction-digits 7;
    }
    description
      "Float type with 7 decimal places";
  }

  typedef ncs_rpc_notif_float-2dp {
    type decimal64 {
      fraction-digits 2;
    }
    description
      "Float type with 2 decimal place";
  }

  typedef ncs_rpc_notif_float-3dp {
    type decimal64 {
      fraction-digits 3;
    }
    description
      "Float type with 3 decimal places";
  }

  typedef live_ncs_string-type {
    type string {
      length "1..32";
    }
    description
      "String type.";
  }

  typedef live_ncs_gnss-oper-state-type {
    type identityref {
      base gnss:sync-gnss-oper-state-identity;
    }
    description
      "GNSS operational state identityref type.";
  }

  typedef live_ncs_gnss-antenna-input-leafref-type {
    type leafref {
      path "/ncs:devices/ncs:device/ncs:live-status/sync:sync/sync:input-references/gnss:gnss-antenna-input/gnss:name" {
        tailf:xpath-root 3;
      }
    }
    description
      "GNSS antenna input leafref type.";
  }

  typedef live_ncs_gnss-input-oper-state-leafref-type {
    type leafref {
      path "/ncs:devices/ncs:device/ncs:live-status/sync:sync-state/sync:input-references/gnss:gnss-antenna-input/gnss:oper-state" {
        tailf:xpath-root 3;
      }
    }
    description
      "GNSS input operational state leafref type.";
  }

  typedef live_ncs_almanac-status-leafref-type {
    type leafref {
      path "/ncs:devices/ncs:device/ncs:live-status/sync:sync-state/gnss:gnss-global/gnss:almanac-status" {
        tailf:xpath-root 3;
      }
    }
    description
      "GNSS almanac status leafref type.";
  }

  typedef live_ncs_antenna-cable-status-leafref-type {
    type leafref {
      path "/ncs:devices/ncs:device/ncs:live-status/sync:sync-state/gnss:gnss-global/gnss:antenna-status" {
        tailf:xpath-root 3;
      }
    }
    description
      "GNSS antenna cable status leafref type.";
  }

  typedef live_ncs_antenna-signal-condition-leafref-type {
    type leafref {
      path "/ncs:devices/ncs:device/ncs:live-status/sync:sync-state/sync:input-references/gnss:gnss-antenna-input/gnss:antenna-signal-condition" {
        tailf:xpath-root 3;
      }
    }
    description
      "GNSS antenna signal condition leafref type.";
  }

  typedef live_ncs_time-standard-type {
    type enumeration {
      enum "utc" {
        description
          "Coordinated Universal Time (UTC).";
      }
    }
    description
      "Time standard type used when displaying the current time.";
  }

  typedef live_ncs_constellation-type {
    type enumeration {
      enum "gps" {
        description
          "Global Positioning System (GPS)";
      }
      enum "galileo" {
        description
          "GNSS constellation";
      }
    }
    description
      "Satellite constellation type used by configuration.";
  }

  typedef live_ncs_antenna-cable-status-type {
    type enumeration {
      enum "detected" {
        description
          "Antenna cable is plugged and detected.";
      }
      enum "not-detected" {
        description
          "Antenna cable is either not plugged or not detected.";
      }
    }
    description
      "Antenna cable status.";
  }

  typedef live_ncs_antenna-signal-condition-type {
    type enumeration {
      enum "normal" {
        description
          "Antenna signal is normal when more satellites than the satellite visibility threshold are visible.";
      }
      enum "degrade" {
        description
          "Antenna signal is degraded when less satellites than the satellite visibility threshold are visible.";
      }
      enum "fault" {
        description
          "Antenna signal is faulted when no satellites are visible.";
      }
    }
    description
      "Antenna signal condition.";
  }

  typedef live_ncs_almanac-status-type {
    type enumeration {
      enum "not-available" {
        description
          "Almanac is not available. This can occur during initial configuration or non-configuration of GNSS antenna-input.";
      }
      enum "acquiring" {
        description
          "GNSS antenna input is configured and is reciving a signal. Almanac is currently being built.";
      }
      enum "complete" {
        description
          "GNSS almanac is now complete after all satellites are acquired.";
      }
    }
    description
      "Almanac status.";
  }

  typedef live_ncs_sv-type {
    type enumeration {
      enum "gps" {
        description
          "Global Positioning System (GPS).";
      }
      enum "galileo" {
        description
          "GNSS constellation.";
      }
      enum "glonass" {
        description
          "GLObal NAvigation Satellite System (GLONASS).";
      }
      enum "beidou" {
        description
          "GNSS constellation.";
      }
      enum "qzss" {
        description
          "Quasi-Zenith Satellite System (QZSS).";
      }
    }
    description
      "GNSS constellation type used in sync-state.";
  }

  typedef live_ncs_acquired-type {
    type enumeration {
      enum "never-acquired" {
        description
          "GNSS satellite signal was never acquired.";
      }
      enum "acquired" {
        description
          "GNSS satellite signal is acquired.";
      }
      enum "reopened-search" {
        description
          "GNSS satellite signal was lost and signal search has commenced.";
      }
    }
    description
      "Satellite acquisition status.";
  }

  typedef live_ncs_float {
    type decimal64 {
      fraction-digits 7;
    }
    description
      "Float type with 7 decimal places";
  }

  typedef live_ncs_float-2dp {
    type decimal64 {
      fraction-digits 2;
    }
    description
      "Float type with 2 decimal place";
  }

  typedef live_ncs_float-3dp {
    type decimal64 {
      fraction-digits 3;
    }
    description
      "Float type with 3 decimal places";
  }

  typedef string-type {
    type string {
      length "1..32";
    }
    description
      "String type.";
  }

  typedef gnss-oper-state-type {
    type identityref {
      base gnss:sync-gnss-oper-state-identity;
    }
    description
      "GNSS operational state identityref type.";
  }

  typedef gnss-antenna-input-leafref-type {
    type leafref {
      path "/ncs:devices/ncs:device/ncs:config/sync:sync/sync:input-references/gnss:gnss-antenna-input/gnss:name" {
        tailf:xpath-root 3;
      }
    }
    description
      "GNSS antenna input leafref type.";
  }

  typedef gnss-input-oper-state-leafref-type {
    type leafref {
      path "/ncs:devices/ncs:device/ncs:live-status/sync:sync-state/sync:input-references/gnss:gnss-antenna-input/gnss:oper-state" {
        tailf:xpath-root 2;
      }
    }
    description
      "GNSS input operational state leafref type.";
  }

  typedef almanac-status-leafref-type {
    type leafref {
      path "/ncs:devices/ncs:device/ncs:live-status/sync:sync-state/gnss:gnss-global/gnss:almanac-status" {
        tailf:xpath-root 2;
      }
    }
    description
      "GNSS almanac status leafref type.";
  }

  typedef antenna-cable-status-leafref-type {
    type leafref {
      path "/ncs:devices/ncs:device/ncs:live-status/sync:sync-state/gnss:gnss-global/gnss:antenna-status" {
        tailf:xpath-root 2;
      }
    }
    description
      "GNSS antenna cable status leafref type.";
  }

  typedef antenna-signal-condition-leafref-type {
    type leafref {
      path "/ncs:devices/ncs:device/ncs:live-status/sync:sync-state/sync:input-references/gnss:gnss-antenna-input/gnss:antenna-signal-condition" {
        tailf:xpath-root 2;
      }
    }
    description
      "GNSS antenna signal condition leafref type.";
  }

  typedef time-standard-type {
    type enumeration {
      enum "utc" {
        description
          "Coordinated Universal Time (UTC).";
      }
    }
    description
      "Time standard type used when displaying the current time.";
  }

  typedef constellation-type {
    type enumeration {
      enum "gps" {
        description
          "Global Positioning System (GPS)";
      }
      enum "galileo" {
        description
          "GNSS constellation";
      }
    }
    description
      "Satellite constellation type used by configuration.";
  }

  typedef antenna-cable-status-type {
    type enumeration {
      enum "detected" {
        description
          "Antenna cable is plugged and detected.";
      }
      enum "not-detected" {
        description
          "Antenna cable is either not plugged or not detected.";
      }
    }
    description
      "Antenna cable status.";
  }

  typedef antenna-signal-condition-type {
    type enumeration {
      enum "normal" {
        description
          "Antenna signal is normal when more satellites than the satellite visibility threshold are visible.";
      }
      enum "degrade" {
        description
          "Antenna signal is degraded when less satellites than the satellite visibility threshold are visible.";
      }
      enum "fault" {
        description
          "Antenna signal is faulted when no satellites are visible.";
      }
    }
    description
      "Antenna signal condition.";
  }

  typedef almanac-status-type {
    type enumeration {
      enum "not-available" {
        description
          "Almanac is not available. This can occur during initial configuration or non-configuration of GNSS antenna-input.";
      }
      enum "acquiring" {
        description
          "GNSS antenna input is configured and is reciving a signal. Almanac is currently being built.";
      }
      enum "complete" {
        description
          "GNSS almanac is now complete after all satellites are acquired.";
      }
    }
    description
      "Almanac status.";
  }

  typedef sv-type {
    type enumeration {
      enum "gps" {
        description
          "Global Positioning System (GPS).";
      }
      enum "galileo" {
        description
          "GNSS constellation.";
      }
      enum "glonass" {
        description
          "GLObal NAvigation Satellite System (GLONASS).";
      }
      enum "beidou" {
        description
          "GNSS constellation.";
      }
      enum "qzss" {
        description
          "Quasi-Zenith Satellite System (QZSS).";
      }
    }
    description
      "GNSS constellation type used in sync-state.";
  }

  typedef acquired-type {
    type enumeration {
      enum "never-acquired" {
        description
          "GNSS satellite signal was never acquired.";
      }
      enum "acquired" {
        description
          "GNSS satellite signal is acquired.";
      }
      enum "reopened-search" {
        description
          "GNSS satellite signal was lost and signal search has commenced.";
      }
    }
    description
      "Satellite acquisition status.";
  }

  typedef float {
    type decimal64 {
      fraction-digits 7;
    }
    description
      "Float type with 7 decimal places";
  }

  typedef float-2dp {
    type decimal64 {
      fraction-digits 2;
    }
    description
      "Float type with 2 decimal place";
  }

  typedef float-3dp {
    type decimal64 {
      fraction-digits 3;
    }
    description
      "Float type with 3 decimal places";
  }

  grouping ncs_template_gnss-antenna-input-config-grouping {
    description
      "GNSS antenna input configuration attributes.";
    leaf antenna-cable-length {
      type string;
      units "meters";
      // NCS drop default statement
      description
        "Antenna cable length in meters.";
    }
    leaf-list constellations {
      // NCS patched for predictable order
      ordered-by user;
      type gnss:ncs_template_constellation-type;
      // NCS drop min-elements statement
      // NCS drop max-elements statement
      description
        "Configure constellations monitored by GNSS receiver";
    }
    uses sync:ncs_template_sync-input-reference-config-grouping;
    leaf forced-quality-level {
      type sync:ncs_template_quality-level-type;
      description
        "Configuration to override the RX quality-level of an input.";
    }
  }

  grouping ncs_rpc_notif_gnss-antenna-input-config-grouping {
    description
      "GNSS antenna input configuration attributes.";
    leaf antenna-cable-length {
      type uint32 {
        range "1..1000";
      }
      units "meters";
      default "2";
      description
        "Antenna cable length in meters.";
    }
    leaf-list constellations {
      type gnss:ncs_rpc_notif_constellation-type;
      min-elements 1;
      max-elements 1;
      description
        "Configure constellations monitored by GNSS receiver";
    }
    uses sync:ncs_rpc_notif_sync-input-reference-config-grouping;
    leaf forced-quality-level {
      type sync:ncs_rpc_notif_quality-level-type;
      description
        "Configuration to override the RX quality-level of an input.";
    }
  }

  grouping live_ncs_gnss-antenna-input-config-grouping {
    description
      "GNSS antenna input configuration attributes.";
    leaf antenna-cable-length {
      type uint32 {
        range "1..1000";
      }
      units "meters";
      // NCS drop default statement
      description
        "Antenna cable length in meters.";
    }
    leaf-list constellations {
      type gnss:live_ncs_constellation-type;
      // NCS drop min-elements statement
      // NCS drop max-elements statement
      description
        "Configure constellations monitored by GNSS receiver";
    }
    uses sync:live_ncs_sync-input-reference-config-grouping;
    leaf forced-quality-level {
      type sync:live_ncs_quality-level-type;
      description
        "Configuration to override the RX quality-level of an input.";
    }
  }

  grouping gnss-antenna-input-config-grouping {
    description
      "GNSS antenna input configuration attributes.";
    leaf antenna-cable-length {
      type uint32 {
        range "1..1000";
      }
      units "meters";
      default "2";
      description
        "Antenna cable length in meters.";
    }
    leaf-list constellations {
      type gnss:constellation-type;
      min-elements 1;
      max-elements 1;
      description
        "Configure constellations monitored by GNSS receiver";
    }
    uses sync:sync-input-reference-config-grouping;
    leaf forced-quality-level {
      type sync:quality-level-type;
      description
        "Configuration to override the RX quality-level of an input.";
    }
  }

  augment "/ncs:devices/ncs:device/ncs:rpc" {
    container rpc-sync-gnss-almanac-clear {
      tailf:ncs-device-type "netconf";
      tailf:display-when "not(../../ncs:module) or ../../ncs:module[ncs:name='ciena-sync-gnss']";
      tailf:action sync-gnss-almanac-clear {
        tailf:actionpoint ncsproxy {
          tailf:internal;
        }
        description
          "Clear the GNSS receiver's almanc and force a new startup sequence.";
        output {
          leaf status {
            type string;
            description
              "Status indicating if the operation has succeeded or not.";
          }
        }
      }
    }
  }
  augment "/ncs:devices/ncs:device-group/ncs:ned-id/ncs:rpc" {
    container rpc-sync-gnss-almanac-clear {
      tailf:ncs-device-type "netconf";
      tailf:display-when "/ncs:devices/ncs:device[ncs:name=current()/../../../ncs:member]/ncs:module[ncs:name='ciena-sync-gnss']";
      tailf:action sync-gnss-almanac-clear {
        tailf:actionpoint ncsproxy {
          tailf:internal;
        }
        description
          "Clear the GNSS receiver's almanc and force a new startup sequence.";
        output {
          container "device" {
            leaf "name" {
              type string;
            }
            leaf "info" {
              type string;
            }
            container "result" {
              leaf status {
                type string;
                description
                  "Status indicating if the operation has succeeded or not.";
              }
            }
          }
        }
      }
    }
  }
  augment "/ncs:devices/ncs:device/ncs:rpc" {
    container rpc-sync-gnss-force-re-acquisition {
      tailf:ncs-device-type "netconf";
      tailf:display-when "not(../../ncs:module) or ../../ncs:module[ncs:name='ciena-sync-gnss']";
      tailf:action sync-gnss-force-re-acquisition {
        tailf:actionpoint ncsproxy {
          tailf:internal;
        }
        description
          "Force re-acquisition of position by GNSS.";
        input {
          leaf gnss-antenna-input-name {
            type gnss:ncs_rpc_notif_gnss-antenna-input-leafref-type;
            description
              "Name of GNSS antenna input.";
          }
        }
        output {
          leaf status {
            type string;
            description
              "Status indicating if the operation has succeeded or not.";
          }
        }
      }
    }
  }
  augment "/ncs:devices/ncs:device-group/ncs:ned-id/ncs:rpc" {
    container rpc-sync-gnss-force-re-acquisition {
      tailf:ncs-device-type "netconf";
      tailf:display-when "/ncs:devices/ncs:device[ncs:name=current()/../../../ncs:member]/ncs:module[ncs:name='ciena-sync-gnss']";
      tailf:action sync-gnss-force-re-acquisition {
        tailf:actionpoint ncsproxy {
          tailf:internal;
        }
        description
          "Force re-acquisition of position by GNSS.";
        input {
          leaf gnss-antenna-input-name {
            type gnss:ncs_rpc_notif_gnss-antenna-input-leafref-type;
            description
              "Name of GNSS antenna input.";
          }
        }
        output {
          container "device" {
            leaf "name" {
              type string;
            }
            leaf "info" {
              type string;
            }
            container "result" {
              leaf status {
                type string;
                description
                  "Status indicating if the operation has succeeded or not.";
              }
            }
          }
        }
      }
    }
  }
  augment "/ncs:devices/ncs:device/ncs:netconf-notifications/ncs:received-notifications/ncs:notification/ncs:data" {
    container gnss-antenna-cable-status-change {
      presence "";
      config false;
      description
        "Generated when the GNSS antenna cable statusichanges (detected/not detected).";
      leaf antenna-status {
        type gnss:ncs_rpc_notif_antenna-cable-status-leafref-type;
        description
          "Antenna cable status.";
      }
    }
  }
  augment "/ncs:devices/ncs:device/ncs:netconf-notifications/ncs:received-notifications/ncs:notification/ncs:data" {
    container gnss-almanac-status-change {
      presence "";
      config false;
      description
        "Generated when the GNSS almanac status changes (available/not available).";
      leaf almanac-status {
        type gnss:ncs_rpc_notif_almanac-status-leafref-type;
        description
          "Almanac status.";
      }
    }
  }
  augment "/ncs:devices/ncs:device/ncs:netconf-notifications/ncs:received-notifications/ncs:notification/ncs:data" {
    container gnss-antenna-input-signal-condition-change {
      presence "";
      config false;
      description
        "Generated when the GNSS antenna signal condition changes.";
      leaf gnss-antenna-input-name {
        type gnss:ncs_rpc_notif_gnss-antenna-input-leafref-type;
        description
          "Name of GNSS input reference.";
      }
      leaf antenna-signal-condition {
        type gnss:ncs_rpc_notif_antenna-signal-condition-leafref-type;
        description
          "Antenna signal condition.";
      }
    }
  }
  augment "/ncs:devices/ncs:device/ncs:netconf-notifications/ncs:received-notifications/ncs:notification/ncs:data" {
    container gnss-antenna-input-oper-state-change {
      presence "";
      config false;
      description
        "Generated when the operational state of a GNSS antenna input changes.";
      leaf gnss-antenna-input-name {
        type gnss:ncs_rpc_notif_gnss-antenna-input-leafref-type;
        description
          "Name of GNSS input reference.";
      }
      leaf oper-state {
        type gnss:ncs_rpc_notif_gnss-input-oper-state-leafref-type;
        description
          "Operational state of GNSS input reference.";
      }
    }
  }
  augment "/ncs:devices/ncs:template/ncs:ned-id/ncs:config/sync:sync" {
    description
      "GNSS configuration.";
    container gnss-global {
      description
        "GNSS global configuration.";
      leaf elevation-mask {
        type string;
        units "degree";
        // NCS drop default statement
        description
          "Elevation mask in degrees.";
      }
      leaf cnr {
        type string;
        units "dB-Hz";
        // NCS drop default statement
        description
          "Carrier-to-noise ratio (dB-Hz).";
      }
      leaf pdop-mask {
        type string;
        // NCS drop default statement
        description
          "Position Dilution of Precision (PDOP) mask.";
      }
      leaf anti-jamming {
        type ciena-types:ncs_template_state;
        // NCS drop default statement
        description
          "GNSS anti-jamming capability.";
      }
      leaf time-standard {
        type gnss:ncs_template_time-standard-type;
        // NCS drop default statement
        description
          "Time standard.";
      }
      leaf antenna-cable-delay-rate {
        type gnss:ncs_template_float-2dp;
        units "ns/m";
        // NCS drop default statement
        description
          "Antenna cable delay rate in ns/m.";
      }
      leaf satellite-visibility-threshold {
        type string;
        // NCS drop default statement
        description
          "Satellite visibility threshold.";
      }
    }
  }
  augment "/ncs:devices/ncs:device/ncs:live-status/sync:sync" {
    description
      "GNSS configuration.";
    container gnss-global {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      description
        "GNSS global configuration.";
      leaf elevation-mask {
        type uint32 {
          range "0..90";
        }
        units "degree";
        // NCS drop default statement
        description
          "Elevation mask in degrees.";
      }
      leaf cnr {
        type uint32 {
          range "0..100";
        }
        units "dB-Hz";
        // NCS drop default statement
        description
          "Carrier-to-noise ratio (dB-Hz).";
      }
      leaf pdop-mask {
        type uint32 {
          range "0..50";
        }
        // NCS drop default statement
        description
          "Position Dilution of Precision (PDOP) mask.";
      }
      leaf anti-jamming {
        type ciena-types:live_ncs_state;
        // NCS drop default statement
        description
          "GNSS anti-jamming capability.";
      }
      leaf time-standard {
        type gnss:live_ncs_time-standard-type;
        // NCS drop default statement
        description
          "Time standard.";
      }
      leaf antenna-cable-delay-rate {
        type gnss:live_ncs_float-2dp;
        units "ns/m";
        // NCS drop default statement
        description
          "Antenna cable delay rate in ns/m.";
      }
      leaf satellite-visibility-threshold {
        type uint32 {
          range "1..12";
        }
        // NCS drop default statement
        description
          "Satellite visibility threshold.";
      }
    }
  }
  augment "/ncs:devices/ncs:device/ncs:config/sync:sync" {
    description
      "GNSS configuration.";
    container gnss-global {
      tailf:ncs-device-type "netconf";
      tailf:display-when "not(../../../ncs:module) or ../../../ncs:module[ncs:name='ciena-sync-gnss']";
      description
        "GNSS global configuration.";
      leaf elevation-mask {
        type uint32 {
          range "0..90";
        }
        units "degree";
        default "10";
        description
          "Elevation mask in degrees.";
      }
      leaf cnr {
        type uint32 {
          range "0..100";
        }
        units "dB-Hz";
        default "35";
        description
          "Carrier-to-noise ratio (dB-Hz).";
      }
      leaf pdop-mask {
        type uint32 {
          range "0..50";
        }
        default "6";
        description
          "Position Dilution of Precision (PDOP) mask.";
      }
      leaf anti-jamming {
        type ciena-types:state;
        default "enabled";
        description
          "GNSS anti-jamming capability.";
      }
      leaf time-standard {
        type gnss:time-standard-type;
        default "utc";
        description
          "Time standard.";
      }
      leaf antenna-cable-delay-rate {
        type gnss:float-2dp {
          range "1..100";
        }
        units "ns/m";
        default "5.05";
        description
          "Antenna cable delay rate in ns/m.";
      }
      leaf satellite-visibility-threshold {
        type uint32 {
          range "1..12";
        }
        default "2";
        description
          "Satellite visibility threshold.";
      }
    }
  }
  augment "/ncs:devices/ncs:template/ncs:ned-id/ncs:config/sync:sync/sync:input-references" {
    description
      "GNSS antenna input configuration.";
    list gnss-antenna-input {
      // NCS patched for predictable order
      ordered-by user;
      key "name";
      // NCS drop max-elements statement
      description
        "A list of all GNSS input configuration entries.";
      leaf name {
        type sync:ncs_template_name-string-type;
        description
          "Name of GNSS antenna input.";
      }
      uses gnss:ncs_template_gnss-antenna-input-config-grouping;
    }
  }
  augment "/ncs:devices/ncs:device/ncs:live-status/sync:sync/sync:input-references" {
    description
      "GNSS antenna input configuration.";
    list gnss-antenna-input {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      key "name";
      // NCS drop max-elements statement
      description
        "A list of all GNSS input configuration entries.";
      leaf name {
        type sync:live_ncs_name-string-type;
        description
          "Name of GNSS antenna input.";
      }
      uses gnss:live_ncs_gnss-antenna-input-config-grouping;
    }
  }
  augment "/ncs:devices/ncs:device/ncs:config/sync:sync/sync:input-references" {
    description
      "GNSS antenna input configuration.";
    list gnss-antenna-input {
      tailf:ncs-device-type "netconf";
      tailf:display-when "not(../../../ncs:module) or ../../../ncs:module[ncs:name='ciena-sync-gnss']";
      key "name";
      max-elements 1;
      description
        "A list of all GNSS input configuration entries.";
      leaf name {
        type sync:name-string-type;
        description
          "Name of GNSS antenna input.";
      }
      uses gnss:gnss-antenna-input-config-grouping;
    }
  }
  augment "/ncs:devices/ncs:template/ncs:ned-id/ncs:config/sync:sync/sync:protection-groups/sync:frequency-protection-group" {
    description
      "GNSS antenna input configuration in frequency protection-group.";
    leaf-list gnss-antenna-input {
      // NCS patched for predictable order
      ordered-by user;
      type gnss:ncs_template_gnss-antenna-input-leafref-type;
      description
        "List of GNSS antenna inputs that shall be considered as candidates
         for clock selection in frequency protection-group.";
    }
  }
  augment "/ncs:devices/ncs:device/ncs:live-status/sync:sync/sync:protection-groups/sync:frequency-protection-group" {
    description
      "GNSS antenna input configuration in frequency protection-group.";
    leaf-list gnss-antenna-input {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "List of GNSS antenna inputs that shall be considered as candidates
         for clock selection in frequency protection-group.";
    }
  }
  augment "/ncs:devices/ncs:device/ncs:config/sync:sync/sync:protection-groups/sync:frequency-protection-group" {
    description
      "GNSS antenna input configuration in frequency protection-group.";
    leaf-list gnss-antenna-input {
      tailf:ncs-device-type "netconf";
      tailf:display-when "not(../../../../../ncs:module) or ../../../../../ncs:module[ncs:name='ciena-sync-gnss']";
      type gnss:gnss-antenna-input-leafref-type;
      description
        "List of GNSS antenna inputs that shall be considered as candidates
         for clock selection in frequency protection-group.";
    }
  }
  augment "/ncs:devices/ncs:template/ncs:ned-id/ncs:config/sync:sync/sync:protection-groups/sync:phase-protection-group" {
    description
      "GNSS antenna input configuration in phase protection-group.";
    leaf-list gnss-antenna-input {
      // NCS patched for predictable order
      ordered-by user;
      type gnss:ncs_template_gnss-antenna-input-leafref-type;
      description
        "List of GNSS inputs that shall be considered as candidates
         for clock selection in phase protection-group.";
    }
  }
  augment "/ncs:devices/ncs:device/ncs:live-status/sync:sync/sync:protection-groups/sync:phase-protection-group" {
    description
      "GNSS antenna input configuration in phase protection-group.";
    leaf-list gnss-antenna-input {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "List of GNSS inputs that shall be considered as candidates
         for clock selection in phase protection-group.";
    }
  }
  augment "/ncs:devices/ncs:device/ncs:config/sync:sync/sync:protection-groups/sync:phase-protection-group" {
    description
      "GNSS antenna input configuration in phase protection-group.";
    leaf-list gnss-antenna-input {
      tailf:ncs-device-type "netconf";
      tailf:display-when "not(../../../../../ncs:module) or ../../../../../ncs:module[ncs:name='ciena-sync-gnss']";
      type gnss:gnss-antenna-input-leafref-type;
      description
        "List of GNSS inputs that shall be considered as candidates
         for clock selection in phase protection-group.";
    }
  }
  augment "/ncs:devices/ncs:template/ncs:ned-id/ncs:config/sync:sync/sync:protection-groups/sync:tod-protection-group" {
    description
      "GNSS antenna input configuration in time-of-day protection-group.";
    leaf-list gnss-antenna-input {
      // NCS patched for predictable order
      ordered-by user;
      type gnss:ncs_template_gnss-antenna-input-leafref-type;
      description
        "List of GNSS inputs that shall be considered as candidates
         for selection in time-of-day protection-group.";
    }
    leaf threshold-quality-level {
      type sync:ncs_template_quality-level-type;
      description
        "Threshold quality-level configuration of time-of-day protection-group.
         Forced quality-level of input added to this
         protection-group must satisfy the configured threshold quality-level
         in order to be considered selectable.";
    }
  }
  augment "/ncs:devices/ncs:device/ncs:live-status/sync:sync/sync:protection-groups/sync:tod-protection-group" {
    description
      "GNSS antenna input configuration in time-of-day protection-group.";
    leaf-list gnss-antenna-input {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "List of GNSS inputs that shall be considered as candidates
         for selection in time-of-day protection-group.";
    }
    leaf threshold-quality-level {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type sync:live_ncs_quality-level-type;
      description
        "Threshold quality-level configuration of time-of-day protection-group.
         Forced quality-level of input added to this
         protection-group must satisfy the configured threshold quality-level
         in order to be considered selectable.";
    }
  }
  augment "/ncs:devices/ncs:device/ncs:config/sync:sync/sync:protection-groups/sync:tod-protection-group" {
    description
      "GNSS antenna input configuration in time-of-day protection-group.";
    leaf-list gnss-antenna-input {
      tailf:ncs-device-type "netconf";
      tailf:display-when "not(../../../../../ncs:module) or ../../../../../ncs:module[ncs:name='ciena-sync-gnss']";
      type gnss:gnss-antenna-input-leafref-type;
      description
        "List of GNSS inputs that shall be considered as candidates
         for selection in time-of-day protection-group.";
    }
    leaf threshold-quality-level {
      tailf:ncs-device-type "netconf";
      tailf:display-when "not(../../../../../ncs:module) or ../../../../../ncs:module[ncs:name='ciena-sync-gnss']";
      type sync:quality-level-type;
      description
        "Threshold quality-level configuration of time-of-day protection-group.
         Forced quality-level of input added to this
         protection-group must satisfy the configured threshold quality-level
         in order to be considered selectable.";
    }
  }
  augment "/ncs:devices/ncs:device/ncs:live-status/sync:sync-state" {
    description
      "GNSS global state.";
    container gnss-global {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      description
        "GNSS global state container.";
      leaf serial-number {
        type gnss:live_ncs_string-type;
        description
          "Serial number of GNSS device.";
      }
      leaf firmware-version {
        type gnss:live_ncs_string-type;
        description
          "Firmware version of GNSS device.";
      }
      leaf antenna-status {
        type gnss:live_ncs_antenna-cable-status-type;
        description
          "GNSS antenna status.";
      }
      leaf almanac-status {
        type gnss:live_ncs_almanac-status-type;
        description
          "Almanac status.";
      }
    }
  }
  augment "/ncs:devices/ncs:device/ncs:live-status/sync:sync-state" {
    description
      "Almanac data.";
    container almanac {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      description
        "Almanac data.";
      list satellite {
        key "prn";
        description
          "A list of all satellites available in the almanac.";
        leaf prn {
          type uint8;
          description
            "Satellite unique Pseudo-Random Noise number.";
        }
        leaf t_oa_raw {
          type uint8;
          description
            "Raw almanac reference time. ";
          reference "IS-GPS-200: GPS Interface Specification";
        }
        leaf sv_health {
          type uint8;
          description
            "Satellite Vehicle health word. ";
          reference "IS-GPS-200: GPS Interface Specification";
        }
        leaf e {
          type live_ncs_float;
          description
            "Eccentricity. ";
          reference "IS-GPS-200: GPS Interface Specification";
        }
        leaf t_oa {
          type live_ncs_float;
          description
            "Almanac reference time. ";
          reference "IS-GPS-200: GPS Interface Specification";
        }
        leaf i_o {
          type live_ncs_float;
          description
            "Inclination angle at reference time. ";
          reference "IS-GPS-200: GPS Interface Specification";
        }
        leaf omegadot {
          type live_ncs_float;
          description
            "Rate of right ascension. ";
          reference "IS-GPS-200: GPS Interface Specification";
        }
        leaf sqrt_a {
          type live_ncs_float;
          description
            "Square root of the semi-major axis. ";
          reference "IS-GPS-200: GPS Interface Specification";
        }
        leaf omega_0 {
          type live_ncs_float;
          description
            "Longitude of ascending node of orbit plane at weekly epoch. ";
          reference "IS-GPS-200: GPS Interface Specification";
        }
        leaf omega {
          type live_ncs_float;
          description
            "Argument of perigee. ";
          reference "IS-GPS-200: GPS Interface Specification";
        }
        leaf m_0 {
          type live_ncs_float;
          description
            "Mean anomaly at reference time. ";
          reference "IS-GPS-200: GPS Interface Specification";
        }
        leaf a_f0 {
          type live_ncs_float;
          description
            "Satellite Vehicle clock bias correction coefficient. ";
          reference "IS-GPS-200: GPS Interface Specification";
        }
        leaf a_f1 {
          type live_ncs_float;
          description
            "Satellite vehicle clock drift correction coefficient. ";
          reference "IS-GPS-200: GPS Interface Specification";
        }
        leaf axis {
          type live_ncs_float;
          description
            "Semi-major axis. ";
          reference "IS-GPS-200: GPS Interface Specification";
        }
        leaf n {
          type live_ncs_float;
          description
            "Corrected mean motion. ";
          reference "IS-GPS-200: GPS Interface Specification";
        }
        leaf omega_n {
          type live_ncs_float;
          description
            "Corrected longitude of ascending node. ";
          reference "IS-GPS-200: GPS Interface Specification";
        }
        leaf odot_n {
          type live_ncs_float;
          description
            "Rate of inclination angle. ";
          reference "IS-GPS-200: GPS Interface Specification";
        }
        leaf t_zc {
          type live_ncs_float;
          description
            "Time from almanac reference time. ";
          reference "IS-GPS-200: GPS Interface Specification";
        }
        leaf week-number {
          type uint16;
          description
            "Week number. ";
          reference "IS-GPS-200: GPS Interface Specification";
        }
        leaf wn_oa {
          type uint16;
          description
            "Almanac week number. ";
          reference "IS-GPS-200: GPS Interface Specification";
        }
      }
    }
  }
  augment "/ncs:devices/ncs:device/ncs:live-status/sync:sync-state" {
    description
      "Satellite ephemeris data.";
    container ephemeris {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      description
        "Satellite ephemeris data container.";
      list satellite {
        key "prn";
        description
          "A list of all visible satellites per configured constellation.";
        leaf prn {
          type uint8;
          description
            "Satellite unique Pseudo-Random Noise number.";
        }
        leaf channel {
          type uint8;
          description
            "Channel number.";
        }
        leaf acquired {
          type gnss:live_ncs_acquired-type;
          description
            "Satellite acquired or not.";
        }
        leaf sv-type {
          type gnss:live_ncs_sv-type;
          description
            "Satellite Vehicle type.";
        }
        leaf signal-level {
          type live_ncs_float;
          units "db-Hz";
          description
            "Signal level in db-Hz.";
        }
        leaf time-of-last-measurement {
          type live_ncs_float;
          units "seconds";
          description
            "Time of last measurement.";
        }
        leaf elevation-angle {
          type live_ncs_float;
          units "degree";
          description
            "Elevation angle.";
        }
        leaf azimuth-angle {
          type live_ncs_float;
          units "degree";
          description
            "Azimuth angle.";
        }
        leaf timing-fix {
          type boolean;
          description
            "Used in timing fix.";
        }
        leaf position-fix {
          type boolean;
          description
            "Used in position fix.";
        }
      }
    }
  }
  augment "/ncs:devices/ncs:device/ncs:live-status/sync:sync-state/sync:input-references" {
    description
      "GNSS antenna input state.";
    list gnss-antenna-input {
      tailf:ncs-device-type "netconf";
      tailf:display-when "not(../../../ncs:module) or ../../../ncs:module[ncs:name='ciena-sync-gnss'] or (../../../ncs:live-status-protocol[not(ncs:capability)]) or (../../../ncs:live-status-protocol/ncs:capability/ncs:module[.='ciena-sync-gnss'])";
      key "name";
      description
        "A list of all GNSS antenna input state entries.";
      leaf name {
        type gnss:live_ncs_gnss-antenna-input-leafref-type;
        description
          "Name of GNSS antenna input.";
      }
      leaf antenna-signal-condition {
        type gnss:live_ncs_antenna-signal-condition-type;
        description
          "GNSS antenna signal condition.";
      }
      leaf oper-state {
        type gnss:live_ncs_gnss-oper-state-type;
        description
          "Current GNSS state.";
      }
      container time-and-position {
        description
          "Current time and location of GNSS antenna.";
        leaf current-time {
          type yang:date-and-time;
          description
            "Current GNSS time.";
        }
        leaf latitude {
          type gnss:live_ncs_float;
          units "degree";
          description
            "Antenna latitude in degrees.";
        }
        leaf longitude {
          type gnss:live_ncs_float;
          units "degree";
          description
            "Antenna longitude in degrees.";
        }
        leaf altitude {
          type gnss:live_ncs_float;
          units "meters";
          description
            "Antenna altitude in meters.";
        }
      }
    }
  }
  augment "/ncs:devices/ncs:device/ncs:live-status/sync:sync-state/sync:protection-groups/sync:frequency-protection-group" {
    description
      "GNSS antenna input selected in frequency protection-group.";
    leaf selected-gnss-antenna-input-name {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "GNSS antenna input name.";
    }
  }
  augment "/ncs:devices/ncs:device/ncs:live-status/sync:sync-state/sync:protection-groups/sync:phase-protection-group" {
    description
      "GNSS antenna input selected in phase protection-group.";
    leaf selected-gnss-antenna-input-name {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "GNSS antenna input name.";
    }
  }
  augment "/ncs:devices/ncs:device/ncs:live-status/sync:sync-state/sync:protection-groups/sync:tod-protection-group" {
    description
      "GNSS antenna input selected in time-of-day protection-group.";
    leaf selected-gnss-antenna-input-name {
      tailf:ncs-device-type "netconf";
      tailf:display-when "not(../../../../../ncs:module) or ../../../../../ncs:module[ncs:name='ciena-sync-gnss'] or (../../../../../ncs:live-status-protocol[not(ncs:capability)]) or (../../../../../ncs:live-status-protocol/ncs:capability/ncs:module[.='ciena-sync-gnss'])";
      type gnss:live_ncs_gnss-antenna-input-leafref-type;
      description
        "GNSS antenna input name.";
    }
  }
  augment "/ncs:devices/ncs:device/ncs:rpc/sync:rpc-sync-protection-group-selection-force-switch/sync:sync-protection-group-selection-force-switch/sync:input" {
    description
      "Force-switch a GNSS antenna input selection on protection-group.";
    leaf gnss-antenna-input-name {
      type gnss:ncs_rpc_notif_gnss-antenna-input-leafref-type;
      description
        "Name of GNSS antenna input.";
    }
  }
  augment "/ncs:devices/ncs:device/ncs:netconf-notifications/ncs:received-notifications/ncs:notification/ncs:data/sync:frequency-protection-group-oper-state-change" {
    description
      "GNSS antenna input selected in frequency protection-group.";
    leaf selected-gnss-antenna-input-name {
      type gnss:ncs_rpc_notif_gnss-antenna-input-leafref-type;
      description
        "GNSS antenna input name.";
    }
  }
  augment "/ncs:devices/ncs:device/ncs:netconf-notifications/ncs:received-notifications/ncs:notification/ncs:data/sync:phase-protection-group-oper-state-change" {
    description
      "GNSS antenna input selected in phase protection-group.";
    leaf selected-gnss-antenna-input-name {
      type gnss:ncs_rpc_notif_gnss-antenna-input-leafref-type;
      description
        "GNSS antenna input name.";
    }
  }
  augment "/ncs:devices/ncs:device/ncs:netconf-notifications/ncs:received-notifications/ncs:notification/ncs:data/sync:tod-protection-group-oper-state-change" {
    description
      "GNSS antenna input selected in time-of-day protection-group.";
    leaf selected-gnss-antenna-input-name {
      type gnss:ncs_rpc_notif_gnss-antenna-input-leafref-type;
      description
        "GNSS antenna input name.";
    }
  }

  identity locked {
    base gnss:sync-gnss-oper-state-identity;
    description
      "GNSS alamanc is now completly built and a timing and position fix are now available.";
  }

  identity acquiring-lock {
    base gnss:sync-gnss-oper-state-identity;
    description
      "GNSS has finished acquiring satellites and currently building the almanac of all acquired satellites. A timing and position fix are also being acquired.";
  }

  identity acquiring-satellites {
    base gnss:sync-gnss-oper-state-identity;
    description
      "GNSS antenna input is configured and currently acquiring satellites.";
  }

  identity sync-gnss-oper-state-identity {
    description
      "Base identity from which specific GNSS antenna input operational
       state types are derived.";
  }
}
