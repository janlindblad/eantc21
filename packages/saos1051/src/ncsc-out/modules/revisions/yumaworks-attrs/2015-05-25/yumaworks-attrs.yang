module yumaworks-attrs {
  // Generated by yanger -t ncs
  tailf:mount-id "saos1051-nc-1.0:saos1051-nc-1.0";
  tailf:ncs-device-type "netconf";

  namespace "http://yumaworks.com/ns/yumaworks-attrs";
  prefix ya;

  import ietf-yang-types {
    prefix yang;
  }
  import yuma-ncx {
    prefix ncx;
  }
  import yuma-types {
    prefix yt;
  }
  import tailf-common {
    prefix tailf;
  }
  import tailf-ncs {
    prefix ncs;
  }

  organization
    "YumaWorks, Inc.";
  contact
    "Support <support@yumaworks.com>";
  description
    "This module contains abstract object definitions for
     the last-modified and etag XML attributes.

     Copyright (c) 2013 - 2015 YumaWorks, Inc. All rights reserved.

     Redistribution and use in source and binary forms, with or
     without modification, is permitted pursuant to, and subject
     to the license terms contained in, the BSD 3-Clause License
     http://opensource.org/licenses/BSD-3-Clause";

  revision 2015-05-25 {
    description
      "Add fixed-value attribute leaf.";
  }
  revision 2014-10-16 {
    description
      "Add owner attribute leaf.";
  }
  revision 2014-05-04 {
    description
      "Add datapath and btype leafs";
  }
  revision 2013-02-28 {
    description
      "Initial version";
  }

  augment "/ncs:devices/ncs:device/ncs:config" {
    leaf last-modified {
      tailf:ncs-device-type "netconf";
      tailf:display-when "not(../../ncs:module) or ../../ncs:module[ncs:name='yumaworks-attrs']";
      ncx:abstract;
      ncx:hidden;
      type yang:date-and-time;
      description
        "Indicates the last-modified timestamp for the node containing
         this attribute.";
    }
    leaf etag {
      tailf:ncs-device-type "netconf";
      tailf:display-when "not(../../ncs:module) or ../../ncs:module[ncs:name='yumaworks-attrs']";
      ncx:abstract;
      ncx:hidden;
      type string;
      description
        "Contains the Entity Tag for the node containing this attribute.";
    }
    leaf datapath {
      tailf:ncs-device-type "netconf";
      tailf:display-when "not(../../ncs:module) or ../../ncs:module[ncs:name='yumaworks-attrs']";
      ncx:abstract;
      ncx:hidden;
      type string;
      description
        "Contains the object path expression for the data node object.";
    }
    leaf btype {
      tailf:ncs-device-type "netconf";
      tailf:display-when "not(../../ncs:module) or ../../ncs:module[ncs:name='yumaworks-attrs']";
      ncx:abstract;
      ncx:hidden;
      type uint8;
      description
        "Contains the basetype enumeration code for an object.
         Used in SIL-SA <key> nodes to allow proper conversion.";
    }
    leaf owner {
      tailf:ncs-device-type "netconf";
      tailf:display-when "not(../../ncs:module) or ../../ncs:module[ncs:name='yumaworks-attrs']";
      ncx:abstract;
      ncx:hidden;
      type yt:NcxName;
      description
        "Contains the owner name for a data node.";
    }
    leaf fixed-value {
      tailf:ncs-device-type "netconf";
      tailf:display-when "not(../../ncs:module) or ../../ncs:module[ncs:name='yumaworks-attrs']";
      ncx:abstract;
      ncx:hidden;
      type boolean;
      description
        "Indicates if a key value node in a get2 request is a
         fixed value for getnext purposes.  In this mode, some keys
         are provided as content-match nodes, but not all.
         The getnext walk applies to the fixed-value=false nodes.
         The caller must not increment a key value for a getnext
         callback if fixed-value=true.";
    }
  }
  augment "/ncs:devices/ncs:device/ncs:live-status" {
    leaf last-modified {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type yang:date-and-time;
      description
        "Indicates the last-modified timestamp for the node containing
         this attribute.";
    }
    leaf etag {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type string;
      description
        "Contains the Entity Tag for the node containing this attribute.";
    }
    leaf datapath {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type string;
      description
        "Contains the object path expression for the data node object.";
    }
    leaf btype {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type uint8;
      description
        "Contains the basetype enumeration code for an object.
         Used in SIL-SA <key> nodes to allow proper conversion.";
    }
    leaf owner {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type yt:live_ncs_NcxName;
      description
        "Contains the owner name for a data node.";
    }
    leaf fixed-value {
      tailf:ncs-device-type "netconf";
      tailf:display-when "not(../../ncs:module) or ../../ncs:module[ncs:name='yumaworks-attrs'] or (../../ncs:live-status-protocol[not(ncs:capability)]) or (../../ncs:live-status-protocol/ncs:capability/ncs:module[.='yumaworks-attrs'])";
      ncx:abstract;
      ncx:hidden;
      type boolean;
      description
        "Indicates if a key value node in a get2 request is a
         fixed value for getnext purposes.  In this mode, some keys
         are provided as content-match nodes, but not all.
         The getnext walk applies to the fixed-value=false nodes.
         The caller must not increment a key value for a getnext
         callback if fixed-value=true.";
    }
  }
  augment "/ncs:devices/ncs:template/ncs:ned-id/ncs:config" {
    leaf last-modified {
      ncx:abstract;
      ncx:hidden;
      type string;
      description
        "Indicates the last-modified timestamp for the node containing
         this attribute.";
    }
    leaf etag {
      ncx:abstract;
      ncx:hidden;
      type string;
      description
        "Contains the Entity Tag for the node containing this attribute.";
    }
    leaf datapath {
      ncx:abstract;
      ncx:hidden;
      type string;
      description
        "Contains the object path expression for the data node object.";
    }
    leaf btype {
      ncx:abstract;
      ncx:hidden;
      type string;
      description
        "Contains the basetype enumeration code for an object.
         Used in SIL-SA <key> nodes to allow proper conversion.";
    }
    leaf owner {
      ncx:abstract;
      ncx:hidden;
      type yt:ncs_template_NcxName;
      description
        "Contains the owner name for a data node.";
    }
    leaf fixed-value {
      ncx:abstract;
      ncx:hidden;
      type string;
      description
        "Indicates if a key value node in a get2 request is a
         fixed value for getnext purposes.  In this mode, some keys
         are provided as content-match nodes, but not all.
         The getnext walk applies to the fixed-value=false nodes.
         The caller must not increment a key value for a getnext
         callback if fixed-value=true.";
    }
  }
}
