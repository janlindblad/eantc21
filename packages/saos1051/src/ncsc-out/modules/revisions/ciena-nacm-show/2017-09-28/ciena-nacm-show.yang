module ciena-nacm-show {
  // Generated by yanger -t ncs
  tailf:mount-id "saos1051-nc-1.0:saos1051-nc-1.0";
  tailf:ncs-device-type "netconf";

  yang-version 1.1;
  namespace "http://www.ciena.com/ns/ciena-nacm-show";
  prefix ciena-nacm-show;

  import yangcli-pro {
    prefix yp;
  }
  import tailf-common {
    prefix tailf;
  }
  import tailf-ncs {
    prefix ncs;
  }

  description
    "Show command extensions by ciena for ciena-nacm";

  revision 2017-09-28 {
    description
      "Initial version";
  }

  augment "/ncs:devices/ncs:device/ncs:rpc/yp:rpc-show/yp:show/yp:input/yp:showtype" {
    case nacm {
      leaf nacm {
        type empty;
      }
    }
  }
}
