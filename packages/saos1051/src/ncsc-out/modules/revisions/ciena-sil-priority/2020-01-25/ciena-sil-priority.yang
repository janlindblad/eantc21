module ciena-sil-priority {
  // Generated by yanger -t ncs
  tailf:mount-id "saos1051-nc-1.0:saos1051-nc-1.0";
  tailf:ncs-device-type "netconf";

  yang-version 1;
  namespace "http://ciena.com/silpriority/yang/ciena-sil-priority";
  prefix ciena-sil-priority;

  import yumaworks-extensions {
    prefix ywx;
  }
  import ciena-bw-calculation-mode {
    prefix ciena-bw-calculation-mode;
  }
  import ciena-mef-access-flow {
    prefix acl;
  }
  import ciena-mef-classifier {
    prefix classifier;
  }
  import ciena-mef-cos-to-frame-map {
    prefix ctf;
  }
  import ciena-mef-egress-qos {
    prefix mef-egress-qos;
  }
  import ciena-mef-egress-qos-binding {
    prefix mef-egress-qos-binding;
  }
  import ciena-mef-fd {
    prefix mef-fd;
  }
  import ciena-mef-flood-containment-profile {
    prefix mef-fc;
  }
  import ciena-mef-fp {
    prefix mef-fp;
  }
  import ciena-mef-frame-to-cos-map {
    prefix ftc;
  }
  import ciena-mef-l2cp-profile {
    prefix mef-l2cp;
  }
  import ciena-mef-logical-port {
    prefix mef-logical-port;
  }
  import ciena-mef-mac-management {
    prefix mef-mac-management;
  }
  import ciena-mef-meter-profile {
    prefix meter;
  }
  import ciena-mef-pfg-profile {
    prefix mef-pfg;
  }
  import ciena-vrf {
    prefix vrf;
  }
  import openconfig-interfaces {
    prefix oc-if;
  }
  import ciena-routing-policy {
    prefix rt-pol;
  }
  import ciena-pon-ctrl {
    prefix pon-ctrl;
  }
  import ciena-sync {
    prefix sync;
  }
  import ciena-sync-ptp {
    prefix sync-ptp;
  }
  import ciena-sat {
    prefix ciena-sat;
  }
  import ciena-flexe {
    prefix ciena-flexe;
  }
  import openconfig-platform {
    prefix oc-platform;
  }
  import ciena-packet-xcvr {
    prefix cn-xcvr;
  }
  import ciena-packet-ptp {
    prefix cn-ptp;
  }
  import ciena-packet-otn-port {
    prefix cn-otn-port;
  }
  import ciena-of-vfsi {
    prefix of-vfsis;
  }
  import ciena-of-flow-tables {
    prefix of-flow-tables;
  }
  import ciena-of-group-tables {
    prefix of-group-tables;
  }
  import ciena-te {
    prefix te;
  }
  import ciena-sr-policy {
    prefix cnsr;
  }
  import ietf-pseudowires {
    prefix pw;
  }
  import ciena-l2vpn {
    prefix l2vpn;
  }
  import ciena-pkix {
    prefix pkix;
  }
  import ciena-tls {
    prefix tls;
  }
  import ciena-tls-service-profile {
    prefix tls-svc-pfl;
  }
  import ciena-evpn {
    prefix cnevpn;
  }
  import ciena-sr {
    prefix sr;
  }
  import ciena-tdm-global {
    prefix tdm-global;
  }
  import ciena-packet-tdm-port {
    prefix tdm-port;
  }
  import ciena-tdm-pseudowire {
    prefix tdm-pw;
  }
  import ciena-packet-pm {
    prefix cn-pm;
  }
  import ciena-vdisk-mgmt {
    prefix vdisk-mgmt;
  }
  import ciena-file-mgmt {
    prefix file-mgmt;
  }
  import ciena-sf {
    prefix sf;
  }
  import ciena-sfc {
    prefix sfc;
  }
  import ciena-nat {
    prefix cn-nat;
  }
  import ciena-subsystem-resource {
    prefix cn-sub-res;
  }
  import ciena-rss-queue {
    prefix cn-rss;
  }
  import ciena-mpls-tp-corouted {
    prefix tp-tunnel;
  }
  import ciena-bfd {
    prefix bfd;
  }
  import ciena-bfd-ip-sh {
    prefix bfd-ip-sh;
  }
  import ciena-bfd-ip-mh {
    prefix bfd-ip-mh;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This module contains the Ciena proprietary SIL priorities
     for all the Ciena YANG files.

     Copyright (c) 2017 Ciena Corporation.  All rights reserved.

     All information contained herein is, and remains
     the property of Ciena Corporation. Dissemination of this
     information or reproduction of this material is strictly
     forbidden unless prior written permission is obtained from
     Ciena Corporation.";

  revision 2020-01-25 {
    description
      "SIL priority for DNFVi yang models, vdisk, file-mgmt, sf, sfc, Subsystems, RSS Queue and Access Flow Yang models, \\
       Tp Tunnel yang models";
    reference "";
  }
  revision 2020-01-21 {
    description
      "SIL priority for xcvrs, ptps, otn-ports, pms, Evpn, Segment Routing, ciena-mef-qos-flow, \\
       TLS service profiles, and removing sil-priority for ciena-mef-mirror-session. \\
       Deleted cn-xcvr:properties and cn-xcvr:state";
    reference "";
  }
  revision 2019-09-12 {
    description
      "Added SIL priority for newly added container for cos-to-queue-map-associations in egress-qos module.";
    reference "";
  }
  revision 2018-09-04 {
    description
      "Initial version";
    reference "";
  }

  deviation "/ncs:devices/ncs:template/ncs:ned-id/ncs:config/oc-platform:components" {
    deviate add {
      ywx:sil-priority "10";
    }
  }
  deviation "/ncs:devices/ncs:device/ncs:live-status/oc-platform:components" {
    deviate add {
      ywx:sil-priority "10";
    }
  }
  deviation "/ncs:devices/ncs:device/ncs:config/oc-platform:components" {
    deviate add {
      ywx:sil-priority "10";
    }
  }
  deviation "/ncs:devices/ncs:template/ncs:ned-id/ncs:config/tdm-global:tdm-global" {
    deviate add {
      ywx:sil-priority "15";
    }
  }
  deviation "/ncs:devices/ncs:device/ncs:live-status/tdm-global:tdm-global" {
    deviate add {
      ywx:sil-priority "15";
    }
  }
  deviation "/ncs:devices/ncs:device/ncs:config/tdm-global:tdm-global" {
    deviate add {
      ywx:sil-priority "15";
    }
  }
  deviation "/ncs:devices/ncs:template/ncs:ned-id/ncs:config/ciena-bw-calculation-mode:bw-calculation-mode" {
    deviate add {
      ywx:sil-priority "20";
    }
  }
  deviation "/ncs:devices/ncs:device/ncs:live-status/ciena-bw-calculation-mode:bw-calculation-mode" {
    deviate add {
      ywx:sil-priority "20";
    }
  }
  deviation "/ncs:devices/ncs:device/ncs:config/ciena-bw-calculation-mode:bw-calculation-mode" {
    deviate add {
      ywx:sil-priority "20";
    }
  }
  deviation "/ncs:devices/ncs:template/ncs:ned-id/ncs:config/ctf:cos-to-frame-maps" {
    deviate add {
      ywx:sil-priority "20";
    }
  }
  deviation "/ncs:devices/ncs:device/ncs:live-status/ctf:cos-to-frame-maps" {
    deviate add {
      ywx:sil-priority "20";
    }
  }
  deviation "/ncs:devices/ncs:device/ncs:config/ctf:cos-to-frame-maps" {
    deviate add {
      ywx:sil-priority "20";
    }
  }
  deviation "/ncs:devices/ncs:template/ncs:ned-id/ncs:config/mef-l2cp:l2cp-profiles" {
    deviate add {
      ywx:sil-priority "20";
    }
  }
  deviation "/ncs:devices/ncs:device/ncs:live-status/mef-l2cp:l2cp-profiles" {
    deviate add {
      ywx:sil-priority "20";
    }
  }
  deviation "/ncs:devices/ncs:device/ncs:config/mef-l2cp:l2cp-profiles" {
    deviate add {
      ywx:sil-priority "20";
    }
  }
  deviation "/ncs:devices/ncs:template/ncs:ned-id/ncs:config/mef-pfg:pfg-profiles" {
    deviate add {
      ywx:sil-priority "20";
    }
  }
  deviation "/ncs:devices/ncs:device/ncs:live-status/mef-pfg:pfg-profiles" {
    deviate add {
      ywx:sil-priority "20";
    }
  }
  deviation "/ncs:devices/ncs:device/ncs:config/mef-pfg:pfg-profiles" {
    deviate add {
      ywx:sil-priority "20";
    }
  }
  deviation "/ncs:devices/ncs:template/ncs:ned-id/ncs:config/mef-fc:flood-containment-profiles" {
    deviate add {
      ywx:sil-priority "20";
    }
  }
  deviation "/ncs:devices/ncs:device/ncs:live-status/mef-fc:flood-containment-profiles" {
    deviate add {
      ywx:sil-priority "20";
    }
  }
  deviation "/ncs:devices/ncs:device/ncs:config/mef-fc:flood-containment-profiles" {
    deviate add {
      ywx:sil-priority "20";
    }
  }
  deviation "/ncs:devices/ncs:template/ncs:ned-id/ncs:config/acl:access-profiles" {
    deviate add {
      ywx:sil-priority "20";
    }
  }
  deviation "/ncs:devices/ncs:device/ncs:live-status/acl:access-profiles" {
    deviate add {
      ywx:sil-priority "20";
    }
  }
  deviation "/ncs:devices/ncs:device/ncs:config/acl:access-profiles" {
    deviate add {
      ywx:sil-priority "20";
    }
  }
  deviation "/ncs:devices/ncs:template/ncs:ned-id/ncs:config/ftc:frame-to-cos-maps" {
    deviate add {
      ywx:sil-priority "20";
    }
  }
  deviation "/ncs:devices/ncs:device/ncs:live-status/ftc:frame-to-cos-maps" {
    deviate add {
      ywx:sil-priority "20";
    }
  }
  deviation "/ncs:devices/ncs:device/ncs:config/ftc:frame-to-cos-maps" {
    deviate add {
      ywx:sil-priority "20";
    }
  }
  deviation "/ncs:devices/ncs:template/ncs:ned-id/ncs:config/meter:meter-profiles" {
    deviate add {
      ywx:sil-priority "20";
    }
  }
  deviation "/ncs:devices/ncs:device/ncs:live-status/meter:meter-profiles" {
    deviate add {
      ywx:sil-priority "20";
    }
  }
  deviation "/ncs:devices/ncs:device/ncs:config/meter:meter-profiles" {
    deviate add {
      ywx:sil-priority "20";
    }
  }
  deviation "/ncs:devices/ncs:template/ncs:ned-id/ncs:config/mef-mac-management:mac-management" {
    deviate add {
      ywx:sil-priority "20";
    }
  }
  deviation "/ncs:devices/ncs:device/ncs:live-status/mef-mac-management:mac-management" {
    deviate add {
      ywx:sil-priority "20";
    }
  }
  deviation "/ncs:devices/ncs:device/ncs:config/mef-mac-management:mac-management" {
    deviate add {
      ywx:sil-priority "20";
    }
  }
  deviation "/ncs:devices/ncs:template/ncs:ned-id/ncs:config/cn-xcvr:xcvrs" {
    deviate add {
      ywx:sil-priority "20";
    }
  }
  deviation "/ncs:devices/ncs:device/ncs:live-status/cn-xcvr:xcvrs" {
    deviate add {
      ywx:sil-priority "20";
    }
  }
  deviation "/ncs:devices/ncs:device/ncs:config/cn-xcvr:xcvrs" {
    deviate add {
      ywx:sil-priority "20";
    }
  }
  deviation "/ncs:devices/ncs:template/ncs:ned-id/ncs:config/cn-ptp:ptps" {
    deviate add {
      ywx:sil-priority "25";
    }
  }
  deviation "/ncs:devices/ncs:device/ncs:live-status/cn-ptp:ptps" {
    deviate add {
      ywx:sil-priority "25";
    }
  }
  deviation "/ncs:devices/ncs:device/ncs:config/cn-ptp:ptps" {
    deviate add {
      ywx:sil-priority "25";
    }
  }
  deviation "/ncs:devices/ncs:template/ncs:ned-id/ncs:config/cn-otn-port:otn-ports" {
    deviate add {
      ywx:sil-priority "26";
    }
  }
  deviation "/ncs:devices/ncs:device/ncs:live-status/cn-otn-port:otn-ports" {
    deviate add {
      ywx:sil-priority "26";
    }
  }
  deviation "/ncs:devices/ncs:device/ncs:config/cn-otn-port:otn-ports" {
    deviate add {
      ywx:sil-priority "26";
    }
  }
  deviation "/ncs:devices/ncs:template/ncs:ned-id/ncs:config/ciena-flexe:flexe-ports" {
    deviate add {
      ywx:sil-priority "26";
    }
  }
  deviation "/ncs:devices/ncs:device/ncs:live-status/ciena-flexe:flexe-ports" {
    deviate add {
      ywx:sil-priority "26";
    }
  }
  deviation "/ncs:devices/ncs:device/ncs:config/ciena-flexe:flexe-ports" {
    deviate add {
      ywx:sil-priority "26";
    }
  }
  deviation "/ncs:devices/ncs:template/ncs:ned-id/ncs:config/cn-pm:pm" {
    deviate add {
      ywx:sil-priority "27";
    }
  }
  deviation "/ncs:devices/ncs:device/ncs:live-status/cn-pm:pm" {
    deviate add {
      ywx:sil-priority "27";
    }
  }
  deviation "/ncs:devices/ncs:device/ncs:config/cn-pm:pm" {
    deviate add {
      ywx:sil-priority "27";
    }
  }
  deviation "/ncs:devices/ncs:template/ncs:ned-id/ncs:config/mef-fd:fds" {
    deviate add {
      ywx:sil-priority "30";
    }
  }
  deviation "/ncs:devices/ncs:device/ncs:live-status/mef-fd:fds" {
    deviate add {
      ywx:sil-priority "30";
    }
  }
  deviation "/ncs:devices/ncs:device/ncs:config/mef-fd:fds" {
    deviate add {
      ywx:sil-priority "30";
    }
  }
  deviation "/ncs:devices/ncs:template/ncs:ned-id/ncs:config/vrf:vrf" {
    deviate add {
      ywx:sil-priority "30";
    }
  }
  deviation "/ncs:devices/ncs:device/ncs:live-status/vrf:vrf" {
    deviate add {
      ywx:sil-priority "30";
    }
  }
  deviation "/ncs:devices/ncs:device/ncs:config/vrf:vrf" {
    deviate add {
      ywx:sil-priority "30";
    }
  }
  deviation "/ncs:devices/ncs:template/ncs:ned-id/ncs:config/tls:hello-params" {
    deviate add {
      ywx:sil-priority "35";
    }
  }
  deviation "/ncs:devices/ncs:device/ncs:live-status/tls:hello-params" {
    deviate add {
      ywx:sil-priority "35";
    }
  }
  deviation "/ncs:devices/ncs:device/ncs:config/tls:hello-params" {
    deviate add {
      ywx:sil-priority "35";
    }
  }
  deviation "/ncs:devices/ncs:template/ncs:ned-id/ncs:config/pkix:pkix" {
    deviate add {
      ywx:sil-priority "35";
    }
  }
  deviation "/ncs:devices/ncs:device/ncs:live-status/pkix:pkix" {
    deviate add {
      ywx:sil-priority "35";
    }
  }
  deviation "/ncs:devices/ncs:device/ncs:config/pkix:pkix" {
    deviate add {
      ywx:sil-priority "35";
    }
  }
  deviation "/ncs:devices/ncs:template/ncs:ned-id/ncs:config/ciena-flexe:flexe-groups" {
    deviate add {
      ywx:sil-priority "35";
    }
  }
  deviation "/ncs:devices/ncs:device/ncs:live-status/ciena-flexe:flexe-groups" {
    deviate add {
      ywx:sil-priority "35";
    }
  }
  deviation "/ncs:devices/ncs:device/ncs:config/ciena-flexe:flexe-groups" {
    deviate add {
      ywx:sil-priority "35";
    }
  }
  deviation "/ncs:devices/ncs:template/ncs:ned-id/ncs:config/tls-svc-pfl:tls-service-profiles" {
    deviate add {
      ywx:sil-priority "40";
    }
  }
  deviation "/ncs:devices/ncs:device/ncs:live-status/tls-svc-pfl:tls-service-profiles" {
    deviate add {
      ywx:sil-priority "40";
    }
  }
  deviation "/ncs:devices/ncs:device/ncs:config/tls-svc-pfl:tls-service-profiles" {
    deviate add {
      ywx:sil-priority "40";
    }
  }
  deviation "/ncs:devices/ncs:template/ncs:ned-id/ncs:config/ciena-flexe:flexe-channels" {
    deviate add {
      ywx:sil-priority "40";
    }
  }
  deviation "/ncs:devices/ncs:device/ncs:live-status/ciena-flexe:flexe-channels" {
    deviate add {
      ywx:sil-priority "40";
    }
  }
  deviation "/ncs:devices/ncs:device/ncs:config/ciena-flexe:flexe-channels" {
    deviate add {
      ywx:sil-priority "40";
    }
  }
  deviation "/ncs:devices/ncs:template/ncs:ned-id/ncs:config/oc-if:interfaces" {
    deviate add {
      ywx:sil-priority "50";
    }
  }
  deviation "/ncs:devices/ncs:device/ncs:live-status/oc-if:interfaces" {
    deviate add {
      ywx:sil-priority "50";
    }
  }
  deviation "/ncs:devices/ncs:device/ncs:config/oc-if:interfaces" {
    deviate add {
      ywx:sil-priority "50";
    }
  }
  deviation "/ncs:devices/ncs:template/ncs:ned-id/ncs:config/rt-pol:routing-policy" {
    deviate add {
      ywx:sil-priority "51";
    }
  }
  deviation "/ncs:devices/ncs:device/ncs:live-status/rt-pol:routing-policy" {
    deviate add {
      ywx:sil-priority "51";
    }
  }
  deviation "/ncs:devices/ncs:device/ncs:config/rt-pol:routing-policy" {
    deviate add {
      ywx:sil-priority "51";
    }
  }
  deviation "/ncs:devices/ncs:template/ncs:ned-id/ncs:config/classifier:classifiers" {
    deviate add {
      ywx:sil-priority "60";
    }
  }
  deviation "/ncs:devices/ncs:device/ncs:live-status/classifier:classifiers" {
    deviate add {
      ywx:sil-priority "60";
    }
  }
  deviation "/ncs:devices/ncs:device/ncs:config/classifier:classifiers" {
    deviate add {
      ywx:sil-priority "60";
    }
  }
  deviation "/ncs:devices/ncs:template/ncs:ned-id/ncs:config/acl:acl-actions" {
    deviate add {
      ywx:sil-priority "60";
    }
  }
  deviation "/ncs:devices/ncs:device/ncs:live-status/acl:acl-actions" {
    deviate add {
      ywx:sil-priority "60";
    }
  }
  deviation "/ncs:devices/ncs:device/ncs:config/acl:acl-actions" {
    deviate add {
      ywx:sil-priority "60";
    }
  }
  deviation "/ncs:devices/ncs:template/ncs:ned-id/ncs:config/mef-logical-port:logical-ports" {
    deviate add {
      ywx:sil-priority "60";
    }
  }
  deviation "/ncs:devices/ncs:device/ncs:live-status/mef-logical-port:logical-ports" {
    deviate add {
      ywx:sil-priority "60";
    }
  }
  deviation "/ncs:devices/ncs:device/ncs:config/mef-logical-port:logical-ports" {
    deviate add {
      ywx:sil-priority "60";
    }
  }
  deviation "/ncs:devices/ncs:template/ncs:ned-id/ncs:config/cn-nat:nat" {
    deviate add {
      ywx:sil-priority "60";
    }
  }
  deviation "/ncs:devices/ncs:device/ncs:live-status/cn-nat:nat" {
    deviate add {
      ywx:sil-priority "60";
    }
  }
  deviation "/ncs:devices/ncs:device/ncs:config/cn-nat:nat" {
    deviate add {
      ywx:sil-priority "60";
    }
  }
  deviation "/ncs:devices/ncs:template/ncs:ned-id/ncs:config/mef-egress-qos:egress-qos" {
    deviate add {
      ywx:sil-priority "70";
    }
  }
  deviation "/ncs:devices/ncs:device/ncs:live-status/mef-egress-qos:egress-qos" {
    deviate add {
      ywx:sil-priority "70";
    }
  }
  deviation "/ncs:devices/ncs:device/ncs:config/mef-egress-qos:egress-qos" {
    deviate add {
      ywx:sil-priority "70";
    }
  }
  deviation "/ncs:devices/ncs:template/ncs:ned-id/ncs:config/ciena-flexe:flexe-cross-connects" {
    deviate add {
      ywx:sil-priority "70";
    }
  }
  deviation "/ncs:devices/ncs:device/ncs:live-status/ciena-flexe:flexe-cross-connects" {
    deviate add {
      ywx:sil-priority "70";
    }
  }
  deviation "/ncs:devices/ncs:device/ncs:config/ciena-flexe:flexe-cross-connects" {
    deviate add {
      ywx:sil-priority "70";
    }
  }
  deviation "/ncs:devices/ncs:template/ncs:ned-id/ncs:config/mef-egress-qos:egress-qos/mef-egress-qos:cos-queue-map" {
    deviate add {
      ywx:sil-priority "10";
    }
  }
  deviation "/ncs:devices/ncs:device/ncs:live-status/mef-egress-qos:egress-qos/mef-egress-qos:cos-queue-map" {
    deviate add {
      ywx:sil-priority "10";
    }
  }
  deviation "/ncs:devices/ncs:device/ncs:config/mef-egress-qos:egress-qos/mef-egress-qos:cos-queue-map" {
    deviate add {
      ywx:sil-priority "10";
    }
  }
  deviation "/ncs:devices/ncs:template/ncs:ned-id/ncs:config/mef-egress-qos:egress-qos/mef-egress-qos:congestion-avoidance-profile" {
    deviate add {
      ywx:sil-priority "10";
    }
  }
  deviation "/ncs:devices/ncs:device/ncs:live-status/mef-egress-qos:egress-qos/mef-egress-qos:congestion-avoidance-profile" {
    deviate add {
      ywx:sil-priority "10";
    }
  }
  deviation "/ncs:devices/ncs:device/ncs:config/mef-egress-qos:egress-qos/mef-egress-qos:congestion-avoidance-profile" {
    deviate add {
      ywx:sil-priority "10";
    }
  }
  deviation "/ncs:devices/ncs:template/ncs:ned-id/ncs:config/mef-egress-qos:egress-qos/mef-egress-qos:scheduler-profile" {
    deviate add {
      ywx:sil-priority "10";
    }
  }
  deviation "/ncs:devices/ncs:device/ncs:live-status/mef-egress-qos:egress-qos/mef-egress-qos:scheduler-profile" {
    deviate add {
      ywx:sil-priority "10";
    }
  }
  deviation "/ncs:devices/ncs:device/ncs:config/mef-egress-qos:egress-qos/mef-egress-qos:scheduler-profile" {
    deviate add {
      ywx:sil-priority "10";
    }
  }
  deviation "/ncs:devices/ncs:template/ncs:ned-id/ncs:config/mef-egress-qos:egress-qos/mef-egress-qos:queue-group-profile" {
    deviate add {
      ywx:sil-priority "20";
    }
  }
  deviation "/ncs:devices/ncs:device/ncs:live-status/mef-egress-qos:egress-qos/mef-egress-qos:queue-group-profile" {
    deviate add {
      ywx:sil-priority "20";
    }
  }
  deviation "/ncs:devices/ncs:device/ncs:config/mef-egress-qos:egress-qos/mef-egress-qos:queue-group-profile" {
    deviate add {
      ywx:sil-priority "20";
    }
  }
  deviation "/ncs:devices/ncs:template/ncs:ned-id/ncs:config/mef-egress-qos:egress-qos/mef-egress-qos:scheduler" {
    deviate add {
      ywx:sil-priority "30";
    }
  }
  deviation "/ncs:devices/ncs:device/ncs:live-status/mef-egress-qos:egress-qos/mef-egress-qos:scheduler" {
    deviate add {
      ywx:sil-priority "30";
    }
  }
  deviation "/ncs:devices/ncs:device/ncs:config/mef-egress-qos:egress-qos/mef-egress-qos:scheduler" {
    deviate add {
      ywx:sil-priority "30";
    }
  }
  deviation "/ncs:devices/ncs:template/ncs:ned-id/ncs:config/mef-egress-qos:egress-qos/mef-egress-qos:queue-group" {
    deviate add {
      ywx:sil-priority "40";
    }
  }
  deviation "/ncs:devices/ncs:device/ncs:live-status/mef-egress-qos:egress-qos/mef-egress-qos:queue-group" {
    deviate add {
      ywx:sil-priority "40";
    }
  }
  deviation "/ncs:devices/ncs:device/ncs:config/mef-egress-qos:egress-qos/mef-egress-qos:queue-group" {
    deviate add {
      ywx:sil-priority "40";
    }
  }
  deviation "/ncs:devices/ncs:template/ncs:ned-id/ncs:config/of-vfsis:of-vfsis" {
    deviate add {
      ywx:sil-priority "70";
    }
  }
  deviation "/ncs:devices/ncs:device/ncs:live-status/of-vfsis:of-vfsis" {
    deviate add {
      ywx:sil-priority "70";
    }
  }
  deviation "/ncs:devices/ncs:device/ncs:config/of-vfsis:of-vfsis" {
    deviate add {
      ywx:sil-priority "70";
    }
  }
  deviation "/ncs:devices/ncs:template/ncs:ned-id/ncs:config/mef-egress-qos:cos-to-queue-map-associations" {
    deviate add {
      ywx:sil-priority "80";
    }
  }
  deviation "/ncs:devices/ncs:device/ncs:live-status/mef-egress-qos:cos-to-queue-map-associations" {
    deviate add {
      ywx:sil-priority "80";
    }
  }
  deviation "/ncs:devices/ncs:device/ncs:config/mef-egress-qos:cos-to-queue-map-associations" {
    deviate add {
      ywx:sil-priority "80";
    }
  }
  deviation "/ncs:devices/ncs:template/ncs:ned-id/ncs:config/mef-egress-qos-binding:interface-qos-binding" {
    deviate add {
      ywx:sil-priority "80";
    }
  }
  deviation "/ncs:devices/ncs:device/ncs:live-status/mef-egress-qos-binding:interface-qos-binding" {
    deviate add {
      ywx:sil-priority "80";
    }
  }
  deviation "/ncs:devices/ncs:device/ncs:config/mef-egress-qos-binding:interface-qos-binding" {
    deviate add {
      ywx:sil-priority "80";
    }
  }
  deviation "/ncs:devices/ncs:template/ncs:ned-id/ncs:config/mef-mac-management:fdbs" {
    deviate add {
      ywx:sil-priority "80";
    }
  }
  deviation "/ncs:devices/ncs:device/ncs:live-status/mef-mac-management:fdbs" {
    deviate add {
      ywx:sil-priority "80";
    }
  }
  deviation "/ncs:devices/ncs:device/ncs:config/mef-mac-management:fdbs" {
    deviate add {
      ywx:sil-priority "80";
    }
  }
  deviation "/ncs:devices/ncs:template/ncs:ned-id/ncs:config/of-group-tables:of-group-tables" {
    deviate add {
      ywx:sil-priority "80";
    }
  }
  deviation "/ncs:devices/ncs:device/ncs:live-status/of-group-tables:of-group-tables" {
    deviate add {
      ywx:sil-priority "80";
    }
  }
  deviation "/ncs:devices/ncs:device/ncs:config/of-group-tables:of-group-tables" {
    deviate add {
      ywx:sil-priority "80";
    }
  }
  deviation "/ncs:devices/ncs:template/ncs:ned-id/ncs:config/of-group-tables:of-group-tables/of-group-tables:of-group-table" {
    deviate add {
      ywx:sil-priority "10";
    }
  }
  deviation "/ncs:devices/ncs:device/ncs:live-status/of-group-tables:of-group-tables/of-group-tables:of-group-table" {
    deviate add {
      ywx:sil-priority "10";
    }
  }
  deviation "/ncs:devices/ncs:device/ncs:config/of-group-tables:of-group-tables/of-group-tables:of-group-table" {
    deviate add {
      ywx:sil-priority "10";
    }
  }
  deviation "/ncs:devices/ncs:template/ncs:ned-id/ncs:config/of-group-tables:of-group-tables/of-group-tables:of-group-table-entry" {
    deviate add {
      ywx:sil-priority "20";
    }
  }
  deviation "/ncs:devices/ncs:device/ncs:live-status/of-group-tables:of-group-tables/of-group-tables:of-group-table-entry" {
    deviate add {
      ywx:sil-priority "20";
    }
  }
  deviation "/ncs:devices/ncs:device/ncs:config/of-group-tables:of-group-tables/of-group-tables:of-group-table-entry" {
    deviate add {
      ywx:sil-priority "20";
    }
  }
  deviation "/ncs:devices/ncs:template/ncs:ned-id/ncs:config/tdm-port:tdm-ports" {
    deviate add {
      ywx:sil-priority "80";
    }
  }
  deviation "/ncs:devices/ncs:device/ncs:live-status/tdm-port:tdm-ports" {
    deviate add {
      ywx:sil-priority "80";
    }
  }
  deviation "/ncs:devices/ncs:device/ncs:config/tdm-port:tdm-ports" {
    deviate add {
      ywx:sil-priority "80";
    }
  }
  deviation "/ncs:devices/ncs:template/ncs:ned-id/ncs:config/mef-fp:fps" {
    deviate add {
      ywx:sil-priority "90";
    }
  }
  deviation "/ncs:devices/ncs:device/ncs:live-status/mef-fp:fps" {
    deviate add {
      ywx:sil-priority "90";
    }
  }
  deviation "/ncs:devices/ncs:device/ncs:config/mef-fp:fps" {
    deviate add {
      ywx:sil-priority "90";
    }
  }
  deviation "/ncs:devices/ncs:template/ncs:ned-id/ncs:config/of-flow-tables:of-flow-tables" {
    deviate add {
      ywx:sil-priority "90";
    }
  }
  deviation "/ncs:devices/ncs:device/ncs:live-status/of-flow-tables:of-flow-tables" {
    deviate add {
      ywx:sil-priority "90";
    }
  }
  deviation "/ncs:devices/ncs:device/ncs:config/of-flow-tables:of-flow-tables" {
    deviate add {
      ywx:sil-priority "90";
    }
  }
  deviation "/ncs:devices/ncs:template/ncs:ned-id/ncs:config/of-flow-tables:of-flow-tables/of-flow-tables:of-flow-table" {
    deviate add {
      ywx:sil-priority "10";
    }
  }
  deviation "/ncs:devices/ncs:device/ncs:live-status/of-flow-tables:of-flow-tables/of-flow-tables:of-flow-table" {
    deviate add {
      ywx:sil-priority "10";
    }
  }
  deviation "/ncs:devices/ncs:device/ncs:config/of-flow-tables:of-flow-tables/of-flow-tables:of-flow-table" {
    deviate add {
      ywx:sil-priority "10";
    }
  }
  deviation "/ncs:devices/ncs:template/ncs:ned-id/ncs:config/of-flow-tables:of-flow-tables/of-flow-tables:of-flow-table-entry" {
    deviate add {
      ywx:sil-priority "20";
    }
  }
  deviation "/ncs:devices/ncs:device/ncs:live-status/of-flow-tables:of-flow-tables/of-flow-tables:of-flow-table-entry" {
    deviate add {
      ywx:sil-priority "20";
    }
  }
  deviation "/ncs:devices/ncs:device/ncs:config/of-flow-tables:of-flow-tables/of-flow-tables:of-flow-table-entry" {
    deviate add {
      ywx:sil-priority "20";
    }
  }
  deviation "/ncs:devices/ncs:template/ncs:ned-id/ncs:config/acl:acl-custom-destinations" {
    deviate add {
      ywx:sil-priority "100";
    }
  }
  deviation "/ncs:devices/ncs:device/ncs:live-status/acl:acl-custom-destinations" {
    deviate add {
      ywx:sil-priority "100";
    }
  }
  deviation "/ncs:devices/ncs:device/ncs:config/acl:acl-custom-destinations" {
    deviate add {
      ywx:sil-priority "100";
    }
  }
  deviation "/ncs:devices/ncs:template/ncs:ned-id/ncs:config/mef-mac-management:static-macs" {
    deviate add {
      ywx:sil-priority "100";
    }
  }
  deviation "/ncs:devices/ncs:device/ncs:live-status/mef-mac-management:static-macs" {
    deviate add {
      ywx:sil-priority "100";
    }
  }
  deviation "/ncs:devices/ncs:device/ncs:config/mef-mac-management:static-macs" {
    deviate add {
      ywx:sil-priority "100";
    }
  }
  deviation "/ncs:devices/ncs:template/ncs:ned-id/ncs:config/vdisk-mgmt:vdisks" {
    deviate add {
      ywx:sil-priority "100";
    }
  }
  deviation "/ncs:devices/ncs:device/ncs:live-status/vdisk-mgmt:vdisks" {
    deviate add {
      ywx:sil-priority "100";
    }
  }
  deviation "/ncs:devices/ncs:device/ncs:config/vdisk-mgmt:vdisks" {
    deviate add {
      ywx:sil-priority "100";
    }
  }
  deviation "/ncs:devices/ncs:template/ncs:ned-id/ncs:config/cn-sub-res:subsystems" {
    deviate add {
      ywx:sil-priority "100";
    }
  }
  deviation "/ncs:devices/ncs:device/ncs:live-status/cn-sub-res:subsystems" {
    deviate add {
      ywx:sil-priority "100";
    }
  }
  deviation "/ncs:devices/ncs:device/ncs:config/cn-sub-res:subsystems" {
    deviate add {
      ywx:sil-priority "100";
    }
  }
  deviation "/ncs:devices/ncs:template/ncs:ned-id/ncs:config/file-mgmt:files" {
    deviate add {
      ywx:sil-priority "101";
    }
  }
  deviation "/ncs:devices/ncs:device/ncs:live-status/file-mgmt:files" {
    deviate add {
      ywx:sil-priority "101";
    }
  }
  deviation "/ncs:devices/ncs:device/ncs:config/file-mgmt:files" {
    deviate add {
      ywx:sil-priority "101";
    }
  }
  deviation "/ncs:devices/ncs:template/ncs:ned-id/ncs:config/sfc:sffs" {
    deviate add {
      ywx:sil-priority "103";
    }
  }
  deviation "/ncs:devices/ncs:device/ncs:live-status/sfc:sffs" {
    deviate add {
      ywx:sil-priority "103";
    }
  }
  deviation "/ncs:devices/ncs:device/ncs:config/sfc:sffs" {
    deviate add {
      ywx:sil-priority "103";
    }
  }
  deviation "/ncs:devices/ncs:template/ncs:ned-id/ncs:config/acl:access-flows" {
    deviate add {
      ywx:sil-priority "110";
    }
  }
  deviation "/ncs:devices/ncs:device/ncs:live-status/acl:access-flows" {
    deviate add {
      ywx:sil-priority "110";
    }
  }
  deviation "/ncs:devices/ncs:device/ncs:config/acl:access-flows" {
    deviate add {
      ywx:sil-priority "110";
    }
  }
  deviation "/ncs:devices/ncs:template/ncs:ned-id/ncs:config/ciena-sat:sat/ciena-sat:emix-sequence" {
    deviate add {
      ywx:sil-priority "120";
    }
  }
  deviation "/ncs:devices/ncs:device/ncs:live-status/ciena-sat:sat/ciena-sat:emix-sequence" {
    deviate add {
      ywx:sil-priority "120";
    }
  }
  deviation "/ncs:devices/ncs:device/ncs:config/ciena-sat:sat/ciena-sat:emix-sequence" {
    deviate add {
      ywx:sil-priority "120";
    }
  }
  deviation "/ncs:devices/ncs:template/ncs:ned-id/ncs:config/ciena-sat:sat/ciena-sat:kpi-profile" {
    deviate add {
      ywx:sil-priority "120";
    }
  }
  deviation "/ncs:devices/ncs:device/ncs:live-status/ciena-sat:sat/ciena-sat:kpi-profile" {
    deviate add {
      ywx:sil-priority "120";
    }
  }
  deviation "/ncs:devices/ncs:device/ncs:config/ciena-sat:sat/ciena-sat:kpi-profile" {
    deviate add {
      ywx:sil-priority "120";
    }
  }
  deviation "/ncs:devices/ncs:template/ncs:ned-id/ncs:config/ciena-sat:sat/ciena-sat:bw-alloc-profile" {
    deviate add {
      ywx:sil-priority "120";
    }
  }
  deviation "/ncs:devices/ncs:device/ncs:live-status/ciena-sat:sat/ciena-sat:bw-alloc-profile" {
    deviate add {
      ywx:sil-priority "120";
    }
  }
  deviation "/ncs:devices/ncs:device/ncs:config/ciena-sat:sat/ciena-sat:bw-alloc-profile" {
    deviate add {
      ywx:sil-priority "120";
    }
  }
  deviation "/ncs:devices/ncs:template/ncs:ned-id/ncs:config/sync:sync/sync:global" {
    deviate add {
      ywx:sil-priority "130";
    }
  }
  deviation "/ncs:devices/ncs:device/ncs:live-status/sync:sync/sync:global" {
    deviate add {
      ywx:sil-priority "130";
    }
  }
  deviation "/ncs:devices/ncs:device/ncs:config/sync:sync/sync:global" {
    deviate add {
      ywx:sil-priority "130";
    }
  }
  deviation "/ncs:devices/ncs:template/ncs:ned-id/ncs:config/ciena-sat:sat/ciena-sat:sat-global" {
    deviate add {
      ywx:sil-priority "130";
    }
  }
  deviation "/ncs:devices/ncs:device/ncs:live-status/ciena-sat:sat/ciena-sat:sat-global" {
    deviate add {
      ywx:sil-priority "130";
    }
  }
  deviation "/ncs:devices/ncs:device/ncs:config/ciena-sat:sat/ciena-sat:sat-global" {
    deviate add {
      ywx:sil-priority "130";
    }
  }
  deviation "/ncs:devices/ncs:template/ncs:ned-id/ncs:config/ciena-sat:sat/ciena-sat:test-profile" {
    deviate add {
      ywx:sil-priority "130";
    }
  }
  deviation "/ncs:devices/ncs:device/ncs:live-status/ciena-sat:sat/ciena-sat:test-profile" {
    deviate add {
      ywx:sil-priority "130";
    }
  }
  deviation "/ncs:devices/ncs:device/ncs:config/ciena-sat:sat/ciena-sat:test-profile" {
    deviate add {
      ywx:sil-priority "130";
    }
  }
  deviation "/ncs:devices/ncs:template/ncs:ned-id/ncs:config/pon-ctrl:pon-ctrl/pon-ctrl:olts" {
    deviate add {
      ywx:sil-priority "130";
    }
  }
  deviation "/ncs:devices/ncs:device/ncs:live-status/pon-ctrl:pon-ctrl/pon-ctrl:olts" {
    deviate add {
      ywx:sil-priority "130";
    }
  }
  deviation "/ncs:devices/ncs:device/ncs:config/pon-ctrl:pon-ctrl/pon-ctrl:olts" {
    deviate add {
      ywx:sil-priority "130";
    }
  }
  deviation "/ncs:devices/ncs:template/ncs:ned-id/ncs:config/pon-ctrl:pon-ctrl/pon-ctrl:sla-profiles" {
    deviate add {
      ywx:sil-priority "130";
    }
  }
  deviation "/ncs:devices/ncs:device/ncs:live-status/pon-ctrl:pon-ctrl/pon-ctrl:sla-profiles" {
    deviate add {
      ywx:sil-priority "130";
    }
  }
  deviation "/ncs:devices/ncs:device/ncs:config/pon-ctrl:pon-ctrl/pon-ctrl:sla-profiles" {
    deviate add {
      ywx:sil-priority "130";
    }
  }
  deviation "/ncs:devices/ncs:template/ncs:ned-id/ncs:config/sync:sync/sync-ptp:ptp-global" {
    deviate add {
      ywx:sil-priority "140";
    }
  }
  deviation "/ncs:devices/ncs:device/ncs:live-status/sync:sync/sync-ptp:ptp-global" {
    deviate add {
      ywx:sil-priority "140";
    }
  }
  deviation "/ncs:devices/ncs:device/ncs:config/sync:sync/sync-ptp:ptp-global" {
    deviate add {
      ywx:sil-priority "140";
    }
  }
  deviation "/ncs:devices/ncs:template/ncs:ned-id/ncs:config/ciena-sat:sat/ciena-sat:entity" {
    deviate add {
      ywx:sil-priority "140";
    }
  }
  deviation "/ncs:devices/ncs:device/ncs:live-status/ciena-sat:sat/ciena-sat:entity" {
    deviate add {
      ywx:sil-priority "140";
    }
  }
  deviation "/ncs:devices/ncs:device/ncs:config/ciena-sat:sat/ciena-sat:entity" {
    deviate add {
      ywx:sil-priority "140";
    }
  }
  deviation "/ncs:devices/ncs:template/ncs:ned-id/ncs:config/pon-ctrl:pon-ctrl/pon-ctrl:onus" {
    deviate add {
      ywx:sil-priority "140";
    }
  }
  deviation "/ncs:devices/ncs:device/ncs:live-status/pon-ctrl:pon-ctrl/pon-ctrl:onus" {
    deviate add {
      ywx:sil-priority "140";
    }
  }
  deviation "/ncs:devices/ncs:device/ncs:config/pon-ctrl:pon-ctrl/pon-ctrl:onus" {
    deviate add {
      ywx:sil-priority "140";
    }
  }
  deviation "/ncs:devices/ncs:template/ncs:ned-id/ncs:config/sync:sync/sync:input-references" {
    deviate add {
      ywx:sil-priority "150";
    }
  }
  deviation "/ncs:devices/ncs:device/ncs:live-status/sync:sync/sync:input-references" {
    deviate add {
      ywx:sil-priority "150";
    }
  }
  deviation "/ncs:devices/ncs:device/ncs:config/sync:sync/sync:input-references" {
    deviate add {
      ywx:sil-priority "150";
    }
  }
  deviation "/ncs:devices/ncs:template/ncs:ned-id/ncs:config/ciena-sat:sat/ciena-sat:test-instance" {
    deviate add {
      ywx:sil-priority "150";
    }
  }
  deviation "/ncs:devices/ncs:device/ncs:live-status/ciena-sat:sat/ciena-sat:test-instance" {
    deviate add {
      ywx:sil-priority "150";
    }
  }
  deviation "/ncs:devices/ncs:device/ncs:config/ciena-sat:sat/ciena-sat:test-instance" {
    deviate add {
      ywx:sil-priority "150";
    }
  }
  deviation "/ncs:devices/ncs:template/ncs:ned-id/ncs:config/cn-rss:rss-queue-config" {
    deviate add {
      ywx:sil-priority "150";
    }
  }
  deviation "/ncs:devices/ncs:device/ncs:live-status/cn-rss:rss-queue-config" {
    deviate add {
      ywx:sil-priority "150";
    }
  }
  deviation "/ncs:devices/ncs:device/ncs:config/cn-rss:rss-queue-config" {
    deviate add {
      ywx:sil-priority "150";
    }
  }
  deviation "/ncs:devices/ncs:template/ncs:ned-id/ncs:config/sync:sync/sync:protection-groups" {
    deviate add {
      ywx:sil-priority "160";
    }
  }
  deviation "/ncs:devices/ncs:device/ncs:live-status/sync:sync/sync:protection-groups" {
    deviate add {
      ywx:sil-priority "160";
    }
  }
  deviation "/ncs:devices/ncs:device/ncs:config/sync:sync/sync:protection-groups" {
    deviate add {
      ywx:sil-priority "160";
    }
  }
  deviation "/ncs:devices/ncs:template/ncs:ned-id/ncs:config/sync:sync/sync:output-references" {
    deviate add {
      ywx:sil-priority "170";
    }
  }
  deviation "/ncs:devices/ncs:device/ncs:live-status/sync:sync/sync:output-references" {
    deviate add {
      ywx:sil-priority "170";
    }
  }
  deviation "/ncs:devices/ncs:device/ncs:config/sync:sync/sync:output-references" {
    deviate add {
      ywx:sil-priority "170";
    }
  }
  deviation "/ncs:devices/ncs:template/ncs:ned-id/ncs:config/te:te" {
    deviate add {
      ywx:sil-priority "175";
    }
  }
  deviation "/ncs:devices/ncs:device/ncs:live-status/te:te" {
    deviate add {
      ywx:sil-priority "175";
    }
  }
  deviation "/ncs:devices/ncs:device/ncs:config/te:te" {
    deviate add {
      ywx:sil-priority "175";
    }
  }
  deviation "/ncs:devices/ncs:template/ncs:ned-id/ncs:config/cnsr:segment-routing-traffic-engineering" {
    deviate add {
      ywx:sil-priority "175";
    }
  }
  deviation "/ncs:devices/ncs:device/ncs:live-status/cnsr:segment-routing-traffic-engineering" {
    deviate add {
      ywx:sil-priority "175";
    }
  }
  deviation "/ncs:devices/ncs:device/ncs:config/cnsr:segment-routing-traffic-engineering" {
    deviate add {
      ywx:sil-priority "175";
    }
  }
  deviation "/ncs:devices/ncs:template/ncs:ned-id/ncs:config/tp-tunnel:tp-corouted-tunnels" {
    deviate add {
      ywx:sil-priority "175";
    }
  }
  deviation "/ncs:devices/ncs:device/ncs:live-status/tp-tunnel:tp-corouted-tunnels" {
    deviate add {
      ywx:sil-priority "175";
    }
  }
  deviation "/ncs:devices/ncs:device/ncs:config/tp-tunnel:tp-corouted-tunnels" {
    deviate add {
      ywx:sil-priority "175";
    }
  }
  deviation "/ncs:devices/ncs:template/ncs:ned-id/ncs:config/sr:segment-routing" {
    deviate add {
      ywx:sil-priority "176";
    }
  }
  deviation "/ncs:devices/ncs:device/ncs:live-status/sr:segment-routing" {
    deviate add {
      ywx:sil-priority "176";
    }
  }
  deviation "/ncs:devices/ncs:device/ncs:config/sr:segment-routing" {
    deviate add {
      ywx:sil-priority "176";
    }
  }
  deviation "/ncs:devices/ncs:template/ncs:ned-id/ncs:config/pw:pseudowires" {
    deviate add {
      ywx:sil-priority "180";
    }
  }
  deviation "/ncs:devices/ncs:device/ncs:live-status/pw:pseudowires" {
    deviate add {
      ywx:sil-priority "180";
    }
  }
  deviation "/ncs:devices/ncs:device/ncs:config/pw:pseudowires" {
    deviate add {
      ywx:sil-priority "180";
    }
  }
  deviation "/ncs:devices/ncs:template/ncs:ned-id/ncs:config/tdm-pw:tdm-pseudowires" {
    deviate add {
      ywx:sil-priority "180";
    }
  }
  deviation "/ncs:devices/ncs:device/ncs:live-status/tdm-pw:tdm-pseudowires" {
    deviate add {
      ywx:sil-priority "180";
    }
  }
  deviation "/ncs:devices/ncs:device/ncs:config/tdm-pw:tdm-pseudowires" {
    deviate add {
      ywx:sil-priority "180";
    }
  }
  deviation "/ncs:devices/ncs:template/ncs:ned-id/ncs:config/l2vpn:l2vpn-services" {
    deviate add {
      ywx:sil-priority "190";
    }
  }
  deviation "/ncs:devices/ncs:device/ncs:live-status/l2vpn:l2vpn-services" {
    deviate add {
      ywx:sil-priority "190";
    }
  }
  deviation "/ncs:devices/ncs:device/ncs:config/l2vpn:l2vpn-services" {
    deviate add {
      ywx:sil-priority "190";
    }
  }
  deviation "/ncs:devices/ncs:template/ncs:ned-id/ncs:config/cnevpn:evpn" {
    deviate add {
      ywx:sil-priority "200";
    }
  }
  deviation "/ncs:devices/ncs:device/ncs:live-status/cnevpn:evpn" {
    deviate add {
      ywx:sil-priority "200";
    }
  }
  deviation "/ncs:devices/ncs:device/ncs:config/cnevpn:evpn" {
    deviate add {
      ywx:sil-priority "200";
    }
  }
  deviation "/ncs:devices/ncs:template/ncs:ned-id/ncs:config/bfd:bfd/bfd-ip-sh:ip-sh" {
    deviate add {
      ywx:sil-priority "210";
    }
  }
  deviation "/ncs:devices/ncs:device/ncs:live-status/bfd:bfd/bfd-ip-sh:ip-sh" {
    deviate add {
      ywx:sil-priority "210";
    }
  }
  deviation "/ncs:devices/ncs:device/ncs:config/bfd:bfd/bfd-ip-sh:ip-sh" {
    deviate add {
      ywx:sil-priority "210";
    }
  }
  deviation "/ncs:devices/ncs:template/ncs:ned-id/ncs:config/bfd:bfd/bfd-ip-mh:ip-mh" {
    deviate add {
      ywx:sil-priority "210";
    }
  }
  deviation "/ncs:devices/ncs:device/ncs:live-status/bfd:bfd/bfd-ip-mh:ip-mh" {
    deviate add {
      ywx:sil-priority "210";
    }
  }
  deviation "/ncs:devices/ncs:device/ncs:config/bfd:bfd/bfd-ip-mh:ip-mh" {
    deviate add {
      ywx:sil-priority "210";
    }
  }
}
