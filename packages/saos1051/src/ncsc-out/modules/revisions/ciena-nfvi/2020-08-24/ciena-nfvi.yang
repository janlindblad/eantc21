module ciena-nfvi {
  // Generated by yanger -t ncs
  tailf:mount-id "saos1051-nc-1.0:saos1051-nc-1.0";
  tailf:ncs-device-type "netconf";

  namespace "urn:ciena:params:xml:ns:yang:ciena-pn::ciena-nfvi";
  prefix cienanfvi;

  import tailf-common {
    prefix tailf;
  }
  import tailf-ncs {
    prefix ncs;
  }

  organization
    "Ciena Corporation";
  contact
    "Web URL: http://www.ciena.com/
     E-mail:   yang@ciena.com
     Postal:   7035 Ridge Road
              Hanover, Maryland 21076
              U.S.A.
     Phone:    +1 800-921-1144
     Fax:      +1 410-694-5750";
  description
    "This YANG model defines the data nodes for NFV orchestration";

  revision 2020-08-24 {
    description
      "Added config-pending-reason leaf.";
  }
  revision 2020-02-25 {
    description
      "Added support for hugepage configuration and hugepage operation data.
       Added NUMA and socket mapping info.";
  }
  revision 2016-07-28 {
    description
      "1.0";
  }

  typedef ncs_template_hugepage-size-type {
    description
      "Size of Memory huge page in MB";
    type string;
  }

  typedef ncs_rpc_notif_hugepage-size-type {
    description
      "Size of Memory huge page in MB";
    type enumeration {
      enum "2MB" {
        description
          "Memory hugepage size in 2MB";
      }
    }
  }

  typedef live_ncs_hugepage-size-type {
    description
      "Size of Memory huge page in MB";
    type enumeration {
      enum "2MB" {
        description
          "Memory hugepage size in 2MB";
      }
    }
  }

  typedef hugepage-size-type {
    description
      "Size of Memory huge page in MB";
    type enumeration {
      enum "2MB" {
        description
          "Memory hugepage size in 2MB";
      }
    }
  }

  grouping ncs_template_hugepage-config {
    list hugepage {
      // NCS patched for predictable order
      ordered-by user;
      description
        "List of hugepage related configuration";
      key "page-size numa-node";
      leaf page-size {
        description
          "The size of memory hugepage";
        type ncs_template_hugepage-size-type;
      }
      leaf numa-node {
        description
          "Numa node";
        type string;
      }
      choice page-config {
        case percentage {
          leaf percentage {
            description
              "Percentage of total physical memory to allocate as hugepages";
            type string;
            units "percentage";
          }
        }
        case page-count {
          leaf page-count {
            description
              "The number of huge pages";
            type string;
          }
        }
      }
    }
  }

  grouping ncs_template_hugepage-state {
    list hugepage {
      // NCS patched for predictable order
      ordered-by user;
      key "numa-node";
      description
        "List of hugepage memory state";
      leaf numa-node {
        description
          "Numa node";
        type string;
      }
      leaf page-size {
        description
          "The size of a huge page memory";
        type ncs_template_hugepage-size-type;
      }
      leaf page-count {
        description
          "Total number of huge pages";
        type string;
      }
      leaf total {
        description
          "Total amount of hugepage memory available for this hugepage size";
        type string;
        units "KB";
      }
      leaf free {
        description
          "Total amount of free hugepage memory for this hugepage size";
        type string;
        units "KB";
      }
      leaf percentage {
        description
          "Percentage of total physical memory allocated as hugepages";
        type string;
        units "percentage";
      }
    }
  }

  grouping ncs_rpc_notif_hugepage-config {
    list hugepage {
      description
        "List of hugepage related configuration";
      key "page-size numa-node";
      leaf page-size {
        description
          "The size of memory hugepage";
        type ncs_rpc_notif_hugepage-size-type;
      }
      leaf numa-node {
        description
          "Numa node";
        type uint8;
      }
      choice page-config {
        case percentage {
          leaf percentage {
            description
              "Percentage of total physical memory to allocate as hugepages";
            type uint8 {
              range "0..100";
            }
            units "percentage";
          }
        }
        case page-count {
          leaf page-count {
            description
              "The number of huge pages";
            type uint64;
          }
        }
      }
    }
  }

  grouping ncs_rpc_notif_hugepage-state {
    list hugepage {
      key "numa-node";
      description
        "List of hugepage memory state";
      leaf numa-node {
        description
          "Numa node";
        type uint8;
      }
      leaf page-size {
        description
          "The size of a huge page memory";
        type ncs_rpc_notif_hugepage-size-type;
      }
      leaf page-count {
        description
          "Total number of huge pages";
        type uint64;
      }
      leaf total {
        description
          "Total amount of hugepage memory available for this hugepage size";
        type uint64;
        units "KB";
      }
      leaf free {
        description
          "Total amount of free hugepage memory for this hugepage size";
        type uint64;
        units "KB";
      }
      leaf percentage {
        description
          "Percentage of total physical memory allocated as hugepages";
        type decimal64 {
          fraction-digits 2;
          range "0.00..100.00";
        }
        units "percentage";
      }
    }
  }

  grouping live_ncs_hugepage-config {
    list hugepage {
      description
        "List of hugepage related configuration";
      key "page-size numa-node";
      leaf page-size {
        description
          "The size of memory hugepage";
        type live_ncs_hugepage-size-type;
      }
      leaf numa-node {
        description
          "Numa node";
        type uint8;
      }
      choice page-config {
        case percentage {
          leaf percentage {
            description
              "Percentage of total physical memory to allocate as hugepages";
            type uint8 {
              range "0..100";
            }
            units "percentage";
          }
        }
        case page-count {
          leaf page-count {
            description
              "The number of huge pages";
            type uint64;
          }
        }
      }
    }
  }

  grouping live_ncs_hugepage-state {
    list hugepage {
      key "numa-node";
      description
        "List of hugepage memory state";
      leaf numa-node {
        description
          "Numa node";
        type uint8;
      }
      leaf page-size {
        description
          "The size of a huge page memory";
        type live_ncs_hugepage-size-type;
      }
      leaf page-count {
        description
          "Total number of huge pages";
        type uint64;
      }
      leaf total {
        description
          "Total amount of hugepage memory available for this hugepage size";
        type uint64;
        units "KB";
      }
      leaf free {
        description
          "Total amount of free hugepage memory for this hugepage size";
        type uint64;
        units "KB";
      }
      leaf percentage {
        description
          "Percentage of total physical memory allocated as hugepages";
        type decimal64 {
          fraction-digits 2;
          range "0.00..100.00";
        }
        units "percentage";
      }
    }
  }

  grouping hugepage-config {
    list hugepage {
      description
        "List of hugepage related configuration";
      key "page-size numa-node";
      leaf page-size {
        description
          "The size of memory hugepage";
        type hugepage-size-type;
      }
      leaf numa-node {
        description
          "Numa node";
        type uint8;
      }
      choice page-config {
        case percentage {
          leaf percentage {
            description
              "Percentage of total physical memory to allocate as hugepages";
            type uint8 {
              range "0..100";
            }
            units "percentage";
          }
        }
        case page-count {
          leaf page-count {
            description
              "The number of huge pages";
            type uint64;
          }
        }
      }
    }
  }

  grouping hugepage-state {
    list hugepage {
      key "numa-node";
      description
        "List of hugepage memory state";
      leaf numa-node {
        description
          "Numa node";
        type uint8;
      }
      leaf page-size {
        description
          "The size of a huge page memory";
        type hugepage-size-type;
      }
      leaf page-count {
        description
          "Total number of huge pages";
        type uint64;
      }
      leaf total {
        description
          "Total amount of hugepage memory available for this hugepage size";
        type uint64;
        units "KB";
      }
      leaf free {
        description
          "Total amount of free hugepage memory for this hugepage size";
        type uint64;
        units "KB";
      }
      leaf percentage {
        description
          "Percentage of total physical memory allocated as hugepages";
        type decimal64 {
          fraction-digits 2;
          range "0.00..100.00";
        }
        units "percentage";
      }
    }
  }

  augment "/ncs:devices/ncs:device/ncs:config" {
    container nfvi {
      tailf:ncs-device-type "netconf";
      tailf:display-when "not(../../ncs:module) or ../../ncs:module[ncs:name='ciena-nfvi']";
      leaf name {
        type string;
        default "nfvi";
      }
      container memory {
        description
          "Configuration of system memory";
        container hugepages {
          description
            "Configuration of system huge page memory";
          uses hugepage-config;
        }
      }
      // NCS drop config false container 'nfvi-state'
    }
  }
  augment "/ncs:devices/ncs:device/ncs:live-status" {
    container nfvi {
      tailf:ncs-device-type "netconf";
      tailf:display-when "not(../../ncs:module) or ../../ncs:module[ncs:name='ciena-nfvi'] or (../../ncs:live-status-protocol[not(ncs:capability)]) or (../../ncs:live-status-protocol/ncs:capability/ncs:module[.='ciena-nfvi'])";
      leaf name {
        type string;
        // NCS drop default statement
      }
      container memory {
        description
          "Configuration of system memory";
        container hugepages {
          description
            "Configuration of system huge page memory";
          uses live_ncs_hugepage-config;
        }
      }
      container nfvi-state {
        description
          "Operational state of the NFVi subsystem";
        leaf cpu-total {
          type uint64;
          description
            "Total number of vCPUs";
        }
        leaf cpu-available {
          type uint64;
          description
            "Number of vCPUs available for service functions";
        }
        leaf mem-total {
          type uint64;
          units "megabytes";
          description
            "Total amount of memory";
        }
        leaf mem-available {
          type uint64;
          units "megabytes";
          description
            "Amount of memory available for service functions";
        }
        leaf disk-total {
          type uint64;
          units "megabyte";
          description
            "Total hard disk size";
        }
        leaf disk-available {
          type uint64;
          units "megabytes";
          description
            "Hard disk size available for service functions";
        }
        container memory {
          description
            "Memory state information";
          leaf total {
            description
              "Total amount of total physical memory";
            type uint64;
            units "KB";
          }
          leaf free {
            description
              "Total amount of free physical memory";
            type uint64;
            units "KB";
          }
          leaf memory-4k-total {
            description
              "Amount of total memory in default 4k page size";
            type uint64;
            units "KB";
          }
          leaf memory-4k-free {
            description
              "Amount of free memory in default 4k page size";
            type uint64;
            units "KB";
          }
          container hugepages {
            description
              "Active huge page configuration on device";
            uses live_ncs_hugepage-state;
          }
        }
        list numa-node {
          key "node-id";
          description
            "NUMA node list";
          leaf node-id {
            type uint8;
            description
              "NUMA node ID";
          }
          leaf memory-available {
            type uint32;
            units "megabytes";
            description
              "Memory available on NUMA node for service function";
          }
          leaf memory-total {
            type uint32;
            units "megabytes";
            description
              "Memory total on NUMA node";
          }
        }
        list socket {
          key "socket-id";
          description
            "Socket list";
          leaf socket-id {
            type uint8;
            description
              "CPU Socket ID";
          }
          leaf node-id {
            type uint8;
            description
              "NUMA node ID";
          }
          leaf-list cpu-list {
            type uint16;
            description
              "List of total CPU cores on socket";
          }
          leaf-list cpu-available {
            type uint16;
            description
              "List of available CPU cores on socket";
          }
        }
        leaf config-pending {
          description
            "Status of configuration; When true, there is a pending configuration change that requires device restart to activate";
          type boolean;
        }
        leaf config-pending-reason {
          description
            "The reason there is a pending configuration change";
          type bits {
            bit hugepage-config-pending {
              position 0;
              description
                "Hugepage configuration is pending";
            }
            bit local-management-config-pending {
              position 1;
              description
                "Local management configuration is pending";
            }
          }
        }
      }
    }
  }
  augment "/ncs:devices/ncs:template/ncs:ned-id/ncs:config" {
    container nfvi {
      leaf name {
        type string;
        // NCS drop default statement
      }
      container memory {
        description
          "Configuration of system memory";
        container hugepages {
          description
            "Configuration of system huge page memory";
          uses ncs_template_hugepage-config;
        }
      }
      // NCS drop config false container 'nfvi-state'
    }
  }
}
