module ciena-ntp-deviation {
  // Generated by yanger -t ncs
  tailf:mount-id "saos1051-nc-1.0:saos1051-nc-1.0";
  tailf:ncs-device-type "netconf";

  namespace "http://www.ciena.com/ns/yang/ciena-ntp-dev";
  prefix ciena-ntp-dev;

  import openconfig-system {
    prefix oc-sys;
  }
  import ciena-ntp {
    prefix ciena-ntp;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's deviations from the ciena-ntp model.

      Copyright (c) 2016 Ciena Corporation.  All rights
      reserved.

      All information contained herein is, and remains
      the property of Ciena Corporation. Dissemination of this
      information or reproduction of this material is strictly
      forbidden unless prior written permission is obtained from
      Ciena Corporation.";

  revision 2018-06-14 {
    description
      "Remove deviation on multicast and authentication.";
    reference "";
  }
  revision 2017-11-01 {
    description
      "Initial version";
    reference
      "RFC 6020: YANG - A Data Modeling Language for
       the Network Configuration Protocol (NETCONF).
       No specific reference; standard not available.";
  }

  deviation "/ncs:devices/ncs:template/ncs:ned-id/ncs:config/oc-sys:system/ciena-ntp:ntp/ciena-ntp:sync-notification" {
    deviate not-supported;
  }
  deviation "/ncs:devices/ncs:device/ncs:live-status/oc-sys:system/ciena-ntp:ntp/ciena-ntp:sync-notification" {
    deviate not-supported;
  }
  deviation "/ncs:devices/ncs:device/ncs:config/oc-sys:system/ciena-ntp:ntp/ciena-ntp:sync-notification" {
    deviate not-supported;
  }
  deviation "/ncs:devices/ncs:template/ncs:ned-id/ncs:config/oc-sys:system/ciena-ntp:ntp/ciena-ntp:associations/ciena-ntp:peer-server" {
    deviate not-supported;
  }
  deviation "/ncs:devices/ncs:device/ncs:live-status/oc-sys:system/ciena-ntp:ntp/ciena-ntp:associations/ciena-ntp:peer-server" {
    deviate not-supported;
  }
  deviation "/ncs:devices/ncs:device/ncs:config/oc-sys:system/ciena-ntp:ntp/ciena-ntp:associations/ciena-ntp:peer-server" {
    deviate not-supported;
  }
  deviation "/ncs:devices/ncs:template/ncs:ned-id/ncs:config/oc-sys:system/ciena-ntp:ntp/ciena-ntp:associations/ciena-ntp:remote-ntp-server/ciena-ntp:server-entry/ciena-ntp:admin-state" {
    deviate add {
      // NCS drop default statement
    }
  }
  deviation "/ncs:devices/ncs:device/ncs:live-status/oc-sys:system/ciena-ntp:ntp/ciena-ntp:associations/ciena-ntp:remote-ntp-server/ciena-ntp:server-entry/ciena-ntp:admin-state" {
    deviate add {
      // NCS drop default statement
    }
  }
  deviation "/ncs:devices/ncs:device/ncs:config/oc-sys:system/ciena-ntp:ntp/ciena-ntp:associations/ciena-ntp:remote-ntp-server/ciena-ntp:server-entry/ciena-ntp:admin-state" {
    deviate add {
      default "enabled";
    }
  }
  deviation "/ncs:devices/ncs:template/ncs:ned-id/ncs:config/oc-sys:system/ciena-ntp:ntp/ciena-ntp:authentication/ciena-ntp:auth-admin-state" {
    deviate add {
      // NCS drop default statement
    }
  }
  deviation "/ncs:devices/ncs:device/ncs:live-status/oc-sys:system/ciena-ntp:ntp/ciena-ntp:authentication/ciena-ntp:auth-admin-state" {
    deviate add {
      // NCS drop default statement
    }
  }
  deviation "/ncs:devices/ncs:device/ncs:config/oc-sys:system/ciena-ntp:ntp/ciena-ntp:authentication/ciena-ntp:auth-admin-state" {
    deviate add {
      default "disabled";
    }
  }
  deviation "/ncs:devices/ncs:template/ncs:ned-id/ncs:config/oc-sys:system/ciena-ntp:ntp/ciena-ntp:authentication/ciena-ntp:auth-entry/ciena-ntp:auth-key" {
    deviate not-supported;
  }
  deviation "/ncs:devices/ncs:device/ncs:live-status/oc-sys:system/ciena-ntp:ntp/ciena-ntp:authentication/ciena-ntp:auth-entry/ciena-ntp:auth-key" {
    deviate not-supported;
  }
  deviation "/ncs:devices/ncs:device/ncs:config/oc-sys:system/ciena-ntp:ntp/ciena-ntp:authentication/ciena-ntp:auth-entry/ciena-ntp:auth-key" {
    deviate not-supported;
  }
}
