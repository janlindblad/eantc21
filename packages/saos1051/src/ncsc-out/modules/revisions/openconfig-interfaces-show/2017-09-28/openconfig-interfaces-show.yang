module openconfig-interfaces-show {
  // Generated by yanger -t ncs
  tailf:mount-id "saos1051-nc-1.0:saos1051-nc-1.0";
  tailf:ncs-device-type "netconf";

  yang-version 1.1;
  namespace "http://www.ciena.com/ns/openconfig-interfaces-show";
  prefix openconfig-interfaces-show;

  import yangcli-pro {
    prefix yp;
  }
  import tailf-common {
    prefix tailf;
  }
  import tailf-ncs {
    prefix ncs;
  }

  description
    "Show command extensions by ciena for openconfig-interfaces";

  revision 2017-09-28 {
    description
      "Initial version";
  }

  augment "/ncs:devices/ncs:device/ncs:rpc/yp:rpc-show/yp:show/yp:input/yp:showtype" {
    case ip {
      leaf ip {
        type empty;
      }
      leaf interface {
        type empty;
      }
      leaf neighbor {
        type empty;
      }
      leaf route {
        type empty;
      }
    }
    case lldp {
      leaf lldp {
        type string;
      }
    }
    case eoam {
      leaf eoam {
        type string;
      }
    }
    case aggregation {
      leaf aggregation {
        type string;
      }
    }
    case ettp {
      leaf ettp {
        type string;
      }
    }
  }
}
