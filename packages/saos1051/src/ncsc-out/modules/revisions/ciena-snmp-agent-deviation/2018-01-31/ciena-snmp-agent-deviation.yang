module ciena-snmp-agent-deviation {
  // Generated by yanger -t ncs
  tailf:mount-id "saos1051-nc-1.0:saos1051-nc-1.0";
  tailf:ncs-device-type "netconf";

  namespace "http://www.ciena.com/ns/yang/ciena-snmp-agent-deviation";
  prefix snmp-agent-dev;

  import ietf-snmp {
    prefix snmp;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's deviations from rfc7407.

     Copyright (c) 2018 Ciena Corporation.  All rights
     reserved.

     All information contained herein is, and remains
     the property of Ciena Corporation. Dissemination of this
     information or reproduction of this material is strictly
     forbidden unless prior written permission is obtained from
     Ciena Corporation.";

  revision 2018-01-31 {
    description
      "Initial version";
    reference "[rfc7407](https://tools.ietf.org/rfc/rfc7407.txt)";
  }

  deviation "/ncs:devices/ncs:template/ncs:ned-id/ncs:config/snmp:snmp/snmp:usm" {
    deviate not-supported;
  }
  deviation "/ncs:devices/ncs:device/ncs:live-status/snmp:snmp/snmp:usm" {
    deviate not-supported;
  }
  deviation "/ncs:devices/ncs:device/ncs:config/snmp:snmp/snmp:usm" {
    deviate not-supported;
  }
  deviation "/ncs:devices/ncs:template/ncs:ned-id/ncs:config/snmp:snmp/snmp:engine" {
    deviate not-supported;
  }
  deviation "/ncs:devices/ncs:device/ncs:live-status/snmp:snmp/snmp:engine" {
    deviate not-supported;
  }
  deviation "/ncs:devices/ncs:device/ncs:config/snmp:snmp/snmp:engine" {
    deviate not-supported;
  }
  deviation "/ncs:devices/ncs:template/ncs:ned-id/ncs:config/snmp:snmp/snmp:target/snmp:transport/snmp:tls" {
    deviate not-supported;
  }
  deviation "/ncs:devices/ncs:device/ncs:live-status/snmp:snmp/snmp:target/snmp:transport/snmp:tls" {
    deviate not-supported;
  }
  deviation "/ncs:devices/ncs:device/ncs:config/snmp:snmp/snmp:target/snmp:transport/snmp:tls" {
    deviate not-supported;
  }
  deviation "/ncs:devices/ncs:template/ncs:ned-id/ncs:config/snmp:snmp/snmp:target/snmp:transport/snmp:dtls" {
    deviate not-supported;
  }
  deviation "/ncs:devices/ncs:device/ncs:live-status/snmp:snmp/snmp:target/snmp:transport/snmp:dtls" {
    deviate not-supported;
  }
  deviation "/ncs:devices/ncs:device/ncs:config/snmp:snmp/snmp:target/snmp:transport/snmp:dtls" {
    deviate not-supported;
  }
  deviation "/ncs:devices/ncs:template/ncs:ned-id/ncs:config/snmp:snmp/snmp:target/snmp:transport/snmp:ssh" {
    deviate not-supported;
  }
  deviation "/ncs:devices/ncs:device/ncs:live-status/snmp:snmp/snmp:target/snmp:transport/snmp:ssh" {
    deviate not-supported;
  }
  deviation "/ncs:devices/ncs:device/ncs:config/snmp:snmp/snmp:target/snmp:transport/snmp:ssh" {
    deviate not-supported;
  }
  deviation "/ncs:devices/ncs:template/ncs:ned-id/ncs:config/snmp:snmp/snmp:target-params/snmp:params/snmp:tsm" {
    deviate not-supported;
  }
  deviation "/ncs:devices/ncs:device/ncs:live-status/snmp:snmp/snmp:target-params/snmp:params/snmp:tsm" {
    deviate not-supported;
  }
  deviation "/ncs:devices/ncs:device/ncs:config/snmp:snmp/snmp:target-params/snmp:params/snmp:tsm" {
    deviate not-supported;
  }
  deviation "/ncs:devices/ncs:template/ncs:ned-id/ncs:config/snmp:snmp/snmp:target-params/snmp:notify-filter-profile" {
    deviate not-supported;
  }
  deviation "/ncs:devices/ncs:device/ncs:live-status/snmp:snmp/snmp:target-params/snmp:notify-filter-profile" {
    deviate not-supported;
  }
  deviation "/ncs:devices/ncs:device/ncs:config/snmp:snmp/snmp:target-params/snmp:notify-filter-profile" {
    deviate not-supported;
  }
  deviation "/ncs:devices/ncs:template/ncs:ned-id/ncs:config/snmp:snmp/snmp:proxy" {
    deviate not-supported;
  }
  deviation "/ncs:devices/ncs:device/ncs:live-status/snmp:snmp/snmp:proxy" {
    deviate not-supported;
  }
  deviation "/ncs:devices/ncs:device/ncs:config/snmp:snmp/snmp:proxy" {
    deviate not-supported;
  }
  deviation "/ncs:devices/ncs:template/ncs:ned-id/ncs:config/snmp:snmp/snmp:tlstm" {
    deviate not-supported;
  }
  deviation "/ncs:devices/ncs:device/ncs:live-status/snmp:snmp/snmp:tlstm" {
    deviate not-supported;
  }
  deviation "/ncs:devices/ncs:device/ncs:config/snmp:snmp/snmp:tlstm" {
    deviate not-supported;
  }
  deviation "/ncs:devices/ncs:template/ncs:ned-id/ncs:config/snmp:snmp/snmp:tsm" {
    deviate not-supported;
  }
  deviation "/ncs:devices/ncs:device/ncs:live-status/snmp:snmp/snmp:tsm" {
    deviate not-supported;
  }
  deviation "/ncs:devices/ncs:device/ncs:config/snmp:snmp/snmp:tsm" {
    deviate not-supported;
  }
  deviation "/ncs:devices/ncs:template/ncs:ned-id/ncs:config/snmp:snmp/snmp:community/snmp:context" {
    deviate not-supported;
  }
  deviation "/ncs:devices/ncs:device/ncs:live-status/snmp:snmp/snmp:community/snmp:context" {
    deviate not-supported;
  }
  deviation "/ncs:devices/ncs:device/ncs:config/snmp:snmp/snmp:community/snmp:context" {
    deviate not-supported;
  }
  deviation "/ncs:devices/ncs:template/ncs:ned-id/ncs:config/snmp:snmp/snmp:community/snmp:engine-id" {
    deviate not-supported;
  }
  deviation "/ncs:devices/ncs:device/ncs:live-status/snmp:snmp/snmp:community/snmp:engine-id" {
    deviate not-supported;
  }
  deviation "/ncs:devices/ncs:device/ncs:config/snmp:snmp/snmp:community/snmp:engine-id" {
    deviate not-supported;
  }
  deviation "/ncs:devices/ncs:template/ncs:ned-id/ncs:config/snmp:snmp/snmp:community/snmp:name/snmp:binary-name" {
    deviate not-supported;
  }
  deviation "/ncs:devices/ncs:device/ncs:live-status/snmp:snmp/snmp:community/snmp:name/snmp:binary-name" {
    deviate not-supported;
  }
  deviation "/ncs:devices/ncs:device/ncs:config/snmp:snmp/snmp:community/snmp:name/snmp:binary-name" {
    deviate not-supported;
  }
  deviation "/ncs:devices/ncs:template/ncs:ned-id/ncs:config/snmp:snmp/snmp:community/snmp:target-tag" {
    deviate not-supported;
  }
  deviation "/ncs:devices/ncs:device/ncs:live-status/snmp:snmp/snmp:community/snmp:target-tag" {
    deviate not-supported;
  }
  deviation "/ncs:devices/ncs:device/ncs:config/snmp:snmp/snmp:community/snmp:target-tag" {
    deviate not-supported;
  }
  deviation "/ncs:devices/ncs:template/ncs:ned-id/ncs:config/snmp:snmp/snmp:target-params/snmp:params/snmp:usm" {
    deviate not-supported;
  }
  deviation "/ncs:devices/ncs:device/ncs:live-status/snmp:snmp/snmp:target-params/snmp:params/snmp:usm" {
    deviate not-supported;
  }
  deviation "/ncs:devices/ncs:device/ncs:config/snmp:snmp/snmp:target-params/snmp:params/snmp:usm" {
    deviate not-supported;
  }
  deviation "/ncs:devices/ncs:template/ncs:ned-id/ncs:config/snmp:snmp/snmp:target/snmp:mms" {
    deviate not-supported;
  }
  deviation "/ncs:devices/ncs:device/ncs:live-status/snmp:snmp/snmp:target/snmp:mms" {
    deviate not-supported;
  }
  deviation "/ncs:devices/ncs:device/ncs:config/snmp:snmp/snmp:target/snmp:mms" {
    deviate not-supported;
  }
  deviation "/ncs:devices/ncs:template/ncs:ned-id/ncs:config/snmp:snmp/snmp:notify-filter-profile" {
    deviate not-supported;
  }
  deviation "/ncs:devices/ncs:device/ncs:live-status/snmp:snmp/snmp:notify-filter-profile" {
    deviate not-supported;
  }
  deviation "/ncs:devices/ncs:device/ncs:config/snmp:snmp/snmp:notify-filter-profile" {
    deviate not-supported;
  }
  deviation "/ncs:devices/ncs:template/ncs:ned-id/ncs:config/snmp:snmp/snmp:vacm/snmp:group/snmp:access/snmp:read-view" {
    deviate not-supported;
  }
  deviation "/ncs:devices/ncs:device/ncs:live-status/snmp:snmp/snmp:vacm/snmp:group/snmp:access/snmp:read-view" {
    deviate not-supported;
  }
  deviation "/ncs:devices/ncs:device/ncs:config/snmp:snmp/snmp:vacm/snmp:group/snmp:access/snmp:read-view" {
    deviate not-supported;
  }
  deviation "/ncs:devices/ncs:template/ncs:ned-id/ncs:config/snmp:snmp/snmp:vacm/snmp:group/snmp:access/snmp:write-view" {
    deviate not-supported;
  }
  deviation "/ncs:devices/ncs:device/ncs:live-status/snmp:snmp/snmp:vacm/snmp:group/snmp:access/snmp:write-view" {
    deviate not-supported;
  }
  deviation "/ncs:devices/ncs:device/ncs:config/snmp:snmp/snmp:vacm/snmp:group/snmp:access/snmp:write-view" {
    deviate not-supported;
  }
}
