module ietf-network-state {
  // Generated by yanger -t ncs
  tailf:mount-id "saos1051-nc-1.0:saos1051-nc-1.0";
  tailf:ncs-device-type "netconf";

  yang-version 1.1;
  namespace "urn:ietf:params:xml:ns:yang:ietf-network-state";
  prefix nw-s;

  import ietf-network {
    prefix nw;
    reference "RFC 8345: A YANG Data Model for Network Topologies";
  }
  import tailf-common {
    prefix tailf;
  }
  import tailf-ncs {
    prefix ncs;
  }

  organization
    "IETF I2RS (Interface to the Routing System) Working Group";
  contact
    "WG Web:    <https://datatracker.ietf.org/wg/i2rs/>
     WG List:   <mailto:i2rs@ietf.org>

     Editor:    Alexander Clemm
                <mailto:ludwig@clemm.org>

     Editor:    Jan Medved
                <mailto:jmedved@cisco.com>

     Editor:    Robert Varga
                <mailto:robert.varga@pantheon.tech>

     Editor:    Nitin Bahadur
                <mailto:nitin_bahadur@yahoo.com>
     Editor:    Hariharan Ananthakrishnan
                <mailto:hari@packetdesign.com>

     Editor:    Xufeng Liu
                <mailto:xufeng.liu.ietf@gmail.com>";
  description
    "This module defines a common base data model for a collection
     of nodes in a network.  Node definitions are further used
     in network topologies and inventories.  It represents
     information that either (1) is learned and automatically
     populated or (2) results from applying network information
     that has been configured per the 'ietf-network' data model,
     mirroring the corresponding data nodes in this data model.

     The data model mirrors 'ietf-network' but contains only
     read-only state data.  The data model is not needed when the
     underlying implementation infrastructure supports the Network
     Management Datastore Architecture (NMDA).

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC 8345;
     see the RFC itself for full legal notices.";

  revision 2018-02-26 {
    description
      "Initial revision.";
    reference "RFC 8345: A YANG Data Model for Network Topologies";
  }

  grouping ncs_template_network-ref {
    description
      "Contains the information necessary to reference a network --
       for example, an underlay network.";
    leaf network-ref {
      type string;
      description
        "Used to reference a network -- for example, an underlay
         network.";
    }
  }

  grouping ncs_template_node-ref {
    description
      "Contains the information necessary to reference a node.";
    leaf node-ref {
      type string;
      description
        "Used to reference a node.
         Nodes are identified relative to the network that
         contains them.";
    }
    uses ncs_template_network-ref;
  }

  grouping ncs_rpc_notif_network-ref {
    description
      "Contains the information necessary to reference a network --
       for example, an underlay network.";
    leaf network-ref {
      type string;
      description
        "Used to reference a network -- for example, an underlay
         network.";
    }
  }

  grouping ncs_rpc_notif_node-ref {
    description
      "Contains the information necessary to reference a node.";
    leaf node-ref {
      type string;
      description
        "Used to reference a node.
         Nodes are identified relative to the network that
         contains them.";
    }
    uses ncs_rpc_notif_network-ref;
  }

  grouping live_ncs_network-ref {
    description
      "Contains the information necessary to reference a network --
       for example, an underlay network.";
    leaf network-ref {
      type leafref {
        path "/ncs:devices/ncs:device/ncs:live-status/nw-s:networks/nw-s:network/nw-s:network-id" {
          tailf:xpath-root 3;
        }
        require-instance false;
      }
      description
        "Used to reference a network -- for example, an underlay
         network.";
    }
  }

  grouping live_ncs_node-ref {
    description
      "Contains the information necessary to reference a node.";
    leaf node-ref {
      type leafref {
        path "/ncs:devices/ncs:device/ncs:live-status/nw-s:networks/nw-s:network[nw-s:network-id=current()/../network-ref]/nw-s:node/nw-s:node-id" {
          tailf:xpath-root 3;
        }
        require-instance false;
      }
      description
        "Used to reference a node.
         Nodes are identified relative to the network that
         contains them.";
    }
    uses live_ncs_network-ref;
  }

  grouping network-ref {
    description
      "Contains the information necessary to reference a network --
       for example, an underlay network.";
    leaf network-ref {
      type leafref {
        path "/ncs:devices/ncs:device/ncs:live-status/nw-s:networks/nw-s:network/nw-s:network-id" {
          tailf:xpath-root 2;
        }
        require-instance false;
      }
      description
        "Used to reference a network -- for example, an underlay
         network.";
    }
  }

  grouping node-ref {
    description
      "Contains the information necessary to reference a node.";
    leaf node-ref {
      type leafref {
        path "/ncs:devices/ncs:device/ncs:live-status/nw-s:networks/nw-s:network[nw-s:network-id=current()/../network-ref]/nw-s:node/nw-s:node-id" {
          tailf:xpath-root 2;
        }
        require-instance false;
      }
      description
        "Used to reference a node.
         Nodes are identified relative to the network that
         contains them.";
    }
    uses network-ref;
  }

  augment "/ncs:devices/ncs:device/ncs:config" {
    // NCS drop config false container networks
  }
  augment "/ncs:devices/ncs:device/ncs:live-status" {
    container networks {
      tailf:ncs-device-type "netconf";
      tailf:display-when "not(../../ncs:module) or ../../ncs:module[ncs:name='ietf-network-state'] or (../../ncs:live-status-protocol[not(ncs:capability)]) or (../../ncs:live-status-protocol/ncs:capability/ncs:module[.='ietf-network-state'])";
      description
        "Serves as a top-level container for a list of networks.";
      list network {
        key "network-id";
        description
          "Describes a network.
           A network typically contains an inventory of nodes,
           topological information (augmented through the
           network-topology data model), and layering information.";
        container network-types {
          description
            "Serves as an augmentation target.
             The network type is indicated through corresponding
             presence containers augmented into this container.";
        }
        leaf network-id {
          type nw:live_ncs_network-id;
          description
            "Identifies a network.";
        }
        list supporting-network {
          key "network-ref";
          description
            "An underlay network, used to represent layered network
             topologies.";
          leaf network-ref {
            type leafref {
              path "/ncs:devices/ncs:device/ncs:live-status/nw-s:networks/nw-s:network/nw-s:network-id" {
                tailf:xpath-root 3;
              }
              require-instance false;
            }
            description
              "References the underlay network.";
          }
        }
        list node {
          key "node-id";
          description
            "The inventory of nodes of this network.";
          leaf node-id {
            type nw:live_ncs_node-id;
            description
              "Uniquely identifies a node within the containing
               network.";
          }
          list supporting-node {
            key "network-ref node-ref";
            description
              "Represents another node that is in an underlay network
               and that supports this node.  Used to represent layering
               structure.";
            leaf network-ref {
              type leafref {
                path "../../../nw-s:supporting-network/nw-s:network-ref";
                require-instance false;
              }
              description
                "References the underlay network of which the
                 underlay node is a part.";
            }
            leaf node-ref {
              type leafref {
                path "/ncs:devices/ncs:device/ncs:live-status/nw-s:networks/nw-s:network/nw-s:node/nw-s:node-id" {
                  tailf:xpath-root 3;
                }
                require-instance false;
              }
              description
                "References the underlay node itself.";
            }
          }
        }
      }
    }
  }
  augment "/ncs:devices/ncs:template/ncs:ned-id/ncs:config" {
    // NCS drop config false container networks
  }
}
