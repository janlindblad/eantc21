module yumaworks-config-change {
  // Generated by yanger -t ncs
  tailf:mount-id "saos1051-nc-1.0:saos1051-nc-1.0";
  tailf:ncs-device-type "netconf";

  namespace "http://yumaworks.com/ns/yumaworks-config-change";
  prefix ycc;

  import ietf-netconf-notifications {
    prefix ncn;
  }
  import tailf-common {
    prefix tailf;
  }
  import tailf-ncs {
    prefix ncs;
  }

  organization
    "YumaWorks, Inc.";
  contact
    "Support <support@yumaworks.com>";
  description
    "YumaPro Common Identities

     Copyright (c) 2019 YumaWorks, Inc. All rights reserved.

     Redistribution and use in source and binary forms, with or
     without modification, is permitted pursuant to, and subject
     to the license terms contained in, the BSD 3-Clause License
     http://opensource.org/licenses/BSD-3-Clause";

  revision 2019-06-09 {
    description
      "Initial version";
  }

  augment "/ncs:devices/ncs:device/ncs:netconf-notifications/ncs:received-notifications/ncs:notification/ncs:data/ncn:netconf-config-change/ncn:edit" {
    description
      "Datastore values are added to each edit within the
       netconf-config-change notification.

       Note that this added data represents a security risk since it is
       not subject to the same access control rules within a notification
       as within a datastore.  NACM does not provide access control
       for the contents of a notification, only for the notification
       event type.   Use this module with caution!  Only allow a
       superuser administrator access to the 'netconf-config-change'
       notification if this module is used.";
    anyxml new-value {
      description
        "Contains the new value for the associated 'target' if the
         operation is not 'delete' or 'remove'. This object should
         represent a container with one child node specifying the
         new value used in the associated edit.";
    }
    anyxml old-value {
      description
        "Contains the old value for the associate 'target' that was
         changed or deleted, if operation is not 'create', This object
         should represent a container with one child node specifying
         the current value used in the associated edit.";
    }
  }
}
