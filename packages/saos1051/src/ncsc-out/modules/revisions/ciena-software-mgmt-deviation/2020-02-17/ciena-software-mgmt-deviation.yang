module ciena-software-mgmt-deviation {
  // Generated by yanger -t ncs
  tailf:mount-id "saos1051-nc-1.0:saos1051-nc-1.0";
  tailf:ncs-device-type "netconf";

  namespace "http://www.ciena.com/ns/yang/ciena-software-mgmt-dev";
  prefix ciena-software-management-dev;

  import ciena-software-mgmt {
    prefix software-mgmt;
  }
  import tailf-common {
    prefix tailf;
  }
  import tailf-ncs {
    prefix ncs;
  }

  revision 2020-02-17 {
    description
      "Added default value false to software-install rpc defer-activation attribute.";
  }
  revision 2019-09-19 {
    description
      "Adding not-supported deviation for unsupported capabilities.
       Adding not-supported deviation for software-state/running-package/standby-bootchain.";
  }
  revision 2019-04-05 {
    description
      "Initial revision.";
  }

  deviation "/ncs:devices/ncs:template/ncs:ned-id/ncs:config/software-mgmt:software" {
    deviate not-supported;
  }
  deviation "/ncs:devices/ncs:device/ncs:live-status/software-mgmt:software" {
    deviate not-supported;
  }
  deviation "/ncs:devices/ncs:device/ncs:config/software-mgmt:software" {
    deviate not-supported;
  }
  deviation "/ncs:devices/ncs:device/ncs:live-status/software-mgmt:software-state/software-mgmt:auto-revert-timer" {
    deviate not-supported;
  }
  deviation "/ncs:devices/ncs:device/ncs:live-status/software-mgmt:software-state/software-mgmt:user-revert-timer" {
    deviate not-supported;
  }
  deviation "/ncs:devices/ncs:device/ncs:live-status/software-mgmt:software-state/software-mgmt:running-package/software-mgmt:package-status" {
    deviate not-supported;
  }
  deviation "/ncs:devices/ncs:device/ncs:live-status/software-mgmt:software-state/software-mgmt:running-package/software-mgmt:release-status" {
    deviate not-supported;
  }
  deviation "/ncs:devices/ncs:device/ncs:live-status/software-mgmt:software-state/software-mgmt:running-package/software-mgmt:active-bootchain/software-mgmt:status" {
    deviate not-supported;
  }
  deviation "/ncs:devices/ncs:device/ncs:live-status/software-mgmt:software-state/software-mgmt:running-package/software-mgmt:standby-bootchain" {
    deviate not-supported;
  }
  deviation "/ncs:devices/ncs:device/ncs:live-status/software-mgmt:software-state/software-mgmt:running-package/software-mgmt:release-package" {
    deviate not-supported;
  }
  deviation "/ncs:devices/ncs:device/ncs:live-status/software-mgmt:software-state/software-mgmt:running-package/software-mgmt:kernel" {
    deviate not-supported;
  }
  deviation "/ncs:devices/ncs:device/ncs:live-status/software-mgmt:software-state/software-mgmt:running-package/software-mgmt:uboot" {
    deviate not-supported;
  }
  deviation "/ncs:devices/ncs:device/ncs:live-status/software-mgmt:software-state/software-mgmt:package/software-mgmt:active-bootchain" {
    deviate not-supported;
  }
  deviation "/ncs:devices/ncs:device/ncs:live-status/software-mgmt:software-state/software-mgmt:package/software-mgmt:standby-bootchain" {
    deviate not-supported;
  }
  deviation "/ncs:devices/ncs:device/ncs:live-status/software-mgmt:software-state/software-mgmt:package/software-mgmt:release-package" {
    deviate not-supported;
  }
  deviation "/ncs:devices/ncs:device/ncs:live-status/software-mgmt:software-state/software-mgmt:package/software-mgmt:kernel" {
    deviate not-supported;
  }
  deviation "/ncs:devices/ncs:device/ncs:live-status/software-mgmt:software-state/software-mgmt:package/software-mgmt:uboot" {
    deviate not-supported;
  }
  deviation "/ncs:devices/ncs:device/ncs:rpc/software-mgmt:rpc-software-activate/software-mgmt:software-activate/software-mgmt:input/software-mgmt:allow-service-disruption" {
    deviate not-supported;
  }
  deviation "/ncs:devices/ncs:device/ncs:rpc/software-mgmt:rpc-software-activate/software-mgmt:software-activate/software-mgmt:input/software-mgmt:force-standby" {
    deviate not-supported;
  }
  deviation "/ncs:devices/ncs:device/ncs:rpc/software-mgmt:rpc-software-activate/software-mgmt:software-activate/software-mgmt:input/software-mgmt:revert-timeout" {
    deviate not-supported;
  }
  deviation "/ncs:devices/ncs:device/ncs:rpc/software-mgmt:rpc-software-cancel/software-mgmt:software-cancel" {
    deviate not-supported;
  }
  deviation "/ncs:devices/ncs:device/ncs:rpc/software-mgmt:rpc-software-download/software-mgmt:software-download/software-mgmt:input/software-mgmt:file-transfer-syntax/software-mgmt:component/software-mgmt:filename" {
    deviate not-supported;
  }
  deviation "/ncs:devices/ncs:device/ncs:rpc/software-mgmt:rpc-software-download/software-mgmt:software-download/software-mgmt:input/software-mgmt:file-transfer-syntax/software-mgmt:component/software-mgmt:server-type" {
    deviate not-supported;
  }
  deviation "/ncs:devices/ncs:device/ncs:rpc/software-mgmt:rpc-software-download/software-mgmt:software-download/software-mgmt:input/software-mgmt:file-transfer-syntax/software-mgmt:component/software-mgmt:address" {
    deviate not-supported;
  }
  deviation "/ncs:devices/ncs:device/ncs:rpc/software-mgmt:rpc-software-download/software-mgmt:software-download/software-mgmt:input/software-mgmt:file-transfer-syntax/software-mgmt:component/software-mgmt:login-id" {
    deviate not-supported;
  }
  deviation "/ncs:devices/ncs:device/ncs:rpc/software-mgmt:rpc-software-download/software-mgmt:software-download/software-mgmt:input/software-mgmt:file-transfer-syntax/software-mgmt:component/software-mgmt:password" {
    deviate not-supported;
  }
  deviation "/ncs:devices/ncs:device/ncs:rpc/software-mgmt:rpc-software-download/software-mgmt:software-download/software-mgmt:input/software-mgmt:file-transfer-syntax/software-mgmt:component" {
    deviate not-supported;
  }
  deviation "/ncs:devices/ncs:device/ncs:rpc/software-mgmt:rpc-software-download/software-mgmt:software-download/software-mgmt:input/software-mgmt:destination-path" {
    deviate not-supported;
  }
  deviation "/ncs:devices/ncs:device/ncs:rpc/software-mgmt:rpc-software-install/software-mgmt:software-install/software-mgmt:input/software-mgmt:package-path" {
    deviate not-supported;
  }
  deviation "/ncs:devices/ncs:device/ncs:rpc/software-mgmt:rpc-software-install/software-mgmt:software-install/software-mgmt:input/software-mgmt:file-transfer-syntax/software-mgmt:component/software-mgmt:filename" {
    deviate not-supported;
  }
  deviation "/ncs:devices/ncs:device/ncs:rpc/software-mgmt:rpc-software-install/software-mgmt:software-install/software-mgmt:input/software-mgmt:file-transfer-syntax/software-mgmt:component/software-mgmt:server-type" {
    deviate not-supported;
  }
  deviation "/ncs:devices/ncs:device/ncs:rpc/software-mgmt:rpc-software-install/software-mgmt:software-install/software-mgmt:input/software-mgmt:file-transfer-syntax/software-mgmt:component/software-mgmt:address" {
    deviate not-supported;
  }
  deviation "/ncs:devices/ncs:device/ncs:rpc/software-mgmt:rpc-software-install/software-mgmt:software-install/software-mgmt:input/software-mgmt:file-transfer-syntax/software-mgmt:component/software-mgmt:login-id" {
    deviate not-supported;
  }
  deviation "/ncs:devices/ncs:device/ncs:rpc/software-mgmt:rpc-software-install/software-mgmt:software-install/software-mgmt:input/software-mgmt:file-transfer-syntax/software-mgmt:component/software-mgmt:password" {
    deviate not-supported;
  }
  deviation "/ncs:devices/ncs:device/ncs:rpc/software-mgmt:rpc-software-install/software-mgmt:software-install/software-mgmt:input/software-mgmt:file-transfer-syntax/software-mgmt:component" {
    deviate not-supported;
  }
  deviation "/ncs:devices/ncs:device/ncs:rpc/software-mgmt:rpc-software-install/software-mgmt:software-install/software-mgmt:input/software-mgmt:defer-activation" {
    deviate add {
      default "false";
    }
  }
  deviation "/ncs:devices/ncs:device/ncs:rpc/software-mgmt:rpc-software-protect/software-mgmt:software-protect" {
    deviate not-supported;
  }
  deviation "/ncs:devices/ncs:device/ncs:rpc/software-mgmt:rpc-software-validate/software-mgmt:software-validate" {
    deviate not-supported;
  }
}
