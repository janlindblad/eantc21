module ciena-dns-client {
  // Generated by yanger -t ncs
  tailf:mount-id "saos1051-nc-1.0:saos1051-nc-1.0";
  tailf:ncs-device-type "netconf";

  namespace "http://www.ciena.com/ns/yang/ciena-dns-client";
  prefix dnsc;

  import ciena-types {
    prefix ciena;
  }
  import ietf-inet-types {
    prefix inet;
  }
  import openconfig-system {
    prefix oc-sys;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's global configuration for DNS client settings.

     Copyright (c) 2016 Ciena Corporation.  All rights
     reserved.

     All information contained herein is, and remains
     the property of Ciena Corporation. Dissemination of this
     information or reproduction of this material is strictly
     forbidden unless prior written permission is obtained from
     Ciena Corporation.";

  revision 2019-12-11 {
    description
      "Add default value of 'enabled' for dns-client
       admin-status";
    reference "";
  }
  revision 2017-05-25 {
    description
      "Initial version";
    reference
      "RFC 6020: YANG - A Data Modeling Language for
       the Network Configuration Protocol (NETCONF).
       No specific reference; standard not available.";
  }

  typedef ncs_template_dns-scope {
    type string;
    description
      "Whether the currently operational DNS parameter was configured by the
       user, DHCPv4, or DHCPv6.";
  }

  typedef ncs_rpc_notif_dns-scope {
    type enumeration {
      enum "user" {
        description
          "The user-configured DNS parameter is currently operational.";
      }
      enum "dhcpv4" {
        description
          "The DHCPv4-configured DNS parameter is currently operational.";
      }
      enum "dhcpv6" {
        description
          "The DHCPv6-configured DNS parameter is currently operational.";
      }
    }
    description
      "Whether the currently operational DNS parameter was configured by the
       user, DHCPv4, or DHCPv6.";
  }

  typedef live_ncs_dns-scope {
    type enumeration {
      enum "user" {
        description
          "The user-configured DNS parameter is currently operational.";
      }
      enum "dhcpv4" {
        description
          "The DHCPv4-configured DNS parameter is currently operational.";
      }
      enum "dhcpv6" {
        description
          "The DHCPv6-configured DNS parameter is currently operational.";
      }
    }
    description
      "Whether the currently operational DNS parameter was configured by the
       user, DHCPv4, or DHCPv6.";
  }

  typedef dns-scope {
    type enumeration {
      enum "user" {
        description
          "The user-configured DNS parameter is currently operational.";
      }
      enum "dhcpv4" {
        description
          "The DHCPv4-configured DNS parameter is currently operational.";
      }
      enum "dhcpv6" {
        description
          "The DHCPv6-configured DNS parameter is currently operational.";
      }
    }
    description
      "Whether the currently operational DNS parameter was configured by the
       user, DHCPv4, or DHCPv6.";
  }

  grouping ncs_template_dhcp-server {
    description
      "Operational data pertaining to DNS servers configured through DHCP.";
    leaf domain-name {
      type string;
      description
        "Specifies the domain name configured through DHCP.";
    }
    list server {
      // NCS patched for predictable order
      ordered-by user;
      key "address";
      description
        "State information pertaining to a DNS server configured through DHCP.";
      leaf address {
        type string;
        description
          "The IP address of the DNS server.";
      }
      leaf admin-status {
        type ciena:ncs_template_admin-state;
        description
          "The administrative state of the DNS server.";
      }
      leaf oper-status {
        type ciena:ncs_template_oper-state;
        description
          "The operational state of the DNS server.";
      }
    }
  }

  grouping ncs_rpc_notif_dhcp-server {
    description
      "Operational data pertaining to DNS servers configured through DHCP.";
    leaf domain-name {
      type inet:domain-name;
      description
        "Specifies the domain name configured through DHCP.";
    }
    list server {
      key "address";
      description
        "State information pertaining to a DNS server configured through DHCP.";
      leaf address {
        type inet:ip-address;
        description
          "The IP address of the DNS server.";
      }
      leaf admin-status {
        type ciena:ncs_rpc_notif_admin-state;
        description
          "The administrative state of the DNS server.";
      }
      leaf oper-status {
        type ciena:ncs_rpc_notif_oper-state;
        description
          "The operational state of the DNS server.";
      }
    }
  }

  grouping live_ncs_dhcp-server {
    description
      "Operational data pertaining to DNS servers configured through DHCP.";
    leaf domain-name {
      type inet:domain-name;
      description
        "Specifies the domain name configured through DHCP.";
    }
    list server {
      key "address";
      description
        "State information pertaining to a DNS server configured through DHCP.";
      leaf address {
        type inet:ip-address;
        description
          "The IP address of the DNS server.";
      }
      leaf admin-status {
        type ciena:live_ncs_admin-state;
        description
          "The administrative state of the DNS server.";
      }
      leaf oper-status {
        type ciena:live_ncs_oper-state;
        description
          "The operational state of the DNS server.";
      }
    }
  }

  grouping dhcp-server {
    description
      "Operational data pertaining to DNS servers configured through DHCP.";
    leaf domain-name {
      type inet:domain-name;
      description
        "Specifies the domain name configured through DHCP.";
    }
    list server {
      key "address";
      description
        "State information pertaining to a DNS server configured through DHCP.";
      leaf address {
        type inet:ip-address;
        description
          "The IP address of the DNS server.";
      }
      leaf admin-status {
        type ciena:admin-state;
        description
          "The administrative state of the DNS server.";
      }
      leaf oper-status {
        type ciena:oper-state;
        description
          "The operational state of the DNS server.";
      }
    }
  }

  augment "/ncs:devices/ncs:device/ncs:rpc" {
    container rpc-resolve-hostname {
      tailf:ncs-device-type "netconf";
      tailf:display-when "not(../../ncs:module) or ../../ncs:module[ncs:name='ciena-dns-client']";
      tailf:action resolve-hostname {
        tailf:actionpoint ncsproxy {
          tailf:internal;
        }
        description
          "Resolve a host name to an IP address.";
        input {
          leaf host-name {
            type inet:domain-name;
            description
              "The host name to be resolved.";
          }
        }
        output {
          leaf address {
            type inet:ip-address;
            description
              "The IP address resolved from the input host name.";
          }
        }
      }
    }
  }
  augment "/ncs:devices/ncs:device-group/ncs:ned-id/ncs:rpc" {
    container rpc-resolve-hostname {
      tailf:ncs-device-type "netconf";
      tailf:display-when "/ncs:devices/ncs:device[ncs:name=current()/../../../ncs:member]/ncs:module[ncs:name='ciena-dns-client']";
      tailf:action resolve-hostname {
        tailf:actionpoint ncsproxy {
          tailf:internal;
        }
        description
          "Resolve a host name to an IP address.";
        input {
          leaf host-name {
            type inet:domain-name;
            description
              "The host name to be resolved.";
          }
        }
        output {
          container "device" {
            leaf "name" {
              type string;
            }
            leaf "info" {
              type string;
            }
            container "result" {
              leaf address {
                type inet:ip-address;
                description
                  "The IP address resolved from the input host name.";
              }
            }
          }
        }
      }
    }
  }
  augment "/ncs:devices/ncs:device/ncs:rpc" {
    container rpc-resolve-ip {
      tailf:ncs-device-type "netconf";
      tailf:display-when "not(../../ncs:module) or ../../ncs:module[ncs:name='ciena-dns-client']";
      tailf:action resolve-ip {
        tailf:actionpoint ncsproxy {
          tailf:internal;
        }
        description
          "Resolve an IP address to a host name.";
        input {
          leaf address {
            type inet:ip-address;
            description
              "The IP address to be resolved.";
          }
        }
        output {
          leaf host-name {
            type inet:domain-name;
            description
              "The host name resolved from the input IP address.";
          }
        }
      }
    }
  }
  augment "/ncs:devices/ncs:device-group/ncs:ned-id/ncs:rpc" {
    container rpc-resolve-ip {
      tailf:ncs-device-type "netconf";
      tailf:display-when "/ncs:devices/ncs:device[ncs:name=current()/../../../ncs:member]/ncs:module[ncs:name='ciena-dns-client']";
      tailf:action resolve-ip {
        tailf:actionpoint ncsproxy {
          tailf:internal;
        }
        description
          "Resolve an IP address to a host name.";
        input {
          leaf address {
            type inet:ip-address;
            description
              "The IP address to be resolved.";
          }
        }
        output {
          container "device" {
            leaf "name" {
              type string;
            }
            leaf "info" {
              type string;
            }
            container "result" {
              leaf host-name {
                type inet:domain-name;
                description
                  "The host name resolved from the input IP address.";
              }
            }
          }
        }
      }
    }
  }
  augment "/ncs:devices/ncs:template/ncs:ned-id/ncs:config/oc-sys:system" {
    container dns {
      container dns-client {
        description
          "Configuration parameters of the DNS client resolver.";
        leaf admin-status {
          type ciena:ncs_template_admin-state;
          // NCS drop default statement
          description
            "The global administrative state of the DNS client resolver.";
        }
        leaf domain-name {
          type string;
          description
            "Specifies the domain name configured by the user for this device.";
        }
        list server {
          // NCS patched for predictable order
          ordered-by user;
          key "address";
          description
            "Defines administrative information pertaining to a DNS server
              configured by the user.";
          leaf address {
            type string;
            description
              "The IP address of the configured DNS server.";
          }
          leaf admin-status {
            type ciena:ncs_template_admin-state;
            description
              "The administrative state of the configured DNS server.";
          }
        }
      }
      // NCS drop config false container 'dns-client-state'
    }
  }
  augment "/ncs:devices/ncs:device/ncs:live-status/oc-sys:system" {
    container dns {
      tailf:ncs-device-type "netconf";
      tailf:display-when "not(../../../ncs:module) or ../../../ncs:module[ncs:name='ciena-dns-client'] or (../../../ncs:live-status-protocol[not(ncs:capability)]) or (../../../ncs:live-status-protocol/ncs:capability/ncs:module[.='ciena-dns-client'])";
      container dns-client {
        description
          "Configuration parameters of the DNS client resolver.";
        leaf admin-status {
          type ciena:live_ncs_admin-state;
          // NCS drop default statement
          description
            "The global administrative state of the DNS client resolver.";
        }
        leaf domain-name {
          type string {
            length "0..64";
          }
          description
            "Specifies the domain name configured by the user for this device.";
        }
        list server {
          key "address";
          ordered-by user;
          description
            "Defines administrative information pertaining to a DNS server
              configured by the user.";
          leaf address {
            type inet:ip-address;
            description
              "The IP address of the configured DNS server.";
          }
          leaf admin-status {
            type ciena:live_ncs_admin-state;
            description
              "The administrative state of the configured DNS server.";
          }
        }
      }
      container dns-client-state {
        description
          "Operational data for the DNS client resolver.";
        leaf domain-name-scope {
          type live_ncs_dns-scope;
          description
            "Whether the currently operational domain name is user,
             DHCPv4, or DHCPv6.";
        }
        leaf server-scope {
          type live_ncs_dns-scope;
          description
            "Whether the currently operational DNS server is user,
             DHCPv4, or DHCPv6.";
        }
        container user-servers {
          description
            "Operational data pertaining to DNS servers configured by the user.";
          list server {
            key "address";
            description
              "State information pertaining to a DNS server configured by the user.";
            leaf address {
              type inet:ip-address;
              description
                "The IP address of the configured DNS server.";
            }
            leaf oper-status {
              type ciena:live_ncs_oper-state;
              description
                "The operational state of the configured DNS server.";
            }
          }
        }
        container dhcpv4-servers {
          description
            "Operational data pertaining to DNS servers configured through DHCPv4.";
          uses live_ncs_dhcp-server;
        }
        container dhcpv6-servers {
          description
            "Operational data pertaining to DNS servers configured through DHCPv6.";
          uses live_ncs_dhcp-server;
        }
      }
    }
  }
  augment "/ncs:devices/ncs:device/ncs:config/oc-sys:system" {
    container dns {
      tailf:ncs-device-type "netconf";
      tailf:display-when "not(../../../ncs:module) or ../../../ncs:module[ncs:name='ciena-dns-client']";
      container dns-client {
        description
          "Configuration parameters of the DNS client resolver.";
        leaf admin-status {
          type ciena:admin-state;
          default "enabled";
          description
            "The global administrative state of the DNS client resolver.";
        }
        leaf domain-name {
          type string {
            length "0..64";
          }
          description
            "Specifies the domain name configured by the user for this device.";
        }
        list server {
          key "address";
          ordered-by user;
          description
            "Defines administrative information pertaining to a DNS server
              configured by the user.";
          leaf address {
            type inet:ip-address;
            description
              "The IP address of the configured DNS server.";
          }
          leaf admin-status {
            type ciena:admin-state;
            description
              "The administrative state of the configured DNS server.";
          }
        }
      }
      // NCS drop config false container 'dns-client-state'
    }
  }
}
