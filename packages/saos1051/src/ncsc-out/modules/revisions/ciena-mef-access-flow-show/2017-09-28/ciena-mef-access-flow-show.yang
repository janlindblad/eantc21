module ciena-mef-access-flow-show {
  // Generated by yanger -t ncs
  tailf:mount-id "saos1051-nc-1.0:saos1051-nc-1.0";
  tailf:ncs-device-type "netconf";

  yang-version 1.1;
  namespace "http://www.ciena.com/ns/ciena-mef-access-flow-show";
  prefix ciena-mef-access-flow-show;

  import yangcli-pro {
    prefix yp;
  }
  import tailf-common {
    prefix tailf;
  }
  import tailf-ncs {
    prefix ncs;
  }

  description
    "Show command extensions by ciena for ciena-mef-access-flow";

  revision 2017-09-28 {
    description
      "Initial version";
  }

  augment "/ncs:devices/ncs:device/ncs:rpc/yp:rpc-show/yp:show/yp:input/yp:showtype" {
    case acl-action {
      leaf acl-action {
        type union {
          type string;
        }
      }
    }
    case access-flow {
      leaf access-flow {
        type union {
          type string;
        }
      }
    }
    case acl-custom-destinations {
      leaf acl-custom-destinations {
        type union {
          type string;
        }
      }
    }
  }
}
