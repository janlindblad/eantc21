module ciena-packet-pm-deviation {
  // Generated by yanger -t ncs
  tailf:mount-id "saos1051-nc-1.0:saos1051-nc-1.0";
  tailf:ncs-device-type "netconf";

  namespace "http://www.ciena.com/ns/yang/ciena-packet-pm-deviation";
  prefix ciena-pm-deviation;

  import ciena-packet-pm {
    prefix ciena-pm;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";

  revision 2018-11-07 {
    description
      "Initial revision";
  }

  deviation "/ncs:devices/ncs:template/ncs:ned-id/ncs:config/ciena-pm:pm/ciena-pm:ethernet-performance-instances" {
    deviate not-supported;
  }
  deviation "/ncs:devices/ncs:device/ncs:live-status/ciena-pm:pm/ciena-pm:ethernet-performance-instances" {
    deviate not-supported;
  }
  deviation "/ncs:devices/ncs:device/ncs:config/ciena-pm:pm/ciena-pm:ethernet-performance-instances" {
    deviate not-supported;
  }
}
