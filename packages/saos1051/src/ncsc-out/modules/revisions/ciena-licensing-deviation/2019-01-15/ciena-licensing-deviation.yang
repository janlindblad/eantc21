module ciena-licensing-deviation {
  // Generated by yanger -t ncs
  tailf:mount-id "saos1051-nc-1.0:saos1051-nc-1.0";
  tailf:ncs-device-type "netconf";

  namespace "urn:ciena:params:xml:ns:yang:ciena:ciena-licensing-deviation";
  prefix ciena-licensing-deviation;

  import ciena-licensing {
    prefix ciena-licensing;
  }
  import tailf-common {
    prefix tailf;
  }
  import tailf-ncs {
    prefix ncs;
  }

  organization
    "Ciena Corporation";
  contact
    "Web URL: http://www.ciena.com/
     Postal:  7035 Ridge Road
              Hanover, Maryland 21076
              U.S.A.
     Phone:   +1 800-921-1144
     Fax:     +1 410-694-5750";
  description
    "This YANG module defines Ciena's licensing deviations.";

  revision 2019-01-15 {
    description
      "Removed license type leaf.";
    reference "No specific reference; standard not available.";
  }
  revision 2017-04-28 {
    description
      "1.0";
    reference "No specific reference; standard not available.";
  }

  deviation "/ncs:devices/ncs:template/ncs:ned-id/ncs:config/ciena-licensing:license-management-config/ciena-licensing:license-server-config" {
    deviate replace {
      // NCS drop max-elements statement
    }
  }
  deviation "/ncs:devices/ncs:device/ncs:live-status/ciena-licensing:license-management-config/ciena-licensing:license-server-config" {
    deviate replace {
      // NCS drop max-elements statement
    }
  }
  deviation "/ncs:devices/ncs:device/ncs:config/ciena-licensing:license-management-config/ciena-licensing:license-server-config" {
    deviate replace {
      max-elements 1;
    }
  }
  deviation "/ncs:devices/ncs:device/ncs:live-status/ciena-licensing:license-management-state/ciena-licensing:license-client-state/ciena-licensing:license-feature/ciena-licensing:properties/ciena-licensing:type" {
    deviate not-supported;
  }
}
