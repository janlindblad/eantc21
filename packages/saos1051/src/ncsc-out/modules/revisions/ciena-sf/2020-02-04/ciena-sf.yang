module ciena-sf {
  // Generated by yanger -t ncs
  tailf:mount-id "saos1051-nc-1.0:saos1051-nc-1.0";
  tailf:ncs-device-type "netconf";

  namespace "urn:ciena:params:xml:ns:yang:ciena-pn::ciena-sf";
  prefix sf;

  import ciena-mef-logical-port {
    prefix mef-logical-port;
  }
  import ietf-yang-types {
    prefix yt;
  }
  import ciena-file-mgmt {
    prefix file-mgmt;
  }
  import ciena-vdisk-mgmt {
    prefix vdisk-mgmt;
  }
  import ciena-types {
    prefix ct;
  }
  import openconfig-interfaces {
    prefix oc-if;
  }
  import ciena-openconfig-interfaces {
    prefix cn-oc-if;
  }
  import ciena-openconfig-if-ethernet-port {
    prefix cn-oc-if-eth;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines Ciena's management data definition
     for the orchestration of service functions

     Copyright (c) 2016  Ciena Corporation.  All rights
     reserved.

     All information contained herein is, and remains the
     property of Ciena Corporation. Dissemination of this
     information or reproduction of this material is strictly
     forbidden unless prior written permission is obtained
     from Ciena Corporation.";

  revision 2020-02-04 {
    description
      "Updated description field.
       Adding support for downloadable vDisks.
       Added multi socket and NUMA support.
       Added SF type support.
       Added internal DHCP support.
       Added physical NIC support.
       Added e1000 driver support for network interfaces.
       Added new state enum to indicate ETTP not ready to use & Invalid XML.";
  }
  revision 2020-01-13 {
    description
      "Adding ISO support for cloud-init.
       Adding ide vdisk driver type support";
  }
  revision 2019-03-20 {
    description
      "Adding support for notication in the yang model.
       Added SF interface stats.
       Fix the unit of leaf mem-allocated.
       Added cloud-init nodes";
  }
  revision 2017-06-02 {
    description
      "1.3";
  }

  grouping ncs_template_virtual-disk-attribute {
    leaf sf-device-loc {
      type string;
      description
        "Device location where the virtual disk will be installed inside the SF";
    }
    leaf vdisk-driver-type {
      type string;
      description
        "Type of driver to be emulated for the SF. Following types are supported:
         virtio: virtualization standard for disk device drivers";
    }
  }

  grouping ncs_template_virtual-disk-group {
    list sf-vdisk {
      // NCS patched for predictable order
      ordered-by user;
      description
        "List of virtual disks to be attached to the SF";
      key "sf-device-loc";
      unique "boot-order";
      uses ncs_template_virtual-disk-attribute;
      choice sf-vdisk {
        case vdisk {
          leaf vdisk-ref {
            type string;
            description
              "Reference to a virtual disk created using ciena-vdisk-mgmt yang model";
          }
        }
      }
      leaf boot-order {
        type string;
        description
          "Boot order for the vdisk. If no boot-order value is provided for any vDisk,
           software will add boot-order, the order in which vDisks were attached";
      }
    }
  }

  grouping ncs_rpc_notif_virtual-disk-attribute {
    leaf sf-device-loc {
      type string {
        length "1..255";
      }
      description
        "Device location where the virtual disk will be installed inside the SF";
    }
    leaf vdisk-driver-type {
      type enumeration {
        enum "virtio" {
          description
            "emulate virtio bus for a VNF";
        }
        enum "ide" {
          description
            "emulate ide bus for a VNF";
        }
      }
      description
        "Type of driver to be emulated for the SF. Following types are supported:
         virtio: virtualization standard for disk device drivers";
    }
  }

  grouping ncs_rpc_notif_virtual-disk-group {
    list sf-vdisk {
      description
        "List of virtual disks to be attached to the SF";
      key "sf-device-loc";
      unique "boot-order";
      uses ncs_rpc_notif_virtual-disk-attribute;
      choice sf-vdisk {
        case vdisk {
          leaf vdisk-ref {
            type string;
            description
              "Reference to a virtual disk created using ciena-vdisk-mgmt yang model";
          }
        }
      }
      leaf boot-order {
        type uint8 {
          range "1..max";
        }
        description
          "Boot order for the vdisk. If no boot-order value is provided for any vDisk,
           software will add boot-order, the order in which vDisks were attached";
      }
    }
  }

  grouping live_ncs_virtual-disk-attribute {
    leaf sf-device-loc {
      type string {
        length "1..255";
      }
      description
        "Device location where the virtual disk will be installed inside the SF";
    }
    leaf vdisk-driver-type {
      type enumeration {
        enum "virtio" {
          description
            "emulate virtio bus for a VNF";
        }
        enum "ide" {
          description
            "emulate ide bus for a VNF";
        }
      }
      description
        "Type of driver to be emulated for the SF. Following types are supported:
         virtio: virtualization standard for disk device drivers";
    }
  }

  grouping live_ncs_virtual-disk-group {
    list sf-vdisk {
      description
        "List of virtual disks to be attached to the SF";
      key "sf-device-loc";
      unique "boot-order";
      uses live_ncs_virtual-disk-attribute;
      choice sf-vdisk {
        case vdisk {
          leaf vdisk-ref {
            type leafref {
              path "/ncs:devices/ncs:device/ncs:live-status/vdisk-mgmt:vdisks/vdisk-mgmt:vdisk/vdisk-mgmt:vdisk-name" {
                tailf:xpath-root 3;
              }
            }
            description
              "Reference to a virtual disk created using ciena-vdisk-mgmt yang model";
          }
        }
      }
      leaf boot-order {
        type uint8 {
          range "1..max";
        }
        description
          "Boot order for the vdisk. If no boot-order value is provided for any vDisk,
           software will add boot-order, the order in which vDisks were attached";
      }
    }
  }

  grouping virtual-disk-attribute {
    leaf sf-device-loc {
      type string {
        length "1..255";
      }
      description
        "Device location where the virtual disk will be installed inside the SF";
    }
    leaf vdisk-driver-type {
      type enumeration {
        enum "virtio" {
          description
            "emulate virtio bus for a VNF";
        }
        enum "ide" {
          description
            "emulate ide bus for a VNF";
        }
      }
      description
        "Type of driver to be emulated for the SF. Following types are supported:
         virtio: virtualization standard for disk device drivers";
    }
  }

  grouping virtual-disk-group {
    list sf-vdisk {
      description
        "List of virtual disks to be attached to the SF";
      key "sf-device-loc";
      unique "boot-order";
      uses virtual-disk-attribute;
      choice sf-vdisk {
        case vdisk {
          leaf vdisk-ref {
            type leafref {
              path "/ncs:devices/ncs:device/ncs:config/vdisk-mgmt:vdisks/vdisk-mgmt:vdisk/vdisk-mgmt:vdisk-name" {
                tailf:xpath-root 3;
              }
            }
            description
              "Reference to a virtual disk created using ciena-vdisk-mgmt yang model";
          }
        }
      }
      leaf boot-order {
        type uint8 {
          range "1..max";
        }
        description
          "Boot order for the vdisk. If no boot-order value is provided for any vDisk,
           software will add boot-order, the order in which vDisks were attached";
      }
    }
  }

  augment "/ncs:devices/ncs:device/ncs:rpc" {
    container rpc-snapshot {
      tailf:ncs-device-type "netconf";
      tailf:display-when "not(../../ncs:module) or ../../ncs:module[ncs:name='ciena-sf']";
      tailf:action snapshot {
        tailf:actionpoint ncsproxy {
          tailf:internal;
        }
        input {
          leaf sf-name {
            mandatory true;
            type string;
            description
              "Name of service function";
          }
          leaf snapshot-name {
            mandatory true;
            type string {
              length "1..200";
            }
            description
              "Name of snapshot";
          }
          leaf snapshot-action {
            type enumeration {
              enum "create";
              enum "revert";
              enum "delete";
            }
            description
              "Operations which can performed for a snapshot
               create : Send a request to create snapshot (with the name specified in snapshot-name)
                        for Service Function (specified under sf-name)
               revert : Send a request to revert a Service Function (specified under sf-name) to
                        previously taken snapshot (specified under snapshot-name)
               delete : Send a request to delete a snapshot (specified under snapshot-name) for a
                        particular Service Function (specified under sf-name)";
          }
        }
        description
          "RPC to create/delete/revert snapshots for a particular service function";
      }
    }
  }
  augment "/ncs:devices/ncs:device-group/ncs:ned-id/ncs:rpc" {
    container rpc-snapshot {
      tailf:ncs-device-type "netconf";
      tailf:display-when "/ncs:devices/ncs:device[ncs:name=current()/../../../ncs:member]/ncs:module[ncs:name='ciena-sf']";
      tailf:action snapshot {
        tailf:actionpoint ncsproxy {
          tailf:internal;
        }
        input {
          leaf sf-name {
            mandatory true;
            type string;
            description
              "Name of service function";
          }
          leaf snapshot-name {
            mandatory true;
            type string {
              length "1..200";
            }
            description
              "Name of snapshot";
          }
          leaf snapshot-action {
            type enumeration {
              enum "create";
              enum "revert";
              enum "delete";
            }
            description
              "Operations which can performed for a snapshot
               create : Send a request to create snapshot (with the name specified in snapshot-name)
                        for Service Function (specified under sf-name)
               revert : Send a request to revert a Service Function (specified under sf-name) to
                        previously taken snapshot (specified under snapshot-name)
               delete : Send a request to delete a snapshot (specified under snapshot-name) for a
                        particular Service Function (specified under sf-name)";
          }
        }
        description
          "RPC to create/delete/revert snapshots for a particular service function";
      }
    }
  }
  augment "/ncs:devices/ncs:device/ncs:netconf-notifications/ncs:received-notifications/ncs:notification/ncs:data" {
    container sf {
      presence "";
      config false;
      leaf name {
        type string;
        description
          "Name of the service function that triggered the notification.";
      }
      leaf state {
        type ct:ncs_rpc_notif_on-off-state;
        description
          "Represent the state of service function.";
      }
    }
  }
  augment "/ncs:devices/ncs:device/ncs:config" {
    container sfs {
      tailf:ncs-device-type "netconf";
      tailf:display-when "not(../../ncs:module) or ../../ncs:module[ncs:name='ciena-sf']";
      description
        "Service function details";
      list sf {
        key "sf-name";
        description
          "List of service functions";
        leaf sf-name {
          type string {
            length "1..12";
          }
          description
            "This object indicates the identifier and is a
             text string that is used to identify a service functions.
             Unique string values are chosen to uniquely identify
             the service function.";
        }
        leaf sf-type {
          type enumeration {
            enum "vnf" {
              description
                "VM based VNF";
            }
            enum "vm" {
              description
                "Virtual Machine";
            }
          }
          default "vnf";
          description
            "Type of SF";
        }
        container sfo {
          description
            "Service function orchestration information";
          container sfo-metadata {
            description
              "This container groups the attributed required to spawn a sf";
            leaf cpus {
              type uint16;
              description
                "Number of vCPUs";
            }
            list vcpus {
              description
                "List of virtual CPUs. Default affinity for list is thread-affinity shared";
              key "vcpu-group-name";
              leaf vcpu-group-name {
                type string {
                  length "1..255";
                }
                description
                  "Name for the vCPU or a group of vCPU's of the VNF";
              }
              leaf socket-id {
                type uint8;
                description
                  "CPU socket ID";
                default "0";
              }
              leaf-list vcpu-ids {
                type uint16;
                min-elements 1;
                description
                  "Single or a list of vCPU IDs of the VNF";
              }
              leaf core-affinity {
                type enumeration {
                  enum "exclusive" {
                    description
                      "Complete core is dedicated to the requested vCPU";
                  }
                }
                description
                  "Affinity to the core";
              }
              leaf thread-affinity {
                type enumeration {
                  enum "shared" {
                    description
                      "Thread is shared between multiple vCPU's";
                  }
                }
                description
                  "Affinity to the thread";
              }
            }
            leaf cpu-config {
              type enumeration {
                enum "host-passthrough" {
                  description
                    "Pass through host CPU as it is to service function";
                }
              }
              description
                "CPU Configuration exposure";
            }
            leaf memory {
              type uint32;
              units "MB";
              description
                "Memory size should be in the multiple of 2MB.";
            }
            list numa-node {
              description
                "NUMA node list";
              key "node-id";
              leaf node-id {
                type uint8;
                description
                  "NUMA node ID";
              }
              leaf memory {
                type uint32;
                units "MB";
                description
                  "Memory size should be in the multiple of 2MB.";
              }
            }
            uses virtual-disk-group;
          }
          list network-interface {
            key "name";
            ordered-by user;
            leaf name {
              type string;
              description
                "A name for the network";
            }
            leaf network-type {
              type enumeration {
                enum "tap" {
                  description
                    "TAP interface";
                }
                enum "vhost" {
                  description
                    "Vhost interface";
                }
                enum "default" {
                  description
                    "Management interface";
                }
                enum "dhcp" {
                  description
                    "Interface connected to internal DHCP";
                }
                enum "physical" {
                  description
                    "PCI pass through interface";
                }
              }
              description
                "Type of the network interface used for SF";
            }
            leaf logical-port {
              type mef-logical-port:logical-port-ref;
              description
                "Text string that is used to identify a logical port";
            }
            leaf ettp {
              type oc-if:base-interface-ref;
              must "/oc-if:interfaces/oc-if:interface[oc-if:name=current()]/oc-if:config/cn-oc-if:type = 'ettp' and /oc-if:interfaces/oc-if:interface[oc-if:name=current()]/oc-if:config/cn-oc-if-eth:ownership = 'not-owned'" {
                tailf:xpath-root 3;
                error-message "Referenced interface must be of type 'ettp' and ownership must be 'not-owned'";
              }
              description
                "Interface reference when network-type is physical";
            }
            leaf network-model {
              type enumeration {
                enum "virtio" {
                  description
                    "Emulate virtio NIC for the network-interface.
                     virtio is applicable to default, dhcp, vhost, tap
                     network interface type";
                }
                enum "e1000" {
                  description
                    "Emulate e1000 NIC for the network-interface.
                     e1000 is applicable to default, dhcp, tap
                     network interface type";
                }
              }
              description
                "Type of model to be emulated for the network interface.
                 If the network-model is not specifed, the S/W will default
                 to virtio for default, dhcp, vhost, tap network interfaces type
                 and for physical network interface type, S/W will default to vfio";
            }
          }
          container console {
            description
              "Console details";
            choice type {
              case vnc {
                leaf vnc-password {
                  type string;
                  description
                    "Password for VNC session used for accessing SF's console output";
                }
              }
            }
          }
          container cloud-init {
            description
              "Cloud init configuration";
            leaf user-data {
              type leafref {
                path "/ncs:devices/ncs:device/ncs:config/file-mgmt:files/file-mgmt:file/file-mgmt:file-name" {
                  tailf:xpath-root 3;
                }
              }
              description
                "Reference to file of type cloud-init-user-data";
            }
            leaf meta-data {
              type leafref {
                path "/ncs:devices/ncs:device/ncs:config/file-mgmt:files/file-mgmt:file/file-mgmt:file-name" {
                  tailf:xpath-root 3;
                }
              }
              description
                "Reference to file of type cloud-init-meta-data";
            }
            choice data-source {
              case no-cloud {
                choice source {
                  case cdrom {
                    uses virtual-disk-attribute;
                    leaf iso-file {
                      type leafref {
                        path "/ncs:devices/ncs:device/ncs:config/file-mgmt:files/file-mgmt:file/file-mgmt:file-name" {
                          tailf:xpath-root 3;
                        }
                      }
                      description
                        "Reference to file of type cloud-init-iso";
                    }
                    description
                      "Attach a pre-built ISO file to the SF. When this option is chosen
                       user doesn't have to provide above user-data/meta-data leafs";
                  }
                  description
                    "No-clound data source can support mounting CD-ROM or Floppy disk.
                     Currently only CD-ROM is supported";
                }
              }
              description
                "Specify data-source to be used for cloud-init and/or
                 specify any customization for a particular cloud-init
                 data-source";
            }
          }
          container image-mgmt {
            leaf image-path {
              type string;
              description
                "Complete URI location of the image to be downloaded/uploaded";
            }
            leaf libvirt-xml-path {
              type string;
              description
                "Optional xml file path for VM configuration Ex: CPU, memory requirement etc";
            }
            leaf image-size {
              type uint16;
              description
                "The image size in MB.";
            }
            leaf image-ref {
              type leafref {
                path "/ncs:devices/ncs:device/ncs:config/file-mgmt:files/file-mgmt:file/file-mgmt:file-name" {
                  tailf:xpath-root 3;
                }
              }
              description
                "Reference to file-name in ciena-file-mgmt.yang";
            }
            leaf image-encoding {
              type enumeration {
                enum "qcow2" {
                  description
                    "QCOW2 encoding";
                }
                enum "raw" {
                  description
                    "RAW encoding";
                }
              }
              description
                "Type of encoding for the image file";
            }
            uses virtual-disk-attribute;
            choice protocol {
              case ftp {
                leaf ftp-username {
                  type string;
                  description
                    "Username for FTP/SFTP/SCP transfer";
                }
                leaf ftp-password {
                  type string;
                  description
                    "Password for FTP/SFTP/SCP transfer";
                }
              }
              case sftp {
                leaf sftp-username {
                  type string;
                  description
                    "Username for FTP/SFTP/SCP transfer";
                }
                leaf sftp-password {
                  type string;
                  description
                    "Password for FTP/SFTP/SCP transfer";
                }
              }
              case scp {
                leaf scp-username {
                  type string;
                  description
                    "Username for FTP/SFTP/SCP transfer";
                }
                leaf scp-password {
                  type string;
                  description
                    "Password for FTP/SFTP/SCP transfer";
                }
              }
              case http {
                leaf http-username {
                  type string;
                  description
                    "Username for http/https server if required";
                }
                leaf http-password {
                  type string;
                  description
                    "Password for http/https server if required";
                }
                leaf http-checksum-file-path {
                  type string;
                  description
                    "Complete URI location of the checksum file to be downloaded";
                }
              }
              case https {
                leaf https-username {
                  type string;
                  description
                    "Username for http/https server if required";
                }
                leaf https-password {
                  type string;
                  description
                    "Password for http/https server if required";
                }
                leaf https-checksum-file-path {
                  type string;
                  description
                    "Complete URI location of the checksum file to be downloaded";
                }
              }
            }
          }
        }
        container sf-operation {
          leaf state {
            type enumeration {
              enum "start" {
                description
                  "Start SF";
              }
              enum "shutdown" {
                description
                  "Shutdown SF";
              }
              enum "suspend" {
                description
                  "Suspend SF";
              }
              enum "resume" {
                description
                  "Resume SF";
              }
            }
            description
              "List of operations supportd on a service function";
          }
        }
        // NCS drop config false container 'sf-state'
      }
    }
  }
  augment "/ncs:devices/ncs:device/ncs:live-status" {
    container sfs {
      tailf:ncs-device-type "netconf";
      tailf:display-when "not(../../ncs:module) or ../../ncs:module[ncs:name='ciena-sf'] or (../../ncs:live-status-protocol[not(ncs:capability)]) or (../../ncs:live-status-protocol/ncs:capability/ncs:module[.='ciena-sf'])";
      description
        "Service function details";
      list sf {
        key "sf-name";
        description
          "List of service functions";
        leaf sf-name {
          type string {
            length "1..12";
          }
          description
            "This object indicates the identifier and is a
             text string that is used to identify a service functions.
             Unique string values are chosen to uniquely identify
             the service function.";
        }
        leaf sf-type {
          type enumeration {
            enum "vnf" {
              description
                "VM based VNF";
            }
            enum "vm" {
              description
                "Virtual Machine";
            }
          }
          // NCS drop default statement
          description
            "Type of SF";
        }
        container sfo {
          description
            "Service function orchestration information";
          container sfo-metadata {
            description
              "This container groups the attributed required to spawn a sf";
            leaf cpus {
              type uint16;
              description
                "Number of vCPUs";
            }
            list vcpus {
              description
                "List of virtual CPUs. Default affinity for list is thread-affinity shared";
              key "vcpu-group-name";
              leaf vcpu-group-name {
                type string {
                  length "1..255";
                }
                description
                  "Name for the vCPU or a group of vCPU's of the VNF";
              }
              leaf socket-id {
                type uint8;
                description
                  "CPU socket ID";
                // NCS drop default statement
              }
              leaf-list vcpu-ids {
                type uint16;
                // NCS drop min-elements statement
                description
                  "Single or a list of vCPU IDs of the VNF";
              }
              leaf core-affinity {
                type enumeration {
                  enum "exclusive" {
                    description
                      "Complete core is dedicated to the requested vCPU";
                  }
                }
                description
                  "Affinity to the core";
              }
              leaf thread-affinity {
                type enumeration {
                  enum "shared" {
                    description
                      "Thread is shared between multiple vCPU's";
                  }
                }
                description
                  "Affinity to the thread";
              }
            }
            leaf cpu-config {
              type enumeration {
                enum "host-passthrough" {
                  description
                    "Pass through host CPU as it is to service function";
                }
              }
              description
                "CPU Configuration exposure";
            }
            leaf memory {
              type uint32;
              units "MB";
              description
                "Memory size should be in the multiple of 2MB.";
            }
            list numa-node {
              description
                "NUMA node list";
              key "node-id";
              leaf node-id {
                type uint8;
                description
                  "NUMA node ID";
              }
              leaf memory {
                type uint32;
                units "MB";
                description
                  "Memory size should be in the multiple of 2MB.";
              }
            }
            uses live_ncs_virtual-disk-group;
          }
          list network-interface {
            key "name";
            ordered-by user;
            leaf name {
              type string;
              description
                "A name for the network";
            }
            leaf network-type {
              type enumeration {
                enum "tap" {
                  description
                    "TAP interface";
                }
                enum "vhost" {
                  description
                    "Vhost interface";
                }
                enum "default" {
                  description
                    "Management interface";
                }
                enum "dhcp" {
                  description
                    "Interface connected to internal DHCP";
                }
                enum "physical" {
                  description
                    "PCI pass through interface";
                }
              }
              description
                "Type of the network interface used for SF";
            }
            leaf logical-port {
              type mef-logical-port:live_ncs_logical-port-ref;
              description
                "Text string that is used to identify a logical port";
            }
            leaf ettp {
              type oc-if:live_ncs_base-interface-ref;
              // NCS drop must statement
              description
                "Interface reference when network-type is physical";
            }
            leaf network-model {
              type enumeration {
                enum "virtio" {
                  description
                    "Emulate virtio NIC for the network-interface.
                     virtio is applicable to default, dhcp, vhost, tap
                     network interface type";
                }
                enum "e1000" {
                  description
                    "Emulate e1000 NIC for the network-interface.
                     e1000 is applicable to default, dhcp, tap
                     network interface type";
                }
              }
              description
                "Type of model to be emulated for the network interface.
                 If the network-model is not specifed, the S/W will default
                 to virtio for default, dhcp, vhost, tap network interfaces type
                 and for physical network interface type, S/W will default to vfio";
            }
          }
          container console {
            description
              "Console details";
            choice type {
              case vnc {
                leaf vnc-password {
                  type string;
                  description
                    "Password for VNC session used for accessing SF's console output";
                }
              }
            }
          }
          container cloud-init {
            description
              "Cloud init configuration";
            leaf user-data {
              type leafref {
                path "/ncs:devices/ncs:device/ncs:live-status/file-mgmt:files/file-mgmt:file/file-mgmt:file-name" {
                  tailf:xpath-root 3;
                }
              }
              description
                "Reference to file of type cloud-init-user-data";
            }
            leaf meta-data {
              type leafref {
                path "/ncs:devices/ncs:device/ncs:live-status/file-mgmt:files/file-mgmt:file/file-mgmt:file-name" {
                  tailf:xpath-root 3;
                }
              }
              description
                "Reference to file of type cloud-init-meta-data";
            }
            choice data-source {
              case no-cloud {
                choice source {
                  case cdrom {
                    uses live_ncs_virtual-disk-attribute;
                    leaf iso-file {
                      type leafref {
                        path "/ncs:devices/ncs:device/ncs:live-status/file-mgmt:files/file-mgmt:file/file-mgmt:file-name" {
                          tailf:xpath-root 3;
                        }
                      }
                      description
                        "Reference to file of type cloud-init-iso";
                    }
                    description
                      "Attach a pre-built ISO file to the SF. When this option is chosen
                       user doesn't have to provide above user-data/meta-data leafs";
                  }
                  description
                    "No-clound data source can support mounting CD-ROM or Floppy disk.
                     Currently only CD-ROM is supported";
                }
              }
              description
                "Specify data-source to be used for cloud-init and/or
                 specify any customization for a particular cloud-init
                 data-source";
            }
          }
          container image-mgmt {
            leaf image-path {
              type string;
              description
                "Complete URI location of the image to be downloaded/uploaded";
            }
            leaf libvirt-xml-path {
              type string;
              description
                "Optional xml file path for VM configuration Ex: CPU, memory requirement etc";
            }
            leaf image-size {
              type uint16;
              description
                "The image size in MB.";
            }
            leaf image-ref {
              type leafref {
                path "/ncs:devices/ncs:device/ncs:live-status/file-mgmt:files/file-mgmt:file/file-mgmt:file-name" {
                  tailf:xpath-root 3;
                }
              }
              description
                "Reference to file-name in ciena-file-mgmt.yang";
            }
            leaf image-encoding {
              type enumeration {
                enum "qcow2" {
                  description
                    "QCOW2 encoding";
                }
                enum "raw" {
                  description
                    "RAW encoding";
                }
              }
              description
                "Type of encoding for the image file";
            }
            uses live_ncs_virtual-disk-attribute;
            choice protocol {
              case ftp {
                leaf ftp-username {
                  type string;
                  description
                    "Username for FTP/SFTP/SCP transfer";
                }
                leaf ftp-password {
                  type string;
                  description
                    "Password for FTP/SFTP/SCP transfer";
                }
              }
              case sftp {
                leaf sftp-username {
                  type string;
                  description
                    "Username for FTP/SFTP/SCP transfer";
                }
                leaf sftp-password {
                  type string;
                  description
                    "Password for FTP/SFTP/SCP transfer";
                }
              }
              case scp {
                leaf scp-username {
                  type string;
                  description
                    "Username for FTP/SFTP/SCP transfer";
                }
                leaf scp-password {
                  type string;
                  description
                    "Password for FTP/SFTP/SCP transfer";
                }
              }
              case http {
                leaf http-username {
                  type string;
                  description
                    "Username for http/https server if required";
                }
                leaf http-password {
                  type string;
                  description
                    "Password for http/https server if required";
                }
                leaf http-checksum-file-path {
                  type string;
                  description
                    "Complete URI location of the checksum file to be downloaded";
                }
              }
              case https {
                leaf https-username {
                  type string;
                  description
                    "Username for http/https server if required";
                }
                leaf https-password {
                  type string;
                  description
                    "Password for http/https server if required";
                }
                leaf https-checksum-file-path {
                  type string;
                  description
                    "Complete URI location of the checksum file to be downloaded";
                }
              }
            }
          }
        }
        container sf-operation {
          leaf state {
            type enumeration {
              enum "start" {
                description
                  "Start SF";
              }
              enum "shutdown" {
                description
                  "Shutdown SF";
              }
              enum "suspend" {
                description
                  "Suspend SF";
              }
              enum "resume" {
                description
                  "Resume SF";
              }
            }
            description
              "List of operations supportd on a service function";
          }
        }
        container sf-state {
          description
            "Service function metrics.";
          leaf oper-state {
            type enumeration {
              enum "NoState" {
                description
                  "No state information available for SF";
              }
              enum "Running" {
                description
                  "SF is in running state";
              }
              enum "Blocked" {
                description
                  "SF is in blocked state";
              }
              enum "Paused" {
                description
                  "SF is in paused state";
              }
              enum "Shutdown" {
                description
                  "SF is in shutdown state";
              }
              enum "Shutoff" {
                description
                  "SF is in shutoff state";
              }
              enum "Crashed" {
                description
                  "SF has crashed";
              }
              enum "ShuttingDown" {
                description
                  "SF is being shutdown";
              }
              enum "Init" {
                description
                  "SF is being initialized";
              }
              enum "ImageDownloading" {
                description
                  "SF image is downloading";
              }
              enum "ImageDownloadFailed" {
                description
                  "SF image download has failed";
              }
              enum "ImageDownloaded" {
                description
                  "SF image download successful";
              }
              enum "XmlDownloading" {
                description
                  "SF XML is downloading";
              }
              enum "XmlDownloadFailed" {
                description
                  "SF XML download has failed";
              }
              enum "XmlDownloaded" {
                description
                  "SF XML download successful";
              }
              enum "ImgMaxSizeReached" {
                description
                  "SF image max download size reached";
              }
              enum "EttpOwnershipChangePending" {
                description
                  "ETTP not available for SF to use";
              }
              enum "InvalidXml" {
                description
                  "XML validation failed";
              }
            }
            description
              "Operation state of the service function.";
          }
          leaf num-cpus {
            type uint32;
            description
              "Number of virtual CPUs allocated to the instance.";
          }
          leaf cpu-time {
            type uint64;
            units "nanoseconds";
            description
              "Total CPU time used.";
          }
          leaf cpu-user-time {
            type uint64;
            units "nanoseconds";
            description
              "User CPU time";
          }
          leaf cpu-system-time {
            type uint64;
            units "nanoseconds";
            description
              "System CPU time";
          }
          leaf cpu-utilization {
            type uint8 {
              range "0..100";
            }
            units "percentage";
            description
              "Average CPU utilization in the Service function.";
          }
          leaf mem-allocated {
            type uint64;
            units "megabytes";
            description
              "Total memory available to the instance.";
          }
          leaf mem-resident {
            type uint64;
            units "bytes";
            description
              "Total memory used by the instance";
          }
          leaf mem-swap-in {
            type uint64;
            units "bytes";
            description
              "Total memory read from the swap space.";
          }
          leaf mem-swap-out {
            type uint64;
            units "bytes";
            description
              "Total memory written out to the swap space.";
          }
          leaf mem-major-fault {
            type uint64;
            units "bytes";
            description
              "Number of page faults that required disk IO to service.";
          }
          leaf mem-minor-fault {
            type uint64;
            units "bytes";
            description
              "Number of page faults that were serviced with requiring disk IO.";
          }
          leaf mem-available {
            type uint64;
            units "bytes";
            description
              "Total amount of memory available to the instance";
          }
          leaf mem-unused {
            type uint64;
            units "bytes";
            description
              "Total amount of memory not being used by the instance.";
          }
          container console {
            leaf vnc-port {
              type uint16;
              description
                "VNC port number for accessing SF's console output";
            }
          }
          list vcpu-pinning {
            description
              "virtual CPU to physical CPU pinning information";
            leaf vcpu-id {
              type uint16;
              description
                "virtual CPU ID of VNF/VM";
            }
            leaf-list cpu-id {
              type uint16;
              description
                "Physical CPU ID on host";
            }
          }
          list interfaces {
            key "name";
            leaf name {
              type string;
              description
                "A name for the Interface";
            }
            leaf network-type {
              type enumeration {
                enum "default";
                enum "tap";
                enum "vhost";
                enum "physical";
                enum "dhcp";
              }
              description
                "Type of the network interface used for SF";
            }
            leaf mac-address {
              type yt:mac-address;
              description
                "mac address of the interface";
            }
            container stats {
              // NCS drop when statement
              description
                "Interface statistics";
              leaf rxBytes {
                type uint64;
                description
                  "Received bytes";
              }
              leaf rxPkts {
                type uint64;
                description
                  "Received packets";
              }
              leaf rxDrops {
                type uint64;
                description
                  "Packets dropped";
              }
              leaf rxErrors {
                type uint64;
                description
                  "Receive errors";
              }
              leaf txBytes {
                type uint64;
                description
                  "Transmitted bytes";
              }
              leaf txPkts {
                type uint64;
                description
                  "Transmitted packets";
              }
              leaf txDrops {
                type uint64;
                description
                  "Packets dropped";
              }
              leaf txErrors {
                type uint64;
                description
                  "Transmission errors";
              }
            }
          }
          container snapshots {
            description
              "Details regarding snapshot for a SF";
            leaf current-snapshot-name {
              type string;
              description
                "Current snapshot name in use for a SF";
            }
            list snapshot {
              key "snapshot-name";
              description
                "List of all snapshots created by the snapshot RPC";
              leaf snapshot-name {
                type string;
                description
                  "Name of the snapshot provided as part of snapshot RPC";
              }
              leaf snapshot-status {
                type enumeration {
                  enum "Snapshot_Successful";
                  enum "Snapshot_Inprogress";
                  enum "Snapshot_Failed";
                }
                description
                  "Operation status of the snapshot.
                   Snapshot_Successful : Snapshot creation is successful
                   Snapshot_Inprogress : Snapshot creation is in progress
                   Snapshot_Failed     : Snapshot creation failed";
              }
              leaf snapshot-size {
                type uint32;
                description
                  "Amount of disk used by the snapshot. This value is in MB";
              }
            }
          }
        }
      }
    }
  }
  augment "/ncs:devices/ncs:template/ncs:ned-id/ncs:config" {
    container sfs {
      description
        "Service function details";
      list sf {
        // NCS patched for predictable order
        ordered-by user;
        key "sf-name";
        description
          "List of service functions";
        leaf sf-name {
          type string;
          description
            "This object indicates the identifier and is a
             text string that is used to identify a service functions.
             Unique string values are chosen to uniquely identify
             the service function.";
        }
        leaf sf-type {
          type string;
          // NCS drop default statement
          description
            "Type of SF";
        }
        container sfo {
          description
            "Service function orchestration information";
          container sfo-metadata {
            description
              "This container groups the attributed required to spawn a sf";
            leaf cpus {
              type string;
              description
                "Number of vCPUs";
            }
            list vcpus {
              // NCS patched for predictable order
              ordered-by user;
              description
                "List of virtual CPUs. Default affinity for list is thread-affinity shared";
              key "vcpu-group-name";
              leaf vcpu-group-name {
                type string;
                description
                  "Name for the vCPU or a group of vCPU's of the VNF";
              }
              leaf socket-id {
                type string;
                description
                  "CPU socket ID";
                // NCS drop default statement
              }
              leaf-list vcpu-ids {
                // NCS patched for predictable order
                ordered-by user;
                type string;
                // NCS drop min-elements statement
                description
                  "Single or a list of vCPU IDs of the VNF";
              }
              leaf core-affinity {
                type string;
                description
                  "Affinity to the core";
              }
              leaf thread-affinity {
                type string;
                description
                  "Affinity to the thread";
              }
            }
            leaf cpu-config {
              type string;
              description
                "CPU Configuration exposure";
            }
            leaf memory {
              type string;
              units "MB";
              description
                "Memory size should be in the multiple of 2MB.";
            }
            list numa-node {
              // NCS patched for predictable order
              ordered-by user;
              description
                "NUMA node list";
              key "node-id";
              leaf node-id {
                type string;
                description
                  "NUMA node ID";
              }
              leaf memory {
                type string;
                units "MB";
                description
                  "Memory size should be in the multiple of 2MB.";
              }
            }
            uses ncs_template_virtual-disk-group;
          }
          list network-interface {
            // NCS patched for predictable order
            ordered-by user;
            key "name";
            leaf name {
              type string;
              description
                "A name for the network";
            }
            leaf network-type {
              type string;
              description
                "Type of the network interface used for SF";
            }
            leaf logical-port {
              type mef-logical-port:ncs_template_logical-port-ref;
              description
                "Text string that is used to identify a logical port";
            }
            leaf ettp {
              type oc-if:ncs_template_base-interface-ref;
              // NCS drop must statement
              description
                "Interface reference when network-type is physical";
            }
            leaf network-model {
              type string;
              description
                "Type of model to be emulated for the network interface.
                 If the network-model is not specifed, the S/W will default
                 to virtio for default, dhcp, vhost, tap network interfaces type
                 and for physical network interface type, S/W will default to vfio";
            }
          }
          container console {
            description
              "Console details";
            choice type {
              case vnc {
                leaf vnc-password {
                  type string;
                  description
                    "Password for VNC session used for accessing SF's console output";
                }
              }
            }
          }
          container cloud-init {
            description
              "Cloud init configuration";
            leaf user-data {
              type string;
              description
                "Reference to file of type cloud-init-user-data";
            }
            leaf meta-data {
              type string;
              description
                "Reference to file of type cloud-init-meta-data";
            }
            choice data-source {
              case no-cloud {
                choice source {
                  case cdrom {
                    uses ncs_template_virtual-disk-attribute;
                    leaf iso-file {
                      type string;
                      description
                        "Reference to file of type cloud-init-iso";
                    }
                    description
                      "Attach a pre-built ISO file to the SF. When this option is chosen
                       user doesn't have to provide above user-data/meta-data leafs";
                  }
                  description
                    "No-clound data source can support mounting CD-ROM or Floppy disk.
                     Currently only CD-ROM is supported";
                }
              }
              description
                "Specify data-source to be used for cloud-init and/or
                 specify any customization for a particular cloud-init
                 data-source";
            }
          }
          container image-mgmt {
            leaf image-path {
              type string;
              description
                "Complete URI location of the image to be downloaded/uploaded";
            }
            leaf libvirt-xml-path {
              type string;
              description
                "Optional xml file path for VM configuration Ex: CPU, memory requirement etc";
            }
            leaf image-size {
              type string;
              description
                "The image size in MB.";
            }
            leaf image-ref {
              type string;
              description
                "Reference to file-name in ciena-file-mgmt.yang";
            }
            leaf image-encoding {
              type string;
              description
                "Type of encoding for the image file";
            }
            uses ncs_template_virtual-disk-attribute;
            choice protocol {
              case ftp {
                leaf ftp-username {
                  type string;
                  description
                    "Username for FTP/SFTP/SCP transfer";
                }
                leaf ftp-password {
                  type string;
                  description
                    "Password for FTP/SFTP/SCP transfer";
                }
              }
              case sftp {
                leaf sftp-username {
                  type string;
                  description
                    "Username for FTP/SFTP/SCP transfer";
                }
                leaf sftp-password {
                  type string;
                  description
                    "Password for FTP/SFTP/SCP transfer";
                }
              }
              case scp {
                leaf scp-username {
                  type string;
                  description
                    "Username for FTP/SFTP/SCP transfer";
                }
                leaf scp-password {
                  type string;
                  description
                    "Password for FTP/SFTP/SCP transfer";
                }
              }
              case http {
                leaf http-username {
                  type string;
                  description
                    "Username for http/https server if required";
                }
                leaf http-password {
                  type string;
                  description
                    "Password for http/https server if required";
                }
                leaf http-checksum-file-path {
                  type string;
                  description
                    "Complete URI location of the checksum file to be downloaded";
                }
              }
              case https {
                leaf https-username {
                  type string;
                  description
                    "Username for http/https server if required";
                }
                leaf https-password {
                  type string;
                  description
                    "Password for http/https server if required";
                }
                leaf https-checksum-file-path {
                  type string;
                  description
                    "Complete URI location of the checksum file to be downloaded";
                }
              }
            }
          }
        }
        container sf-operation {
          leaf state {
            type string;
            description
              "List of operations supportd on a service function";
          }
        }
        // NCS drop config false container 'sf-state'
      }
    }
  }
}
