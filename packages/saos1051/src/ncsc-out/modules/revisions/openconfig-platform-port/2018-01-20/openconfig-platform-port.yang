module openconfig-platform-port {
  // Generated by yanger -t ncs
  tailf:mount-id "saos1051-nc-1.0:saos1051-nc-1.0";
  tailf:ncs-device-type "netconf";

  yang-version 1;
  namespace "http://openconfig.net/yang/platform/port";
  prefix oc-port;

  import openconfig-platform {
    prefix oc-platform;
  }
  import openconfig-interfaces {
    prefix oc-if;
  }
  import openconfig-if-ethernet {
    prefix oc-eth;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines data related to PORT components in the openconfig-platform model";
  oc-ext:openconfig-version "0.3.0";

  revision 2018-01-20 {
    description
      "Added augmentation for interface-to-port reference";
    reference "0.3.0";
  }
  revision 2017-11-17 {
    description
      "Corrected augmentation path for port data";
    reference "0.2.0";
  }
  revision 2016-10-24 {
    description
      "Initial revision";
    reference "0.1.0";
  }

  grouping ncs_template_port-breakout-config {
    description
      "Configuration data for the port breakout mode";
    leaf num-channels {
      type string;
      description
        "Sets the number of channels to 'breakout' on a port
         capable of channelization";
    }
    leaf channel-speed {
      type string;
      description
        "Sets the channel speed on each channel -- the
         supported values are defined by the
         ETHERNET_SPEED identity";
    }
  }

  grouping ncs_template_port-breakout-state {
    description
      "Operational state data for the port breakout mode ";
  }

  grouping ncs_template_port-breakout-top {
    description
      "Top-level grouping for port breakout data";
    container breakout-mode {
      description
        "Top-level container for port breakout data";
      container config {
        description
          "Configuration data for port breakout";
        uses ncs_template_port-breakout-config;
      }
      // NCS drop config false container state
    }
  }

  grouping ncs_rpc_notif_port-breakout-config {
    description
      "Configuration data for the port breakout mode";
    leaf num-channels {
      type uint8;
      description
        "Sets the number of channels to 'breakout' on a port
         capable of channelization";
    }
    leaf channel-speed {
      type identityref {
        base oc-eth:ETHERNET_SPEED;
      }
      description
        "Sets the channel speed on each channel -- the
         supported values are defined by the
         ETHERNET_SPEED identity";
    }
  }

  grouping ncs_rpc_notif_port-breakout-state {
    description
      "Operational state data for the port breakout mode ";
  }

  grouping ncs_rpc_notif_port-breakout-top {
    description
      "Top-level grouping for port breakout data";
    container breakout-mode {
      description
        "Top-level container for port breakout data";
      container config {
        description
          "Configuration data for port breakout";
        uses ncs_rpc_notif_port-breakout-config;
      }
      container state {
        config false;
        description
          "Operational state data for port breakout";
        uses ncs_rpc_notif_port-breakout-config;
        uses ncs_rpc_notif_port-breakout-state;
      }
    }
  }

  grouping live_ncs_port-breakout-config {
    description
      "Configuration data for the port breakout mode";
    leaf num-channels {
      type uint8;
      description
        "Sets the number of channels to 'breakout' on a port
         capable of channelization";
    }
    leaf channel-speed {
      type identityref {
        base oc-eth:ETHERNET_SPEED;
      }
      description
        "Sets the channel speed on each channel -- the
         supported values are defined by the
         ETHERNET_SPEED identity";
    }
  }

  grouping live_ncs_port-breakout-state {
    description
      "Operational state data for the port breakout mode ";
  }

  grouping live_ncs_port-breakout-top {
    description
      "Top-level grouping for port breakout data";
    container breakout-mode {
      description
        "Top-level container for port breakout data";
      container config {
        description
          "Configuration data for port breakout";
        uses live_ncs_port-breakout-config;
      }
      container state {
        description
          "Operational state data for port breakout";
        uses live_ncs_port-breakout-config;
        uses live_ncs_port-breakout-state;
      }
    }
  }

  grouping port-breakout-config {
    description
      "Configuration data for the port breakout mode";
    leaf num-channels {
      type uint8;
      description
        "Sets the number of channels to 'breakout' on a port
         capable of channelization";
    }
    leaf channel-speed {
      type identityref {
        base oc-eth:ETHERNET_SPEED;
      }
      description
        "Sets the channel speed on each channel -- the
         supported values are defined by the
         ETHERNET_SPEED identity";
    }
  }

  grouping port-breakout-state {
    description
      "Operational state data for the port breakout mode ";
  }

  grouping port-breakout-top {
    description
      "Top-level grouping for port breakout data";
    container breakout-mode {
      description
        "Top-level container for port breakout data";
      container config {
        description
          "Configuration data for port breakout";
        uses port-breakout-config;
      }
      // NCS drop config false container state
    }
  }

  augment "/ncs:devices/ncs:device/ncs:live-status/oc-if:interfaces/oc-if:interface/oc-if:state" {
    description
      "Adds a reference from the base interface to the corresponding
       port component in the device inventory.";
    leaf hardware-port {
      tailf:ncs-device-type "netconf";
      tailf:display-when "not(../../../../../ncs:module) or ../../../../../ncs:module[ncs:name='openconfig-platform-port'] or (../../../../../ncs:live-status-protocol[not(ncs:capability)]) or (../../../../../ncs:live-status-protocol/ncs:capability/ncs:module[.='openconfig-platform-port'])";
      type leafref {
        path "/ncs:devices/ncs:device/ncs:live-status/oc-platform:components/oc-platform:component/oc-platform:name" {
          tailf:xpath-root 3;
        }
      }
      description
        "For non-channelized interfaces, references the hardware port
         corresponding to the base interface.";
    }
  }
}
