module ciena-mpls {
  // Generated by yanger -t ncs
  tailf:mount-id "saos1051-nc-1.0:saos1051-nc-1.0";
  tailf:ncs-device-type "netconf";

  namespace "http://ciena.com/ns/yang/ciena-mpls";
  prefix mpls;

  import ciena-l3-types {
    prefix ciena-l3-types;
  }
  import ciena-vrf {
    prefix vrf;
  }
  import openconfig-interfaces {
    prefix oc-if;
  }
  import ietf-inet-types {
    prefix inet;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's specific LDP protocol

     Copyright (c) 2018  Ciena Corporation.  All rights
     reserved.

     All information contained herein is, and remains the
     property of Ciena Corporation. Dissemination of this
     information or reproduction of this material is strictly
     forbidden unless prior written permission is obtained
     from Ciena Corporation.";

  revision 2020-08-30 {
    description
      "Updated forwarding-table-count-group to support IPv6 FTNs.
       Adding next-hop-type for ilm runtime entry to distinguish primary/backup
       Add FTN runtime flag value to distinguish state of forwarding entry.";
  }
  revision 2020-05-13 {
    description
      "Changed vrf-hash-table and vrf-table-count groupings to support IPv6.";
  }
  revision 2019-03-11 {
    description
      "Add MPLS label-allocation mode containers.
       Change ilm next hop address type to inet:ip-address.";
  }
  revision 2017-10-03 {
    description
      "Initial version of MPLS model.";
  }

  typedef ncs_template_label-mode-type {
    type string;
  }

  typedef ncs_rpc_notif_label-mode-type {
    type enumeration {
      enum "per-prefix" {
        description
          "Per prefix label. By default, it's per-prefix";
      }
      enum "per-vrf" {
        description
          "Per VRF label for entire VRF";
      }
    }
  }

  typedef live_ncs_label-mode-type {
    type enumeration {
      enum "per-prefix" {
        description
          "Per prefix label. By default, it's per-prefix";
      }
      enum "per-vrf" {
        description
          "Per VRF label for entire VRF";
      }
    }
  }

  typedef label-mode-type {
    type enumeration {
      enum "per-prefix" {
        description
          "Per prefix label. By default, it's per-prefix";
      }
      enum "per-vrf" {
        description
          "Per VRF label for entire VRF";
      }
    }
  }

  grouping ncs_template_vrf-hash-table-grouping {
    description
      "Vrf hash table grouping.";
    list vrf-hash-table {
      // NCS patched for predictable order
      ordered-by user;
      key "vrf-name";
      description
        "Vrf table list.";
      leaf vrf-name {
        type string;
        description
          "MPLS vrf name.";
      }
      list vrf-afi-table {
        // NCS patched for predictable order
        ordered-by user;
        key "afi";
        description
          "vrf afi table list.";
        leaf afi {
          type ciena-l3-types:ncs_template_mpls-afi-type;
          description
            "Mpls vrf Ipv4/Ipv6 Address family";
        }
        list mpls-vrf {
          // NCS patched for predictable order
          ordered-by user;
          key "fec-address";
          description
            "MPLS vrf list";
          leaf fec-address {
            type string;
            description
              "MPLS vrf fec address";
          }
          leaf index {
            type string;
            description
              "MPLS vrf index";
          }
          uses ncs_template_ftn-entry-runtime-info-grouping;
          uses ncs_template_runtime-ftn-grouping;
          leaf tunnel-id {
            type string;
            description
              "Tunnel id.";
          }
        }
      }
    }
  }

  grouping ncs_template_ftn-runtime-entry-grouping {
    description
      "FTN runtime entry grouping.";
    list ftn-entry-runtime {
      // NCS patched for predictable order
      ordered-by user;
      key "fec-address";
      description
        "FTN runtime entry list.";
      leaf fec-address {
        type string;
        description
          "FTN Fec address.";
      }
      list ftn-index {
        // NCS patched for predictable order
        ordered-by user;
        key "ftn-index";
        description
          "FTN index list.";
        leaf ftn-index {
          type string;
          description
            "FTN index.";
        }
        uses ncs_template_ftn-entry-runtime-info-grouping;
        uses ncs_template_runtime-ftn-grouping;
      }
    }
    list backup-entry {
      // NCS patched for predictable order
      ordered-by user;
      key "fec-address";
      description
        "List of ftn runtime backup entries.";
      leaf fec-address {
        type string;
        description
          "Ftn Fec address.";
      }
      list entry-data {
        // NCS patched for predictable order
        ordered-by user;
        key "index";
        description
          "FTN backup entry data.";
        leaf index {
          type string;
          description
            "Ftn index.";
        }
        uses ncs_template_ftn-entry-runtime-info-grouping;
      }
    }
  }

  grouping ncs_template_ilm-runtime-entry-grouping {
    description
      "Ilm runtime entry grouping.";
    list ilm-runtime-entry {
      // NCS patched for predictable order
      ordered-by user;
      key "incoming-label";
      description
        "Ilm runtime entry list.";
      leaf incoming-label {
        type string;
        description
          "Incoming label entry in ilm table.";
      }
      list incoming-interface-entry {
        // NCS patched for predictable order
        ordered-by user;
        key "name";
        description
          "Incoming interface entry list";
        leaf name {
          type string;
          description
            "Incoming interface name.";
        }
        list ilm-index {
          // NCS patched for predictable order
          ordered-by user;
          key "index";
          description
            "ilm index list";
          leaf index {
            type string;
            description
              "Ilm index.";
          }
          leaf owner {
            type string;
            description
              "Ownership of the management plane.";
          }
          leaf lsp-type {
            type string;
            description
              "Ilm lsp type.";
          }
          leaf row-status {
            type ciena-l3-types:ncs_template_mpls-row-status;
            description
              "Status of ilm runtime entry such as active,not in services,not ready.";
          }
          leaf flag {
            type string;
            description
              "Ilm flag value.";
          }
          leaf opcode {
            type ciena-l3-types:ncs_template_mpls-opcode;
            description
              "Ilm opcode value such as swap,pop and push.";
          }
          leaf fec-address {
            type string;
            description
              "Ilm fec address.";
          }
          list cross-connect-entry {
            // NCS patched for predictable order
            ordered-by user;
            key "index";
            description
              "Cross connect entry list.";
            leaf index {
              type string;
              description
                "Table index for the cross-connect.";
            }
            container nhlfe-entry {
              description
                "Container with Next hop label forwarding entry .";
              leaf outgoing-label {
                type string;
                description
                  " MPLS outgoing label value.";
              }
              leaf ilm-next-hop-ip-address {
                type string;
                description
                  "IP address of the next hop.";
              }
              leaf outgoing-interface-name {
                type string;
                description
                  "Outgoing interface name.";
              }
              uses ncs_template_runtime-nhlfe-entry;
            }
            leaf next-hop-type {
              type ciena-l3-types:ncs_template_mpls-next-hop-type;
              description
                "Indicates whether next-hop is primary or backup.";
            }
            uses ncs_template_runtime-xc-entry-grouping;
          }
        }
      }
    }
  }

  grouping ncs_template_runtime-nhlfe-entry {
    description
      "Runtime next hop label forwarding entry grouping.";
    leaf index {
      type string;
      description
        "Next hop label forwarding entry index.";
    }
    leaf cross-connect-index {
      type string;
      description
        "Cross connect index.";
    }
    leaf owner {
      type string;
      description
        "Creator of the cross connect, typically a protocol such as BGP,LDP... .";
    }
    leaf recursive-next-hop-address {
      type string;
      description
        "Recursive next hop address .";
    }
    leaf tx-bytes {
      type string;
      description
        "The number of trasmited bytes.";
    }
    leaf tx-pkts {
      type string;
      description
        "The number of transmited packets.";
    }
    leaf error-pkts {
      type string;
      description
        "The number of error packets.";
    }
    leaf discard-pkts {
      type string;
      description
        "The number of discarded packets count.";
    }
  }

  grouping ncs_template_runtime-xc-entry-grouping {
    description
      "Run time cross connect entry grouping.";
    leaf nhlfe-index {
      type string;
      description
        "Next hop label forwarding Entry index.";
    }
    leaf owner {
      type string;
      description
        "Creator of the cross connect, typically a protocol such as BGP,LDP etc.";
    }
    leaf label-stack {
      type string;
      description
        "Contains label stack for backup path.";
    }
  }

  grouping ncs_template_ftn-entry-runtime-info-grouping {
    description
      "FTN runtime entry information grouping.";
    list cross-connect-entry {
      // NCS patched for predictable order
      ordered-by user;
      key "index";
      description
        "Cross connect entry list.";
      leaf index {
        type string;
        description
          "Cross connect index.";
      }
      leaf incoming-label {
        type string;
        description
          "Incoming label value.";
      }
      leaf opcode {
        type string;
        description
          "Contains cross connect opcode.";
      }
      leaf admin-state {
        type string;
        description
          "The admin state of the backup xc-entry";
      }
      leaf oper-state {
        type string;
        description
          "The operational state of the backup xc-entry";
      }
      container nhlfe-entry {
        description
          "Next hop label forwarding Entry";
        leaf outgoing-label {
          type string;
          description
            "Outgoing label value.";
        }
        leaf next-hop-ip-address {
          type string;
          description
            "IP address of the next hop.";
        }
        leaf outgoing-interface-name {
          type string;
          description
            "Outgoing interface name.";
        }
        uses ncs_template_runtime-nhlfe-entry;
      }
      uses ncs_template_runtime-xc-entry-grouping;
    }
  }

  grouping ncs_template_runtime-ftn-grouping {
    description
      "Runtime FTN attributes.";
    leaf row-status {
      type ciena-l3-types:ncs_template_mpls-row-status;
      description
        "Status for FTN runtime entry such as active,not in services,not ready etc.";
    }
    leaf owner {
      type string;
      description
        "Creator of this segment, typically a protocol such as LDP,BGP,RSVP etc.";
    }
    leaf action-type {
      type string;
      description
        "Runtime FTN action type such as Redirect to tunnel.";
    }
    leaf flag {
      type string;
      description
        "Runtime FTN flag value.";
    }
  }

  grouping ncs_template_mpls-all-if-count-grouping {
    description
      "MPLS all interfaces count grouping.";
    container interfaces {
      description
        "MPLS all if count container.";
      leaf total-count {
        type string;
        description
          "The total number of interfaces.";
      }
      list interface {
        // NCS patched for predictable order
        ordered-by user;
        key "name";
        description
          "MPLS interface count list";
        leaf name {
          type string;
          description
            "MPLS nterface name.";
        }
        leaf total-ftn-count {
          type string;
          description
            "The total number of FTN.";
        }
        leaf total-ilm-count {
          type string;
          description
            "The Total number of ilm.";
        }
      }
    }
  }

  grouping ncs_template_mpls-grouping {
    description
      "MPLS grouping.";
    // NCS drop config false container 'mpls-state'
  }

  grouping ncs_template_vrf-table-count-grouping {
    description
      "Vrf table count grouping.";
    container vrf-table {
      description
        "vrf table container";
      leaf vrf-ipv4-count {
        type string;
        description
          "The number of Ipv4 vrf.";
      }
      leaf vrf-ipv4-install-count {
        type string;
        description
          "The number of Ipv4 vrf install.";
      }
      leaf vrf-ipv4-up-count {
        type string;
        description
          "The number of Ipv4 vrf up.";
      }
      leaf vrf-ipv6-count {
        type string;
        description
          "The number of IPv6 VRFs.";
      }
      leaf vrf-ipv6-install-count {
        type string;
        description
          "The number of IPv6 VRF install.";
      }
      leaf vrf-ipv6-up-count {
        type string;
        description
          "The number of IPv6 VRF up.";
      }
    }
  }

  grouping ncs_template_ilm-table-count-grouping {
    description
      "Ilm table count grouping.";
    container ilm-table {
      description
        "ilm table count container.";
      leaf count {
        type string;
        description
          "The number of Ilm Label.";
      }
      leaf install-count {
        type string;
        description
          "The number of Label install.";
      }
      leaf up-count {
        type string;
        description
          "The number of Label up.";
      }
      leaf swap-count {
        type string;
        description
          "The number of Label swap.";
      }
      leaf swap-install-count {
        type string;
        description
          "The number of Label swap install.";
      }
      leaf swap-up-count {
        type string;
        description
          "The number of Label swap up.";
      }
      leaf pop-count {
        type string;
        description
          "The number of Label pop.";
      }
      leaf pop-install-count {
        type string;
        description
          "The number of Label pop install.";
      }
      leaf pop-up-count {
        type string;
        description
          "The number of Label pop up. ";
      }
    }
  }

  grouping ncs_template_forwarding-table-count-grouping {
    description
      "Forwarding table count grouping.";
    container forwarding-table {
      description
        "Forwarding table count container";
      leaf total-ftn-count {
        type string;
        description
          "The total number of FTN.";
      }
      leaf ftn-install-count {
        type string;
        description
          "The number of FTN install.";
      }
      leaf ftn-up-count {
        type string;
        description
          "The number of FTN up.";
      }
      leaf total-primary-ftn-count {
        type string;
        description
          "The total number of primary FTN.";
      }
      leaf primary-ftn-up-count {
        type string;
        description
          "The number of primary FTN up.";
      }
      leaf primary-ftn-install-count {
        type string;
        description
          "The number of Primary FTN install.";
      }
      leaf total-secondary-ftn-count {
        type string;
        description
          "The total number of secondary FTN.";
      }
      leaf secondary-ftn-install-count {
        type string;
        description
          "The number secondary FTN install.";
      }
      leaf secondary-ftn-up-count {
        type string;
        description
          "The number of secondary FTN up.";
      }
      leaf ipv6-total-ftn-count {
        type string;
        description
          "The total number of IPv6 FTN.";
      }
      leaf ipv6-ftn-up-count {
        type string;
        description
          "The number of IPv6 FTN up.";
      }
      leaf ipv6-total-primary-ftn-count {
        type string;
        description
          "The total number of primary IPv6 FTN.";
      }
      leaf ipv6-primary-ftn-up-count {
        type string;
        description
          "The number of primary IPv6  FTN up.";
      }
      leaf ipv6-total-secondary-ftn-count {
        type string;
        description
          "The total number of secondary IPv6 FTN.";
      }
      leaf ipv6-secondary-ftn-up-count {
        type string;
        description
          "The number of secondary IPv6 FTN up.";
      }
    }
  }

  grouping ncs_template_rib-ldp-count-grouping {
    description
      "Rib ldp count grouping.";
    container rib-ldp {
      description
        "rib ldp container.";
      leaf count {
        type string;
        description
          "Ldp rib count.";
      }
      list rib-ldp {
        // NCS patched for predictable order
        ordered-by user;
        key "index";
        description
          "rib ldp list";
        leaf index {
          type string;
          description
            "Ldp rib index.";
        }
        leaf session-address {
          type string;
          description
            "Session ipv4 address .";
        }
        leaf rib-type {
          type string;
          description
            "Rib type .";
        }
        leaf ftn-count {
          type string;
          description
            "The number of FTN.";
        }
        leaf ilm-count {
          type string;
          description
            "The number of ilm.";
        }
        leaf dependent-ilm-count {
          type string;
          description
            "The number of dependent ilm's.";
        }
      }
    }
  }

  grouping ncs_template_tunnel-stats-grouping {
    description
      "Tunnel stats grouping.";
    container tunnel-statistics {
      description
        "MPLS statistics container.";
      list entry {
        // NCS patched for predictable order
        ordered-by user;
        key "fec-address role owner";
        description
          "MPLS stats entry list";
        leaf fec-address {
          type string;
          description
            "MPLS stats FEC address.";
        }
        leaf role {
          type ciena-l3-types:ncs_template_mpls-stats-role;
          description
            "MPLS stats role.";
        }
        leaf owner {
          type ciena-l3-types:ncs_template_mpls-stats-owner;
          description
            "Protocol Owner Name.";
        }
        leaf tx-bytes {
          type string;
          description
            "Tx bytes.";
        }
        leaf tx-packets {
          type string;
          description
            "Tx packets.";
        }
      }
    }
  }

  grouping ncs_template_mpls-label-blocks-grouping {
    description
      "Mpls Label Blocks State grouping.";
    container label-blocks {
      description
        "MPLS label blocks container.";
      list label-block {
        // NCS patched for predictable order
        ordered-by user;
        key "index";
        description
          "MPLS label-block list";
        leaf index {
          type string;
          description
            "A user-specified identifier utilised to uniquely
             reference an MPLS label block.";
        }
        leaf start-label {
          type string;
          description
            "Label-block start.";
        }
        leaf end-label {
          type string;
          description
            "Label-block end.";
        }
        list protocol {
          // NCS patched for predictable order
          ordered-by user;
          key "name";
          description
            "List of MPLS protocols.";
          leaf name {
            type string;
            description
              "MPLS protocols name.";
          }
          leaf start-label {
            type string;
            description
              "Protocol label-block start.";
          }
          leaf end-label {
            type string;
            description
              "Protocol label-block end.";
          }
        }
      }
    }
  }

  grouping ncs_template_mpls-interface-grouping {
    description
      "MPLS interface grouping.";
    container interfaces {
      description
        "MPLS interfaces Container.";
      list interface {
        // NCS patched for predictable order
        ordered-by user;
        key "name";
        description
          "MPLS interface list.";
        leaf name {
          type string;
          description
            "MPLS interface name.";
        }
        leaf label-switching {
          type string;
          // NCS drop default statement
          description
            "This enables ldp on all interfaces and sets the default
             label space value which is 0 by default.";
        }
      }
    }
  }

  grouping ncs_template_address-family-grouping {
    list address-family {
      // NCS patched for predictable order
      ordered-by user;
      key "af-type";
      description
        "MPLS Label allocation for address families";
      leaf af-type {
        type ciena-l3-types:ncs_template_vrf-afi-type;
        description
          "MPLS Label allocation for given address family";
      }
      leaf mode {
        type ncs_template_label-mode-type;
        // NCS drop default statement
        description
          "MPLS Label allocation mode.";
      }
    }
  }

  grouping ncs_template_label-grouping {
    description
      "Grouping for label properties";
    container label-management {
      description
        "Label peoperties management container";
      container allocation-mode {
        description
          "MPLS Label allocation mode";
        container all-vrfs {
          description
            "MPLS Label allocation mode for all VRFs";
          uses ncs_template_address-family-grouping;
        }
        list vrf {
          // NCS patched for predictable order
          ordered-by user;
          key "name";
          leaf name {
            type string;
            description
              "VPN Routing/Forwarding instance name";
          }
          uses ncs_template_address-family-grouping;
        }
      }
      uses ncs_template_mpls-label-blocks;
    }
  }

  grouping ncs_template_mpls-tunnel-statistics-grouping {
    description
      "MPLS tunnel stats grouping.";
    container tunnel-statistics {
      description
        "MPLS tunnel statistics container.";
      list entry {
        // NCS patched for predictable order
        ordered-by user;
        key "fec-address role owner";
        description
          "MPLS stats entry list.";
        leaf fec-address {
          type string;
          description
            "MPLS stats fec Address.";
        }
        leaf role {
          type ciena-l3-types:ncs_template_mpls-stats-role;
          description
            "MPLS role can be ingress/egress/transit.";
        }
        leaf owner {
          type ciena-l3-types:ncs_template_mpls-stats-owner;
          description
            "Protocol Owner Name.";
        }
      }
    }
  }

  grouping ncs_template_mpls-label-blocks {
    description
      "Label-block allocation grouping.";
    container label-blocks {
      description
        "MPLS label blocks container.";
      list label-block {
        // NCS patched for predictable order
        ordered-by user;
        key "index";
        description
          "List of MPLS protocol label range.";
        leaf index {
          type string;
          description
            "A user-specified identifier utilised to uniquely
             reference an MPLS label block.";
        }
        list protocol {
          // NCS patched for predictable order
          ordered-by user;
          key "name";
          description
            "List of MPLS protocols.";
          leaf name {
            type ciena-l3-types:ncs_template_mpls-protocols;
            description
              "MPLS protocols name.";
          }
          leaf start-label {
            // NCS drop mandatory statement
            type string;
            description
              "Protocol label-block start.";
          }
          leaf end-label {
            // NCS drop mandatory statement
            type string;
            description
              "Protocol label-block end.";
          }
        }
      }
    }
  }

  grouping ncs_rpc_notif_vrf-hash-table-grouping {
    description
      "Vrf hash table grouping.";
    list vrf-hash-table {
      key "vrf-name";
      description
        "Vrf table list.";
      leaf vrf-name {
        type string;
        description
          "MPLS vrf name.";
      }
      list vrf-afi-table {
        key "afi";
        description
          "vrf afi table list.";
        leaf afi {
          type ciena-l3-types:ncs_rpc_notif_mpls-afi-type;
          description
            "Mpls vrf Ipv4/Ipv6 Address family";
        }
        list mpls-vrf {
          key "fec-address";
          description
            "MPLS vrf list";
          leaf fec-address {
            type inet:ip-prefix;
            description
              "MPLS vrf fec address";
          }
          leaf index {
            type uint32;
            description
              "MPLS vrf index";
          }
          uses ncs_rpc_notif_ftn-entry-runtime-info-grouping;
          uses ncs_rpc_notif_runtime-ftn-grouping;
          leaf tunnel-id {
            type uint32;
            description
              "Tunnel id.";
          }
        }
      }
    }
  }

  grouping ncs_rpc_notif_ftn-runtime-entry-grouping {
    description
      "FTN runtime entry grouping.";
    list ftn-entry-runtime {
      key "fec-address";
      description
        "FTN runtime entry list.";
      leaf fec-address {
        type inet:ip-prefix;
        description
          "FTN Fec address.";
      }
      list ftn-index {
        key "ftn-index";
        description
          "FTN index list.";
        leaf ftn-index {
          type uint32;
          description
            "FTN index.";
        }
        uses ncs_rpc_notif_ftn-entry-runtime-info-grouping;
        uses ncs_rpc_notif_runtime-ftn-grouping;
      }
    }
    list backup-entry {
      key "fec-address";
      description
        "List of ftn runtime backup entries.";
      leaf fec-address {
        type inet:ip-prefix;
        description
          "Ftn Fec address.";
      }
      list entry-data {
        key "index";
        description
          "FTN backup entry data.";
        leaf index {
          type uint32;
          description
            "Ftn index.";
        }
        uses ncs_rpc_notif_ftn-entry-runtime-info-grouping;
      }
    }
  }

  grouping ncs_rpc_notif_ilm-runtime-entry-grouping {
    description
      "Ilm runtime entry grouping.";
    list ilm-runtime-entry {
      key "incoming-label";
      description
        "Ilm runtime entry list.";
      leaf incoming-label {
        type uint32;
        description
          "Incoming label entry in ilm table.";
      }
      list incoming-interface-entry {
        key "name";
        description
          "Incoming interface entry list";
        leaf name {
          type string;
          description
            "Incoming interface name.";
        }
        list ilm-index {
          key "index";
          description
            "ilm index list";
          leaf index {
            type uint32;
            description
              "Ilm index.";
          }
          leaf owner {
            type string;
            description
              "Ownership of the management plane.";
          }
          leaf lsp-type {
            type string;
            description
              "Ilm lsp type.";
          }
          leaf row-status {
            type ciena-l3-types:ncs_rpc_notif_mpls-row-status;
            description
              "Status of ilm runtime entry such as active,not in services,not ready.";
          }
          leaf flag {
            type string;
            description
              "Ilm flag value.";
          }
          leaf opcode {
            type ciena-l3-types:ncs_rpc_notif_mpls-opcode;
            description
              "Ilm opcode value such as swap,pop and push.";
          }
          leaf fec-address {
            type inet:ip-prefix;
            description
              "Ilm fec address.";
          }
          list cross-connect-entry {
            key "index";
            description
              "Cross connect entry list.";
            leaf index {
              type uint32;
              description
                "Table index for the cross-connect.";
            }
            container nhlfe-entry {
              description
                "Container with Next hop label forwarding entry .";
              leaf outgoing-label {
                type uint32;
                description
                  " MPLS outgoing label value.";
              }
              leaf ilm-next-hop-ip-address {
                type inet:ip-address;
                description
                  "IP address of the next hop.";
              }
              leaf outgoing-interface-name {
                type string;
                description
                  "Outgoing interface name.";
              }
              uses ncs_rpc_notif_runtime-nhlfe-entry;
            }
            leaf next-hop-type {
              type ciena-l3-types:ncs_rpc_notif_mpls-next-hop-type;
              description
                "Indicates whether next-hop is primary or backup.";
            }
            uses ncs_rpc_notif_runtime-xc-entry-grouping;
          }
        }
      }
    }
  }

  grouping ncs_rpc_notif_runtime-nhlfe-entry {
    description
      "Runtime next hop label forwarding entry grouping.";
    leaf index {
      type uint32;
      description
        "Next hop label forwarding entry index.";
    }
    leaf cross-connect-index {
      type uint32;
      description
        "Cross connect index.";
    }
    leaf owner {
      type string;
      description
        "Creator of the cross connect, typically a protocol such as BGP,LDP... .";
    }
    leaf recursive-next-hop-address {
      type inet:ip-address;
      description
        "Recursive next hop address .";
    }
    leaf tx-bytes {
      type uint32;
      description
        "The number of trasmited bytes.";
    }
    leaf tx-pkts {
      type uint32;
      description
        "The number of transmited packets.";
    }
    leaf error-pkts {
      type uint32;
      description
        "The number of error packets.";
    }
    leaf discard-pkts {
      type uint32;
      description
        "The number of discarded packets count.";
    }
  }

  grouping ncs_rpc_notif_runtime-xc-entry-grouping {
    description
      "Run time cross connect entry grouping.";
    leaf nhlfe-index {
      type uint32;
      description
        "Next hop label forwarding Entry index.";
    }
    leaf owner {
      type string;
      description
        "Creator of the cross connect, typically a protocol such as BGP,LDP etc.";
    }
    leaf label-stack {
      type string;
      description
        "Contains label stack for backup path.";
    }
  }

  grouping ncs_rpc_notif_ftn-entry-runtime-info-grouping {
    description
      "FTN runtime entry information grouping.";
    list cross-connect-entry {
      key "index";
      description
        "Cross connect entry list.";
      leaf index {
        type uint32;
        description
          "Cross connect index.";
      }
      leaf incoming-label {
        type uint32;
        description
          "Incoming label value.";
      }
      leaf opcode {
        type string;
        description
          "Contains cross connect opcode.";
      }
      leaf admin-state {
        type string;
        description
          "The admin state of the backup xc-entry";
      }
      leaf oper-state {
        type string;
        description
          "The operational state of the backup xc-entry";
      }
      container nhlfe-entry {
        description
          "Next hop label forwarding Entry";
        leaf outgoing-label {
          type uint32;
          description
            "Outgoing label value.";
        }
        leaf next-hop-ip-address {
          type inet:ip-address;
          description
            "IP address of the next hop.";
        }
        leaf outgoing-interface-name {
          type string;
          description
            "Outgoing interface name.";
        }
        uses ncs_rpc_notif_runtime-nhlfe-entry;
      }
      uses ncs_rpc_notif_runtime-xc-entry-grouping;
    }
  }

  grouping ncs_rpc_notif_runtime-ftn-grouping {
    description
      "Runtime FTN attributes.";
    leaf row-status {
      type ciena-l3-types:ncs_rpc_notif_mpls-row-status;
      description
        "Status for FTN runtime entry such as active,not in services,not ready etc.";
    }
    leaf owner {
      type string;
      description
        "Creator of this segment, typically a protocol such as LDP,BGP,RSVP etc.";
    }
    leaf action-type {
      type string;
      description
        "Runtime FTN action type such as Redirect to tunnel.";
    }
    leaf flag {
      type string;
      description
        "Runtime FTN flag value.";
    }
  }

  grouping ncs_rpc_notif_mpls-all-if-count-grouping {
    description
      "MPLS all interfaces count grouping.";
    container interfaces {
      description
        "MPLS all if count container.";
      leaf total-count {
        type uint32;
        description
          "The total number of interfaces.";
      }
      list interface {
        key "name";
        description
          "MPLS interface count list";
        leaf name {
          type string;
          description
            "MPLS nterface name.";
        }
        leaf total-ftn-count {
          type uint32;
          description
            "The total number of FTN.";
        }
        leaf total-ilm-count {
          type uint32;
          description
            "The Total number of ilm.";
        }
      }
    }
  }

  grouping ncs_rpc_notif_mpls-grouping {
    description
      "MPLS grouping.";
    container mpls-state {
      config false;
      description
        "MPLS state container.";
      uses ncs_rpc_notif_mpls-all-if-count-grouping;
      uses ncs_rpc_notif_vrf-hash-table-grouping;
      uses ncs_rpc_notif_vrf-table-count-grouping;
      uses ncs_rpc_notif_ilm-runtime-entry-grouping;
      uses ncs_rpc_notif_ilm-table-count-grouping;
      uses ncs_rpc_notif_ftn-runtime-entry-grouping;
      uses ncs_rpc_notif_forwarding-table-count-grouping;
      uses ncs_rpc_notif_rib-ldp-count-grouping;
      uses ncs_rpc_notif_tunnel-stats-grouping;
      uses ncs_rpc_notif_mpls-label-blocks-grouping;
    }
  }

  grouping ncs_rpc_notif_vrf-table-count-grouping {
    description
      "Vrf table count grouping.";
    container vrf-table {
      description
        "vrf table container";
      leaf vrf-ipv4-count {
        type uint32;
        description
          "The number of Ipv4 vrf.";
      }
      leaf vrf-ipv4-install-count {
        type uint32;
        description
          "The number of Ipv4 vrf install.";
      }
      leaf vrf-ipv4-up-count {
        type uint32;
        description
          "The number of Ipv4 vrf up.";
      }
      leaf vrf-ipv6-count {
        type uint32;
        description
          "The number of IPv6 VRFs.";
      }
      leaf vrf-ipv6-install-count {
        type uint32;
        description
          "The number of IPv6 VRF install.";
      }
      leaf vrf-ipv6-up-count {
        type uint32;
        description
          "The number of IPv6 VRF up.";
      }
    }
  }

  grouping ncs_rpc_notif_ilm-table-count-grouping {
    description
      "Ilm table count grouping.";
    container ilm-table {
      description
        "ilm table count container.";
      leaf count {
        type uint32;
        description
          "The number of Ilm Label.";
      }
      leaf install-count {
        type uint32;
        description
          "The number of Label install.";
      }
      leaf up-count {
        type uint32;
        description
          "The number of Label up.";
      }
      leaf swap-count {
        type uint32;
        description
          "The number of Label swap.";
      }
      leaf swap-install-count {
        type uint32;
        description
          "The number of Label swap install.";
      }
      leaf swap-up-count {
        type uint32;
        description
          "The number of Label swap up.";
      }
      leaf pop-count {
        type uint32;
        description
          "The number of Label pop.";
      }
      leaf pop-install-count {
        type uint32;
        description
          "The number of Label pop install.";
      }
      leaf pop-up-count {
        type uint32;
        description
          "The number of Label pop up. ";
      }
    }
  }

  grouping ncs_rpc_notif_forwarding-table-count-grouping {
    description
      "Forwarding table count grouping.";
    container forwarding-table {
      description
        "Forwarding table count container";
      leaf total-ftn-count {
        type uint32;
        description
          "The total number of FTN.";
      }
      leaf ftn-install-count {
        type uint32;
        description
          "The number of FTN install.";
      }
      leaf ftn-up-count {
        type uint32;
        description
          "The number of FTN up.";
      }
      leaf total-primary-ftn-count {
        type uint32;
        description
          "The total number of primary FTN.";
      }
      leaf primary-ftn-up-count {
        type uint32;
        description
          "The number of primary FTN up.";
      }
      leaf primary-ftn-install-count {
        type uint32;
        description
          "The number of Primary FTN install.";
      }
      leaf total-secondary-ftn-count {
        type uint32;
        description
          "The total number of secondary FTN.";
      }
      leaf secondary-ftn-install-count {
        type uint32;
        description
          "The number secondary FTN install.";
      }
      leaf secondary-ftn-up-count {
        type uint32;
        description
          "The number of secondary FTN up.";
      }
      leaf ipv6-total-ftn-count {
        type uint32;
        description
          "The total number of IPv6 FTN.";
      }
      leaf ipv6-ftn-up-count {
        type uint32;
        description
          "The number of IPv6 FTN up.";
      }
      leaf ipv6-total-primary-ftn-count {
        type uint32;
        description
          "The total number of primary IPv6 FTN.";
      }
      leaf ipv6-primary-ftn-up-count {
        type uint32;
        description
          "The number of primary IPv6  FTN up.";
      }
      leaf ipv6-total-secondary-ftn-count {
        type uint32;
        description
          "The total number of secondary IPv6 FTN.";
      }
      leaf ipv6-secondary-ftn-up-count {
        type uint32;
        description
          "The number of secondary IPv6 FTN up.";
      }
    }
  }

  grouping ncs_rpc_notif_rib-ldp-count-grouping {
    description
      "Rib ldp count grouping.";
    container rib-ldp {
      description
        "rib ldp container.";
      leaf count {
        type uint32;
        description
          "Ldp rib count.";
      }
      list rib-ldp {
        key "index";
        description
          "rib ldp list";
        leaf index {
          type uint32;
          description
            "Ldp rib index.";
        }
        leaf session-address {
          type inet:ipv4-address;
          description
            "Session ipv4 address .";
        }
        leaf rib-type {
          type string;
          description
            "Rib type .";
        }
        leaf ftn-count {
          type uint32;
          description
            "The number of FTN.";
        }
        leaf ilm-count {
          type uint32;
          description
            "The number of ilm.";
        }
        leaf dependent-ilm-count {
          type uint32;
          description
            "The number of dependent ilm's.";
        }
      }
    }
  }

  grouping ncs_rpc_notif_tunnel-stats-grouping {
    description
      "Tunnel stats grouping.";
    container tunnel-statistics {
      description
        "MPLS statistics container.";
      list entry {
        key "fec-address role owner";
        description
          "MPLS stats entry list";
        leaf fec-address {
          type inet:ip-prefix;
          description
            "MPLS stats FEC address.";
        }
        leaf role {
          type ciena-l3-types:ncs_rpc_notif_mpls-stats-role;
          description
            "MPLS stats role.";
        }
        leaf owner {
          type ciena-l3-types:ncs_rpc_notif_mpls-stats-owner;
          description
            "Protocol Owner Name.";
        }
        leaf tx-bytes {
          type yang:counter64;
          description
            "Tx bytes.";
        }
        leaf tx-packets {
          type yang:counter64;
          description
            "Tx packets.";
        }
      }
    }
  }

  grouping ncs_rpc_notif_mpls-label-blocks-grouping {
    description
      "Mpls Label Blocks State grouping.";
    container label-blocks {
      description
        "MPLS label blocks container.";
      list label-block {
        key "index";
        description
          "MPLS label-block list";
        leaf index {
          type uint16;
          description
            "A user-specified identifier utilised to uniquely
             reference an MPLS label block.";
        }
        leaf start-label {
          type uint32;
          description
            "Label-block start.";
        }
        leaf end-label {
          type uint32;
          description
            "Label-block end.";
        }
        list protocol {
          key "name";
          description
            "List of MPLS protocols.";
          leaf name {
            type string;
            description
              "MPLS protocols name.";
          }
          leaf start-label {
            type uint32;
            description
              "Protocol label-block start.";
          }
          leaf end-label {
            type uint32;
            description
              "Protocol label-block end.";
          }
        }
      }
    }
  }

  grouping ncs_rpc_notif_mpls-interface-grouping {
    description
      "MPLS interface grouping.";
    container interfaces {
      description
        "MPLS interfaces Container.";
      list interface {
        key "name";
        description
          "MPLS interface list.";
        leaf name {
          type string;
          description
            "MPLS interface name.";
        }
        leaf label-switching {
          type boolean;
          default "false";
          description
            "This enables ldp on all interfaces and sets the default
             label space value which is 0 by default.";
        }
      }
    }
  }

  grouping ncs_rpc_notif_address-family-grouping {
    list address-family {
      key "af-type";
      description
        "MPLS Label allocation for address families";
      leaf af-type {
        type ciena-l3-types:ncs_rpc_notif_vrf-afi-type;
        description
          "MPLS Label allocation for given address family";
      }
      leaf mode {
        type ncs_rpc_notif_label-mode-type;
        default "per-prefix";
        description
          "MPLS Label allocation mode.";
      }
    }
  }

  grouping ncs_rpc_notif_label-grouping {
    description
      "Grouping for label properties";
    container label-management {
      description
        "Label peoperties management container";
      container allocation-mode {
        description
          "MPLS Label allocation mode";
        container all-vrfs {
          description
            "MPLS Label allocation mode for all VRFs";
          uses ncs_rpc_notif_address-family-grouping;
        }
        list vrf {
          key "name";
          leaf name {
            type string;
            description
              "VPN Routing/Forwarding instance name";
          }
          uses ncs_rpc_notif_address-family-grouping;
        }
      }
      uses ncs_rpc_notif_mpls-label-blocks;
    }
  }

  grouping ncs_rpc_notif_mpls-tunnel-statistics-grouping {
    description
      "MPLS tunnel stats grouping.";
    container tunnel-statistics {
      description
        "MPLS tunnel statistics container.";
      list entry {
        key "fec-address role owner";
        description
          "MPLS stats entry list.";
        leaf fec-address {
          type inet:ip-prefix;
          description
            "MPLS stats fec Address.";
        }
        leaf role {
          type ciena-l3-types:ncs_rpc_notif_mpls-stats-role;
          description
            "MPLS role can be ingress/egress/transit.";
        }
        leaf owner {
          type ciena-l3-types:ncs_rpc_notif_mpls-stats-owner;
          description
            "Protocol Owner Name.";
        }
      }
    }
  }

  grouping ncs_rpc_notif_mpls-label-blocks {
    description
      "Label-block allocation grouping.";
    container label-blocks {
      description
        "MPLS label blocks container.";
      list label-block {
        key "index";
        description
          "List of MPLS protocol label range.";
        leaf index {
          type uint16 {
            range "0";
          }
          description
            "A user-specified identifier utilised to uniquely
             reference an MPLS label block.";
        }
        list protocol {
          key "name";
          description
            "List of MPLS protocols.";
          leaf name {
            type ciena-l3-types:ncs_rpc_notif_mpls-protocols;
            description
              "MPLS protocols name.";
          }
          leaf start-label {
            mandatory true;
            type uint32 {
              range "24321..1048575";
            }
            description
              "Protocol label-block start.";
          }
          leaf end-label {
            mandatory true;
            type uint32 {
              range "24321..1048575";
            }
            description
              "Protocol label-block end.";
          }
        }
      }
    }
  }

  grouping live_ncs_vrf-hash-table-grouping {
    description
      "Vrf hash table grouping.";
    list vrf-hash-table {
      key "vrf-name";
      description
        "Vrf table list.";
      leaf vrf-name {
        type string;
        description
          "MPLS vrf name.";
      }
      list vrf-afi-table {
        key "afi";
        description
          "vrf afi table list.";
        leaf afi {
          type ciena-l3-types:live_ncs_mpls-afi-type;
          description
            "Mpls vrf Ipv4/Ipv6 Address family";
        }
        list mpls-vrf {
          key "fec-address";
          description
            "MPLS vrf list";
          leaf fec-address {
            type inet:ip-prefix;
            description
              "MPLS vrf fec address";
          }
          leaf index {
            type uint32;
            description
              "MPLS vrf index";
          }
          uses live_ncs_ftn-entry-runtime-info-grouping;
          uses live_ncs_runtime-ftn-grouping;
          leaf tunnel-id {
            type uint32;
            description
              "Tunnel id.";
          }
        }
      }
    }
  }

  grouping live_ncs_ftn-runtime-entry-grouping {
    description
      "FTN runtime entry grouping.";
    list ftn-entry-runtime {
      key "fec-address";
      description
        "FTN runtime entry list.";
      leaf fec-address {
        type inet:ip-prefix;
        description
          "FTN Fec address.";
      }
      list ftn-index {
        key "ftn-index";
        description
          "FTN index list.";
        leaf ftn-index {
          type uint32;
          description
            "FTN index.";
        }
        uses live_ncs_ftn-entry-runtime-info-grouping;
        uses live_ncs_runtime-ftn-grouping;
      }
    }
    list backup-entry {
      key "fec-address";
      description
        "List of ftn runtime backup entries.";
      leaf fec-address {
        type inet:ip-prefix;
        description
          "Ftn Fec address.";
      }
      list entry-data {
        key "index";
        description
          "FTN backup entry data.";
        leaf index {
          type uint32;
          description
            "Ftn index.";
        }
        uses live_ncs_ftn-entry-runtime-info-grouping;
      }
    }
  }

  grouping live_ncs_ilm-runtime-entry-grouping {
    description
      "Ilm runtime entry grouping.";
    list ilm-runtime-entry {
      key "incoming-label";
      description
        "Ilm runtime entry list.";
      leaf incoming-label {
        type uint32;
        description
          "Incoming label entry in ilm table.";
      }
      list incoming-interface-entry {
        key "name";
        description
          "Incoming interface entry list";
        leaf name {
          type string;
          description
            "Incoming interface name.";
        }
        list ilm-index {
          key "index";
          description
            "ilm index list";
          leaf index {
            type uint32;
            description
              "Ilm index.";
          }
          leaf owner {
            type string;
            description
              "Ownership of the management plane.";
          }
          leaf lsp-type {
            type string;
            description
              "Ilm lsp type.";
          }
          leaf row-status {
            type ciena-l3-types:live_ncs_mpls-row-status;
            description
              "Status of ilm runtime entry such as active,not in services,not ready.";
          }
          leaf flag {
            type string;
            description
              "Ilm flag value.";
          }
          leaf opcode {
            type ciena-l3-types:live_ncs_mpls-opcode;
            description
              "Ilm opcode value such as swap,pop and push.";
          }
          leaf fec-address {
            type inet:ip-prefix;
            description
              "Ilm fec address.";
          }
          list cross-connect-entry {
            key "index";
            description
              "Cross connect entry list.";
            leaf index {
              type uint32;
              description
                "Table index for the cross-connect.";
            }
            container nhlfe-entry {
              description
                "Container with Next hop label forwarding entry .";
              leaf outgoing-label {
                type uint32;
                description
                  " MPLS outgoing label value.";
              }
              leaf ilm-next-hop-ip-address {
                type inet:ip-address;
                description
                  "IP address of the next hop.";
              }
              leaf outgoing-interface-name {
                type string;
                description
                  "Outgoing interface name.";
              }
              uses live_ncs_runtime-nhlfe-entry;
            }
            leaf next-hop-type {
              type ciena-l3-types:live_ncs_mpls-next-hop-type;
              description
                "Indicates whether next-hop is primary or backup.";
            }
            uses live_ncs_runtime-xc-entry-grouping;
          }
        }
      }
    }
  }

  grouping live_ncs_runtime-nhlfe-entry {
    description
      "Runtime next hop label forwarding entry grouping.";
    leaf index {
      type uint32;
      description
        "Next hop label forwarding entry index.";
    }
    leaf cross-connect-index {
      type uint32;
      description
        "Cross connect index.";
    }
    leaf owner {
      type string;
      description
        "Creator of the cross connect, typically a protocol such as BGP,LDP... .";
    }
    leaf recursive-next-hop-address {
      type inet:ip-address;
      description
        "Recursive next hop address .";
    }
    leaf tx-bytes {
      type uint32;
      description
        "The number of trasmited bytes.";
    }
    leaf tx-pkts {
      type uint32;
      description
        "The number of transmited packets.";
    }
    leaf error-pkts {
      type uint32;
      description
        "The number of error packets.";
    }
    leaf discard-pkts {
      type uint32;
      description
        "The number of discarded packets count.";
    }
  }

  grouping live_ncs_runtime-xc-entry-grouping {
    description
      "Run time cross connect entry grouping.";
    leaf nhlfe-index {
      type uint32;
      description
        "Next hop label forwarding Entry index.";
    }
    leaf owner {
      type string;
      description
        "Creator of the cross connect, typically a protocol such as BGP,LDP etc.";
    }
    leaf label-stack {
      type string;
      description
        "Contains label stack for backup path.";
    }
  }

  grouping live_ncs_ftn-entry-runtime-info-grouping {
    description
      "FTN runtime entry information grouping.";
    list cross-connect-entry {
      key "index";
      description
        "Cross connect entry list.";
      leaf index {
        type uint32;
        description
          "Cross connect index.";
      }
      leaf incoming-label {
        type uint32;
        description
          "Incoming label value.";
      }
      leaf opcode {
        type string;
        description
          "Contains cross connect opcode.";
      }
      leaf admin-state {
        type string;
        description
          "The admin state of the backup xc-entry";
      }
      leaf oper-state {
        type string;
        description
          "The operational state of the backup xc-entry";
      }
      container nhlfe-entry {
        description
          "Next hop label forwarding Entry";
        leaf outgoing-label {
          type uint32;
          description
            "Outgoing label value.";
        }
        leaf next-hop-ip-address {
          type inet:ip-address;
          description
            "IP address of the next hop.";
        }
        leaf outgoing-interface-name {
          type string;
          description
            "Outgoing interface name.";
        }
        uses live_ncs_runtime-nhlfe-entry;
      }
      uses live_ncs_runtime-xc-entry-grouping;
    }
  }

  grouping live_ncs_runtime-ftn-grouping {
    description
      "Runtime FTN attributes.";
    leaf row-status {
      type ciena-l3-types:live_ncs_mpls-row-status;
      description
        "Status for FTN runtime entry such as active,not in services,not ready etc.";
    }
    leaf owner {
      type string;
      description
        "Creator of this segment, typically a protocol such as LDP,BGP,RSVP etc.";
    }
    leaf action-type {
      type string;
      description
        "Runtime FTN action type such as Redirect to tunnel.";
    }
    leaf flag {
      type string;
      description
        "Runtime FTN flag value.";
    }
  }

  grouping live_ncs_mpls-all-if-count-grouping {
    description
      "MPLS all interfaces count grouping.";
    container interfaces {
      description
        "MPLS all if count container.";
      leaf total-count {
        type uint32;
        description
          "The total number of interfaces.";
      }
      list interface {
        key "name";
        description
          "MPLS interface count list";
        leaf name {
          type string;
          description
            "MPLS nterface name.";
        }
        leaf total-ftn-count {
          type uint32;
          description
            "The total number of FTN.";
        }
        leaf total-ilm-count {
          type uint32;
          description
            "The Total number of ilm.";
        }
      }
    }
  }

  grouping live_ncs_mpls-grouping {
    description
      "MPLS grouping.";
    container mpls-state {
      description
        "MPLS state container.";
      uses live_ncs_mpls-all-if-count-grouping;
      uses live_ncs_vrf-hash-table-grouping;
      uses live_ncs_vrf-table-count-grouping;
      uses live_ncs_ilm-runtime-entry-grouping;
      uses live_ncs_ilm-table-count-grouping;
      uses live_ncs_ftn-runtime-entry-grouping;
      uses live_ncs_forwarding-table-count-grouping;
      uses live_ncs_rib-ldp-count-grouping;
      uses live_ncs_tunnel-stats-grouping;
      uses live_ncs_mpls-label-blocks-grouping;
    }
  }

  grouping live_ncs_vrf-table-count-grouping {
    description
      "Vrf table count grouping.";
    container vrf-table {
      description
        "vrf table container";
      leaf vrf-ipv4-count {
        type uint32;
        description
          "The number of Ipv4 vrf.";
      }
      leaf vrf-ipv4-install-count {
        type uint32;
        description
          "The number of Ipv4 vrf install.";
      }
      leaf vrf-ipv4-up-count {
        type uint32;
        description
          "The number of Ipv4 vrf up.";
      }
      leaf vrf-ipv6-count {
        type uint32;
        description
          "The number of IPv6 VRFs.";
      }
      leaf vrf-ipv6-install-count {
        type uint32;
        description
          "The number of IPv6 VRF install.";
      }
      leaf vrf-ipv6-up-count {
        type uint32;
        description
          "The number of IPv6 VRF up.";
      }
    }
  }

  grouping live_ncs_ilm-table-count-grouping {
    description
      "Ilm table count grouping.";
    container ilm-table {
      description
        "ilm table count container.";
      leaf count {
        type uint32;
        description
          "The number of Ilm Label.";
      }
      leaf install-count {
        type uint32;
        description
          "The number of Label install.";
      }
      leaf up-count {
        type uint32;
        description
          "The number of Label up.";
      }
      leaf swap-count {
        type uint32;
        description
          "The number of Label swap.";
      }
      leaf swap-install-count {
        type uint32;
        description
          "The number of Label swap install.";
      }
      leaf swap-up-count {
        type uint32;
        description
          "The number of Label swap up.";
      }
      leaf pop-count {
        type uint32;
        description
          "The number of Label pop.";
      }
      leaf pop-install-count {
        type uint32;
        description
          "The number of Label pop install.";
      }
      leaf pop-up-count {
        type uint32;
        description
          "The number of Label pop up. ";
      }
    }
  }

  grouping live_ncs_forwarding-table-count-grouping {
    description
      "Forwarding table count grouping.";
    container forwarding-table {
      description
        "Forwarding table count container";
      leaf total-ftn-count {
        type uint32;
        description
          "The total number of FTN.";
      }
      leaf ftn-install-count {
        type uint32;
        description
          "The number of FTN install.";
      }
      leaf ftn-up-count {
        type uint32;
        description
          "The number of FTN up.";
      }
      leaf total-primary-ftn-count {
        type uint32;
        description
          "The total number of primary FTN.";
      }
      leaf primary-ftn-up-count {
        type uint32;
        description
          "The number of primary FTN up.";
      }
      leaf primary-ftn-install-count {
        type uint32;
        description
          "The number of Primary FTN install.";
      }
      leaf total-secondary-ftn-count {
        type uint32;
        description
          "The total number of secondary FTN.";
      }
      leaf secondary-ftn-install-count {
        type uint32;
        description
          "The number secondary FTN install.";
      }
      leaf secondary-ftn-up-count {
        type uint32;
        description
          "The number of secondary FTN up.";
      }
      leaf ipv6-total-ftn-count {
        type uint32;
        description
          "The total number of IPv6 FTN.";
      }
      leaf ipv6-ftn-up-count {
        type uint32;
        description
          "The number of IPv6 FTN up.";
      }
      leaf ipv6-total-primary-ftn-count {
        type uint32;
        description
          "The total number of primary IPv6 FTN.";
      }
      leaf ipv6-primary-ftn-up-count {
        type uint32;
        description
          "The number of primary IPv6  FTN up.";
      }
      leaf ipv6-total-secondary-ftn-count {
        type uint32;
        description
          "The total number of secondary IPv6 FTN.";
      }
      leaf ipv6-secondary-ftn-up-count {
        type uint32;
        description
          "The number of secondary IPv6 FTN up.";
      }
    }
  }

  grouping live_ncs_rib-ldp-count-grouping {
    description
      "Rib ldp count grouping.";
    container rib-ldp {
      description
        "rib ldp container.";
      leaf count {
        type uint32;
        description
          "Ldp rib count.";
      }
      list rib-ldp {
        key "index";
        description
          "rib ldp list";
        leaf index {
          type uint32;
          description
            "Ldp rib index.";
        }
        leaf session-address {
          type inet:ipv4-address;
          description
            "Session ipv4 address .";
        }
        leaf rib-type {
          type string;
          description
            "Rib type .";
        }
        leaf ftn-count {
          type uint32;
          description
            "The number of FTN.";
        }
        leaf ilm-count {
          type uint32;
          description
            "The number of ilm.";
        }
        leaf dependent-ilm-count {
          type uint32;
          description
            "The number of dependent ilm's.";
        }
      }
    }
  }

  grouping live_ncs_tunnel-stats-grouping {
    description
      "Tunnel stats grouping.";
    container tunnel-statistics {
      description
        "MPLS statistics container.";
      list entry {
        key "fec-address role owner";
        description
          "MPLS stats entry list";
        leaf fec-address {
          type inet:ip-prefix;
          description
            "MPLS stats FEC address.";
        }
        leaf role {
          type ciena-l3-types:live_ncs_mpls-stats-role;
          description
            "MPLS stats role.";
        }
        leaf owner {
          type ciena-l3-types:live_ncs_mpls-stats-owner;
          description
            "Protocol Owner Name.";
        }
        leaf tx-bytes {
          type yang:counter64;
          description
            "Tx bytes.";
        }
        leaf tx-packets {
          type yang:counter64;
          description
            "Tx packets.";
        }
      }
    }
  }

  grouping live_ncs_mpls-label-blocks-grouping {
    description
      "Mpls Label Blocks State grouping.";
    container label-blocks {
      description
        "MPLS label blocks container.";
      list label-block {
        key "index";
        description
          "MPLS label-block list";
        leaf index {
          type uint16;
          description
            "A user-specified identifier utilised to uniquely
             reference an MPLS label block.";
        }
        leaf start-label {
          type uint32;
          description
            "Label-block start.";
        }
        leaf end-label {
          type uint32;
          description
            "Label-block end.";
        }
        list protocol {
          key "name";
          description
            "List of MPLS protocols.";
          leaf name {
            type string;
            description
              "MPLS protocols name.";
          }
          leaf start-label {
            type uint32;
            description
              "Protocol label-block start.";
          }
          leaf end-label {
            type uint32;
            description
              "Protocol label-block end.";
          }
        }
      }
    }
  }

  grouping live_ncs_mpls-interface-grouping {
    description
      "MPLS interface grouping.";
    container interfaces {
      description
        "MPLS interfaces Container.";
      list interface {
        key "name";
        description
          "MPLS interface list.";
        leaf name {
          type leafref {
            path "/ncs:devices/ncs:device/ncs:live-status/oc-if:interfaces/oc-if:interface/oc-if:name" {
              tailf:xpath-root 3;
            }
          }
          description
            "MPLS interface name.";
        }
        leaf label-switching {
          type boolean;
          // NCS drop default statement
          description
            "This enables ldp on all interfaces and sets the default
             label space value which is 0 by default.";
        }
      }
    }
  }

  grouping live_ncs_address-family-grouping {
    list address-family {
      key "af-type";
      description
        "MPLS Label allocation for address families";
      leaf af-type {
        type ciena-l3-types:live_ncs_vrf-afi-type;
        description
          "MPLS Label allocation for given address family";
      }
      leaf mode {
        type live_ncs_label-mode-type;
        // NCS drop default statement
        description
          "MPLS Label allocation mode.";
      }
    }
  }

  grouping live_ncs_label-grouping {
    description
      "Grouping for label properties";
    container label-management {
      description
        "Label peoperties management container";
      container allocation-mode {
        description
          "MPLS Label allocation mode";
        container all-vrfs {
          description
            "MPLS Label allocation mode for all VRFs";
          uses live_ncs_address-family-grouping;
        }
        list vrf {
          key "name";
          leaf name {
            type leafref {
              path "/ncs:devices/ncs:device/ncs:live-status/vrf:vrf/vrf:vrfName" {
                tailf:xpath-root 3;
              }
            }
            description
              "VPN Routing/Forwarding instance name";
          }
          uses live_ncs_address-family-grouping;
        }
      }
      uses live_ncs_mpls-label-blocks;
    }
  }

  grouping live_ncs_mpls-tunnel-statistics-grouping {
    description
      "MPLS tunnel stats grouping.";
    container tunnel-statistics {
      description
        "MPLS tunnel statistics container.";
      list entry {
        key "fec-address role owner";
        description
          "MPLS stats entry list.";
        leaf fec-address {
          type inet:ip-prefix;
          description
            "MPLS stats fec Address.";
        }
        leaf role {
          type ciena-l3-types:live_ncs_mpls-stats-role;
          description
            "MPLS role can be ingress/egress/transit.";
        }
        leaf owner {
          type ciena-l3-types:live_ncs_mpls-stats-owner;
          description
            "Protocol Owner Name.";
        }
      }
    }
  }

  grouping live_ncs_mpls-label-blocks {
    description
      "Label-block allocation grouping.";
    container label-blocks {
      description
        "MPLS label blocks container.";
      list label-block {
        key "index";
        description
          "List of MPLS protocol label range.";
        leaf index {
          type uint16 {
            range "0";
          }
          description
            "A user-specified identifier utilised to uniquely
             reference an MPLS label block.";
        }
        list protocol {
          key "name";
          description
            "List of MPLS protocols.";
          leaf name {
            type ciena-l3-types:live_ncs_mpls-protocols;
            description
              "MPLS protocols name.";
          }
          leaf start-label {
            // NCS drop mandatory statement
            type uint32 {
              range "24321..1048575";
            }
            description
              "Protocol label-block start.";
          }
          leaf end-label {
            // NCS drop mandatory statement
            type uint32 {
              range "24321..1048575";
            }
            description
              "Protocol label-block end.";
          }
        }
      }
    }
  }

  grouping vrf-hash-table-grouping {
    description
      "Vrf hash table grouping.";
    list vrf-hash-table {
      key "vrf-name";
      description
        "Vrf table list.";
      leaf vrf-name {
        type string;
        description
          "MPLS vrf name.";
      }
      list vrf-afi-table {
        key "afi";
        description
          "vrf afi table list.";
        leaf afi {
          type ciena-l3-types:mpls-afi-type;
          description
            "Mpls vrf Ipv4/Ipv6 Address family";
        }
        list mpls-vrf {
          key "fec-address";
          description
            "MPLS vrf list";
          leaf fec-address {
            type inet:ip-prefix;
            description
              "MPLS vrf fec address";
          }
          leaf index {
            type uint32;
            description
              "MPLS vrf index";
          }
          uses ftn-entry-runtime-info-grouping;
          uses runtime-ftn-grouping;
          leaf tunnel-id {
            type uint32;
            description
              "Tunnel id.";
          }
        }
      }
    }
  }

  grouping ftn-runtime-entry-grouping {
    description
      "FTN runtime entry grouping.";
    list ftn-entry-runtime {
      key "fec-address";
      description
        "FTN runtime entry list.";
      leaf fec-address {
        type inet:ip-prefix;
        description
          "FTN Fec address.";
      }
      list ftn-index {
        key "ftn-index";
        description
          "FTN index list.";
        leaf ftn-index {
          type uint32;
          description
            "FTN index.";
        }
        uses ftn-entry-runtime-info-grouping;
        uses runtime-ftn-grouping;
      }
    }
    list backup-entry {
      key "fec-address";
      description
        "List of ftn runtime backup entries.";
      leaf fec-address {
        type inet:ip-prefix;
        description
          "Ftn Fec address.";
      }
      list entry-data {
        key "index";
        description
          "FTN backup entry data.";
        leaf index {
          type uint32;
          description
            "Ftn index.";
        }
        uses ftn-entry-runtime-info-grouping;
      }
    }
  }

  grouping ilm-runtime-entry-grouping {
    description
      "Ilm runtime entry grouping.";
    list ilm-runtime-entry {
      key "incoming-label";
      description
        "Ilm runtime entry list.";
      leaf incoming-label {
        type uint32;
        description
          "Incoming label entry in ilm table.";
      }
      list incoming-interface-entry {
        key "name";
        description
          "Incoming interface entry list";
        leaf name {
          type string;
          description
            "Incoming interface name.";
        }
        list ilm-index {
          key "index";
          description
            "ilm index list";
          leaf index {
            type uint32;
            description
              "Ilm index.";
          }
          leaf owner {
            type string;
            description
              "Ownership of the management plane.";
          }
          leaf lsp-type {
            type string;
            description
              "Ilm lsp type.";
          }
          leaf row-status {
            type ciena-l3-types:mpls-row-status;
            description
              "Status of ilm runtime entry such as active,not in services,not ready.";
          }
          leaf flag {
            type string;
            description
              "Ilm flag value.";
          }
          leaf opcode {
            type ciena-l3-types:mpls-opcode;
            description
              "Ilm opcode value such as swap,pop and push.";
          }
          leaf fec-address {
            type inet:ip-prefix;
            description
              "Ilm fec address.";
          }
          list cross-connect-entry {
            key "index";
            description
              "Cross connect entry list.";
            leaf index {
              type uint32;
              description
                "Table index for the cross-connect.";
            }
            container nhlfe-entry {
              description
                "Container with Next hop label forwarding entry .";
              leaf outgoing-label {
                type uint32;
                description
                  " MPLS outgoing label value.";
              }
              leaf ilm-next-hop-ip-address {
                type inet:ip-address;
                description
                  "IP address of the next hop.";
              }
              leaf outgoing-interface-name {
                type string;
                description
                  "Outgoing interface name.";
              }
              uses runtime-nhlfe-entry;
            }
            leaf next-hop-type {
              type ciena-l3-types:mpls-next-hop-type;
              description
                "Indicates whether next-hop is primary or backup.";
            }
            uses runtime-xc-entry-grouping;
          }
        }
      }
    }
  }

  grouping runtime-nhlfe-entry {
    description
      "Runtime next hop label forwarding entry grouping.";
    leaf index {
      type uint32;
      description
        "Next hop label forwarding entry index.";
    }
    leaf cross-connect-index {
      type uint32;
      description
        "Cross connect index.";
    }
    leaf owner {
      type string;
      description
        "Creator of the cross connect, typically a protocol such as BGP,LDP... .";
    }
    leaf recursive-next-hop-address {
      type inet:ip-address;
      description
        "Recursive next hop address .";
    }
    leaf tx-bytes {
      type uint32;
      description
        "The number of trasmited bytes.";
    }
    leaf tx-pkts {
      type uint32;
      description
        "The number of transmited packets.";
    }
    leaf error-pkts {
      type uint32;
      description
        "The number of error packets.";
    }
    leaf discard-pkts {
      type uint32;
      description
        "The number of discarded packets count.";
    }
  }

  grouping runtime-xc-entry-grouping {
    description
      "Run time cross connect entry grouping.";
    leaf nhlfe-index {
      type uint32;
      description
        "Next hop label forwarding Entry index.";
    }
    leaf owner {
      type string;
      description
        "Creator of the cross connect, typically a protocol such as BGP,LDP etc.";
    }
    leaf label-stack {
      type string;
      description
        "Contains label stack for backup path.";
    }
  }

  grouping ftn-entry-runtime-info-grouping {
    description
      "FTN runtime entry information grouping.";
    list cross-connect-entry {
      key "index";
      description
        "Cross connect entry list.";
      leaf index {
        type uint32;
        description
          "Cross connect index.";
      }
      leaf incoming-label {
        type uint32;
        description
          "Incoming label value.";
      }
      leaf opcode {
        type string;
        description
          "Contains cross connect opcode.";
      }
      leaf admin-state {
        type string;
        description
          "The admin state of the backup xc-entry";
      }
      leaf oper-state {
        type string;
        description
          "The operational state of the backup xc-entry";
      }
      container nhlfe-entry {
        description
          "Next hop label forwarding Entry";
        leaf outgoing-label {
          type uint32;
          description
            "Outgoing label value.";
        }
        leaf next-hop-ip-address {
          type inet:ip-address;
          description
            "IP address of the next hop.";
        }
        leaf outgoing-interface-name {
          type string;
          description
            "Outgoing interface name.";
        }
        uses runtime-nhlfe-entry;
      }
      uses runtime-xc-entry-grouping;
    }
  }

  grouping runtime-ftn-grouping {
    description
      "Runtime FTN attributes.";
    leaf row-status {
      type ciena-l3-types:mpls-row-status;
      description
        "Status for FTN runtime entry such as active,not in services,not ready etc.";
    }
    leaf owner {
      type string;
      description
        "Creator of this segment, typically a protocol such as LDP,BGP,RSVP etc.";
    }
    leaf action-type {
      type string;
      description
        "Runtime FTN action type such as Redirect to tunnel.";
    }
    leaf flag {
      type string;
      description
        "Runtime FTN flag value.";
    }
  }

  grouping mpls-all-if-count-grouping {
    description
      "MPLS all interfaces count grouping.";
    container interfaces {
      description
        "MPLS all if count container.";
      leaf total-count {
        type uint32;
        description
          "The total number of interfaces.";
      }
      list interface {
        key "name";
        description
          "MPLS interface count list";
        leaf name {
          type string;
          description
            "MPLS nterface name.";
        }
        leaf total-ftn-count {
          type uint32;
          description
            "The total number of FTN.";
        }
        leaf total-ilm-count {
          type uint32;
          description
            "The Total number of ilm.";
        }
      }
    }
  }

  grouping mpls-grouping {
    description
      "MPLS grouping.";
    // NCS drop config false container 'mpls-state'
  }

  grouping vrf-table-count-grouping {
    description
      "Vrf table count grouping.";
    container vrf-table {
      description
        "vrf table container";
      leaf vrf-ipv4-count {
        type uint32;
        description
          "The number of Ipv4 vrf.";
      }
      leaf vrf-ipv4-install-count {
        type uint32;
        description
          "The number of Ipv4 vrf install.";
      }
      leaf vrf-ipv4-up-count {
        type uint32;
        description
          "The number of Ipv4 vrf up.";
      }
      leaf vrf-ipv6-count {
        type uint32;
        description
          "The number of IPv6 VRFs.";
      }
      leaf vrf-ipv6-install-count {
        type uint32;
        description
          "The number of IPv6 VRF install.";
      }
      leaf vrf-ipv6-up-count {
        type uint32;
        description
          "The number of IPv6 VRF up.";
      }
    }
  }

  grouping ilm-table-count-grouping {
    description
      "Ilm table count grouping.";
    container ilm-table {
      description
        "ilm table count container.";
      leaf count {
        type uint32;
        description
          "The number of Ilm Label.";
      }
      leaf install-count {
        type uint32;
        description
          "The number of Label install.";
      }
      leaf up-count {
        type uint32;
        description
          "The number of Label up.";
      }
      leaf swap-count {
        type uint32;
        description
          "The number of Label swap.";
      }
      leaf swap-install-count {
        type uint32;
        description
          "The number of Label swap install.";
      }
      leaf swap-up-count {
        type uint32;
        description
          "The number of Label swap up.";
      }
      leaf pop-count {
        type uint32;
        description
          "The number of Label pop.";
      }
      leaf pop-install-count {
        type uint32;
        description
          "The number of Label pop install.";
      }
      leaf pop-up-count {
        type uint32;
        description
          "The number of Label pop up. ";
      }
    }
  }

  grouping forwarding-table-count-grouping {
    description
      "Forwarding table count grouping.";
    container forwarding-table {
      description
        "Forwarding table count container";
      leaf total-ftn-count {
        type uint32;
        description
          "The total number of FTN.";
      }
      leaf ftn-install-count {
        type uint32;
        description
          "The number of FTN install.";
      }
      leaf ftn-up-count {
        type uint32;
        description
          "The number of FTN up.";
      }
      leaf total-primary-ftn-count {
        type uint32;
        description
          "The total number of primary FTN.";
      }
      leaf primary-ftn-up-count {
        type uint32;
        description
          "The number of primary FTN up.";
      }
      leaf primary-ftn-install-count {
        type uint32;
        description
          "The number of Primary FTN install.";
      }
      leaf total-secondary-ftn-count {
        type uint32;
        description
          "The total number of secondary FTN.";
      }
      leaf secondary-ftn-install-count {
        type uint32;
        description
          "The number secondary FTN install.";
      }
      leaf secondary-ftn-up-count {
        type uint32;
        description
          "The number of secondary FTN up.";
      }
      leaf ipv6-total-ftn-count {
        type uint32;
        description
          "The total number of IPv6 FTN.";
      }
      leaf ipv6-ftn-up-count {
        type uint32;
        description
          "The number of IPv6 FTN up.";
      }
      leaf ipv6-total-primary-ftn-count {
        type uint32;
        description
          "The total number of primary IPv6 FTN.";
      }
      leaf ipv6-primary-ftn-up-count {
        type uint32;
        description
          "The number of primary IPv6  FTN up.";
      }
      leaf ipv6-total-secondary-ftn-count {
        type uint32;
        description
          "The total number of secondary IPv6 FTN.";
      }
      leaf ipv6-secondary-ftn-up-count {
        type uint32;
        description
          "The number of secondary IPv6 FTN up.";
      }
    }
  }

  grouping rib-ldp-count-grouping {
    description
      "Rib ldp count grouping.";
    container rib-ldp {
      description
        "rib ldp container.";
      leaf count {
        type uint32;
        description
          "Ldp rib count.";
      }
      list rib-ldp {
        key "index";
        description
          "rib ldp list";
        leaf index {
          type uint32;
          description
            "Ldp rib index.";
        }
        leaf session-address {
          type inet:ipv4-address;
          description
            "Session ipv4 address .";
        }
        leaf rib-type {
          type string;
          description
            "Rib type .";
        }
        leaf ftn-count {
          type uint32;
          description
            "The number of FTN.";
        }
        leaf ilm-count {
          type uint32;
          description
            "The number of ilm.";
        }
        leaf dependent-ilm-count {
          type uint32;
          description
            "The number of dependent ilm's.";
        }
      }
    }
  }

  grouping tunnel-stats-grouping {
    description
      "Tunnel stats grouping.";
    container tunnel-statistics {
      description
        "MPLS statistics container.";
      list entry {
        key "fec-address role owner";
        description
          "MPLS stats entry list";
        leaf fec-address {
          type inet:ip-prefix;
          description
            "MPLS stats FEC address.";
        }
        leaf role {
          type ciena-l3-types:mpls-stats-role;
          description
            "MPLS stats role.";
        }
        leaf owner {
          type ciena-l3-types:mpls-stats-owner;
          description
            "Protocol Owner Name.";
        }
        leaf tx-bytes {
          type yang:counter64;
          description
            "Tx bytes.";
        }
        leaf tx-packets {
          type yang:counter64;
          description
            "Tx packets.";
        }
      }
    }
  }

  grouping mpls-label-blocks-grouping {
    description
      "Mpls Label Blocks State grouping.";
    container label-blocks {
      description
        "MPLS label blocks container.";
      list label-block {
        key "index";
        description
          "MPLS label-block list";
        leaf index {
          type uint16;
          description
            "A user-specified identifier utilised to uniquely
             reference an MPLS label block.";
        }
        leaf start-label {
          type uint32;
          description
            "Label-block start.";
        }
        leaf end-label {
          type uint32;
          description
            "Label-block end.";
        }
        list protocol {
          key "name";
          description
            "List of MPLS protocols.";
          leaf name {
            type string;
            description
              "MPLS protocols name.";
          }
          leaf start-label {
            type uint32;
            description
              "Protocol label-block start.";
          }
          leaf end-label {
            type uint32;
            description
              "Protocol label-block end.";
          }
        }
      }
    }
  }

  grouping mpls-interface-grouping {
    description
      "MPLS interface grouping.";
    container interfaces {
      description
        "MPLS interfaces Container.";
      list interface {
        key "name";
        description
          "MPLS interface list.";
        leaf name {
          type leafref {
            path "/ncs:devices/ncs:device/ncs:config/oc-if:interfaces/oc-if:interface/oc-if:name" {
              tailf:xpath-root 3;
            }
          }
          description
            "MPLS interface name.";
        }
        leaf label-switching {
          type boolean;
          default "false";
          description
            "This enables ldp on all interfaces and sets the default
             label space value which is 0 by default.";
        }
      }
    }
  }

  grouping address-family-grouping {
    list address-family {
      key "af-type";
      description
        "MPLS Label allocation for address families";
      leaf af-type {
        type ciena-l3-types:vrf-afi-type;
        description
          "MPLS Label allocation for given address family";
      }
      leaf mode {
        type label-mode-type;
        default "per-prefix";
        description
          "MPLS Label allocation mode.";
      }
    }
  }

  grouping label-grouping {
    description
      "Grouping for label properties";
    container label-management {
      description
        "Label peoperties management container";
      container allocation-mode {
        description
          "MPLS Label allocation mode";
        container all-vrfs {
          description
            "MPLS Label allocation mode for all VRFs";
          uses address-family-grouping;
        }
        list vrf {
          key "name";
          leaf name {
            type leafref {
              path "/ncs:devices/ncs:device/ncs:config/vrf:vrf/vrf:vrfName" {
                tailf:xpath-root 3;
              }
            }
            description
              "VPN Routing/Forwarding instance name";
          }
          uses address-family-grouping;
        }
      }
      uses mpls-label-blocks;
    }
  }

  grouping mpls-tunnel-statistics-grouping {
    description
      "MPLS tunnel stats grouping.";
    container tunnel-statistics {
      description
        "MPLS tunnel statistics container.";
      list entry {
        key "fec-address role owner";
        description
          "MPLS stats entry list.";
        leaf fec-address {
          type inet:ip-prefix;
          description
            "MPLS stats fec Address.";
        }
        leaf role {
          type ciena-l3-types:mpls-stats-role;
          description
            "MPLS role can be ingress/egress/transit.";
        }
        leaf owner {
          type ciena-l3-types:mpls-stats-owner;
          description
            "Protocol Owner Name.";
        }
      }
    }
  }

  grouping mpls-label-blocks {
    description
      "Label-block allocation grouping.";
    container label-blocks {
      description
        "MPLS label blocks container.";
      list label-block {
        key "index";
        description
          "List of MPLS protocol label range.";
        leaf index {
          type uint16 {
            range "0";
          }
          description
            "A user-specified identifier utilised to uniquely
             reference an MPLS label block.";
        }
        list protocol {
          key "name";
          description
            "List of MPLS protocols.";
          leaf name {
            type ciena-l3-types:mpls-protocols;
            description
              "MPLS protocols name.";
          }
          leaf start-label {
            mandatory true;
            type uint32 {
              range "24321..1048575";
            }
            description
              "Protocol label-block start.";
          }
          leaf end-label {
            mandatory true;
            type uint32 {
              range "24321..1048575";
            }
            description
              "Protocol label-block end.";
          }
        }
      }
    }
  }

  augment "/ncs:devices/ncs:device/ncs:rpc" {
    container rpc-mpls-clear-tunnel-statistics {
      tailf:ncs-device-type "netconf";
      tailf:display-when "not(../../ncs:module) or ../../ncs:module[ncs:name='ciena-mpls']";
      tailf:action mpls-clear-tunnel-statistics {
        tailf:actionpoint ncsproxy {
          tailf:internal;
        }
        input {
          leaf fec-address {
            type inet:ip-prefix;
            description
              "IP prefix address";
          }
          leaf role {
            type ciena-l3-types:ncs_rpc_notif_mpls-stats-role;
            description
              "Tunnel Role";
          }
          leaf owner {
            type ciena-l3-types:ncs_rpc_notif_mpls-stats-owner;
            description
              "Tunnel Protocol Owner";
          }
        }
        output {
          leaf response {
            type string;
            description
              "Response output for request";
          }
        }
      }
    }
  }
  augment "/ncs:devices/ncs:device-group/ncs:ned-id/ncs:rpc" {
    container rpc-mpls-clear-tunnel-statistics {
      tailf:ncs-device-type "netconf";
      tailf:display-when "/ncs:devices/ncs:device[ncs:name=current()/../../../ncs:member]/ncs:module[ncs:name='ciena-mpls']";
      tailf:action mpls-clear-tunnel-statistics {
        tailf:actionpoint ncsproxy {
          tailf:internal;
        }
        input {
          leaf fec-address {
            type inet:ip-prefix;
            description
              "IP prefix address";
          }
          leaf role {
            type ciena-l3-types:ncs_rpc_notif_mpls-stats-role;
            description
              "Tunnel Role";
          }
          leaf owner {
            type ciena-l3-types:ncs_rpc_notif_mpls-stats-owner;
            description
              "Tunnel Protocol Owner";
          }
        }
        output {
          container "device" {
            leaf "name" {
              type string;
            }
            leaf "info" {
              type string;
            }
            container "result" {
              leaf response {
                type string;
                description
                  "Response output for request";
              }
            }
          }
        }
      }
    }
  }
  augment "/ncs:devices/ncs:device/ncs:config" {
    container mpls {
      tailf:ncs-device-type "netconf";
      tailf:display-when "not(../../ncs:module) or ../../ncs:module[ncs:name='ciena-mpls']";
      uses mpls-interface-grouping;
      uses label-grouping;
      uses mpls-tunnel-statistics-grouping;
      description
        "MPLS config container.";
    }
    uses mpls-grouping;
  }
  augment "/ncs:devices/ncs:device/ncs:live-status" {
    container mpls {
      tailf:ncs-device-type "netconf";
      tailf:display-when "not(../../ncs:module) or ../../ncs:module[ncs:name='ciena-mpls'] or (../../ncs:live-status-protocol[not(ncs:capability)]) or (../../ncs:live-status-protocol/ncs:capability/ncs:module[.='ciena-mpls'])";
      uses live_ncs_mpls-interface-grouping;
      uses live_ncs_label-grouping;
      uses live_ncs_mpls-tunnel-statistics-grouping;
      description
        "MPLS config container.";
    }
    uses live_ncs_mpls-grouping {
      refine mpls-state {
        tailf:ncs-device-type "netconf";
        tailf:display-when "not(../../ncs:module) or ../../ncs:module[ncs:name='ciena-mpls'] or (../../ncs:live-status-protocol[not(ncs:capability)]) or (../../ncs:live-status-protocol/ncs:capability/ncs:module[.='ciena-mpls'])";
      }
    }
  }
  augment "/ncs:devices/ncs:template/ncs:ned-id/ncs:config" {
    container mpls {
      uses ncs_template_mpls-interface-grouping;
      uses ncs_template_label-grouping;
      uses ncs_template_mpls-tunnel-statistics-grouping;
      description
        "MPLS config container.";
    }
    uses ncs_template_mpls-grouping;
  }
}
