module ciena-packet-otn-port-deviation {
  // Generated by yanger -t ncs
  tailf:mount-id "saos1051-nc-1.0:saos1051-nc-1.0";
  tailf:ncs-device-type "netconf";

  namespace "http://www.ciena.com/ns/yang/ciena-packet-otn-port-dev";
  prefix port-dev;

  import ciena-packet-otn-port {
    prefix port;
  }
  import yuma-ncx {
    prefix ncx;
  }
  import tailf-common {
    prefix tailf;
  }
  import tailf-ncs {
    prefix ncs;
  }

  revision 2019-10-14 {
    description
      "Remove the deviation of admin-state";
  }
  revision 2018-09-17 {
    description
      "Initial revision.";
  }

  deviation "/ncs:devices/ncs:template/ncs:ned-id/ncs:config/port:otn-ports/port:ports/port:properties/port:forward-error-correction" {
    deviate not-supported;
  }
  deviation "/ncs:devices/ncs:device/ncs:live-status/port:otn-ports/port:ports/port:properties/port:forward-error-correction" {
    deviate not-supported;
  }
  deviation "/ncs:devices/ncs:device/ncs:config/port:otn-ports/port:ports/port:properties/port:forward-error-correction" {
    deviate not-supported;
  }
  deviation "/ncs:devices/ncs:device/ncs:live-status/port:otn-ports/port:ports/port:properties/port:service-index" {
    deviate not-supported;
  }
  deviation "/ncs:devices/ncs:device/ncs:live-status/port:otn-ports/port:ports/port:properties/port:service-domain-index" {
    deviate not-supported;
  }
  deviation "/ncs:devices/ncs:template/ncs:ned-id/ncs:config/port:otn-ports/port:ports/port:properties/port:otn/port:pre-fec-otu-sf-threshold" {
    deviate not-supported;
  }
  deviation "/ncs:devices/ncs:device/ncs:live-status/port:otn-ports/port:ports/port:properties/port:otn/port:pre-fec-otu-sf-threshold" {
    deviate not-supported;
  }
  deviation "/ncs:devices/ncs:device/ncs:config/port:otn-ports/port:ports/port:properties/port:otn/port:pre-fec-otu-sf-threshold" {
    deviate not-supported;
  }
  deviation "/ncs:devices/ncs:template/ncs:ned-id/ncs:config/port:otn-ports/port:ports/port:properties/port:otn/port:pre-fec-otu-sd-threshold" {
    deviate not-supported;
  }
  deviation "/ncs:devices/ncs:device/ncs:live-status/port:otn-ports/port:ports/port:properties/port:otn/port:pre-fec-otu-sd-threshold" {
    deviate not-supported;
  }
  deviation "/ncs:devices/ncs:device/ncs:config/port:otn-ports/port:ports/port:properties/port:otn/port:pre-fec-otu-sd-threshold" {
    deviate not-supported;
  }
  deviation "/ncs:devices/ncs:template/ncs:ned-id/ncs:config/port:otn-ports/port:ports/port:properties/port:otn/port:conditioning-type" {
    deviate not-supported;
  }
  deviation "/ncs:devices/ncs:device/ncs:live-status/port:otn-ports/port:ports/port:properties/port:otn/port:conditioning-type" {
    deviate not-supported;
  }
  deviation "/ncs:devices/ncs:device/ncs:config/port:otn-ports/port:ports/port:properties/port:otn/port:conditioning-type" {
    deviate not-supported;
  }
  deviation "/ncs:devices/ncs:device/ncs:live-status/port:otn-ports/port:ports/port:channels/port:properties/port:service-index" {
    deviate not-supported;
  }
  deviation "/ncs:devices/ncs:device/ncs:live-status/port:otn-ports/port:ports/port:channels/port:properties/port:service-domain-index" {
    deviate not-supported;
  }
}
