module ciena-dhcp-l3-relay {
  // Generated by yanger -t ncs
  tailf:mount-id "saos1051-nc-1.0:saos1051-nc-1.0";
  tailf:ncs-device-type "netconf";

  yang-version 1;
  namespace "http://ciena.com/dhcpl3relay/yang/ciena-dhcp-l3-relay";
  prefix ciena-dhcp-l3-relay;

  import ciena-types {
    prefix ciena;
  }
  import openconfig-interfaces {
    prefix oc-if;
  }
  import ciena-mef-fp {
    prefix mef-fp;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This module contains the Ciena proprietary YANG deviations
     of the openconfig-interfaces YANG module.

     Copyright (c) 2017 Ciena Corporation.  All rights reserved.

     All information contained herein is, and remains
     the property of Ciena Corporation. Dissemination of this
     information or reproduction of this material is strictly
     forbidden unless prior written permission is obtained from
     Ciena Corporation.";

  revision 2018-11-01 {
    description
      "Updated leaf ip-interface from type string to type
       oc-if:base-interface-ref for leafref dependency.
       Updated leaf flow-point from type string to type
       mef-fp:fp-ref for leafref dependency.";
    reference "";
  }
  revision 2018-08-23 {
    description
      "Initial version";
    reference "";
  }

  grouping ncs_template_remote-id {
    leaf remote-id-type {
      type string;
      description
        "Use to specify remote ID as device-hostname/device-mac-address/rid-string.";
    }
    leaf rid-string {
      type string;
      description
        "The string value for rid-string.";
    }
  }

  grouping ncs_template_circuit-id {
    leaf circuit-id-type {
      type string;
      description
        "Use to specify circuit ID as cid-string/interface-name.";
    }
  }

  grouping ncs_template_ip-interface {
    list ip-interfaces {
      // NCS patched for predictable order
      ordered-by user;
      key "ip-interface";
      description
        "A list of the ip-interfaces.";
      leaf ip-interface {
        type oc-if:ncs_template_base-interface-ref;
        description
          "The name of the ip-interface.";
      }
      leaf ip-interface-enabled {
        type string;
        description
          "Use to enable/disable ip-interface.";
      }
      leaf ip-interface-trusted {
        type string;
        description
          "Use to enable/disable trusted ip-interface.";
      }
      leaf cid-string {
        type string;
        description
          "The string value for cid-string.";
      }
      list flow-points {
        // NCS patched for predictable order
        ordered-by user;
        key "flow-point";
        description
          "A list of flow points.";
        leaf flow-point {
          type mef-fp:ncs_template_fp-ref;
          description
            "The name of a flow point.";
        }
        leaf flow-point-trusted {
          type string;
          description
            "Use to enable/disable trust for flow point.";
        }
      }
      // NCS drop config false container state
    }
  }

  grouping ncs_template_option-82 {
    leaf option-82 {
      type string;
      description
        "Set option 82 to on/off/replace/remove/include.";
    }
    leaf encapsulate-option-82 {
      type string;
      description
        "Enable/disable encapsulation of option 82.";
    }
  }

  grouping ncs_rpc_notif_remote-id {
    leaf remote-id-type {
      type identityref {
        base remote-id-type;
      }
      description
        "Use to specify remote ID as device-hostname/device-mac-address/rid-string.";
    }
    leaf rid-string {
      type string {
        length "0..64";
      }
      description
        "The string value for rid-string.";
    }
  }

  grouping ncs_rpc_notif_circuit-id {
    leaf circuit-id-type {
      type identityref {
        base circuit-id-type;
      }
      description
        "Use to specify circuit ID as cid-string/interface-name.";
    }
  }

  grouping ncs_rpc_notif_ip-interface {
    list ip-interfaces {
      key "ip-interface";
      description
        "A list of the ip-interfaces.";
      leaf ip-interface {
        type oc-if:ncs_rpc_notif_base-interface-ref;
        description
          "The name of the ip-interface.";
      }
      leaf ip-interface-enabled {
        type boolean;
        description
          "Use to enable/disable ip-interface.";
      }
      leaf ip-interface-trusted {
        type boolean;
        description
          "Use to enable/disable trusted ip-interface.";
      }
      leaf cid-string {
        type string {
          length "0..64";
        }
        description
          "The string value for cid-string.";
      }
      list flow-points {
        key "flow-point";
        description
          "A list of flow points.";
        leaf flow-point {
          type mef-fp:ncs_rpc_notif_fp-ref;
          description
            "The name of a flow point.";
        }
        leaf flow-point-trusted {
          type boolean;
          description
            "Use to enable/disable trust for flow point.";
        }
      }
      container state {
        config false;
        description
          "Operational data for DHCP L3 Relay Agent instance.";
        leaf server-packets-relayed {
          type uint32;
          description
            "The number of server packets relayed to the server.";
        }
        leaf server-packet-errors {
          type uint32;
          description
            "The number of server packet errors.";
        }
        leaf agent-option-errors {
          type uint32;
          description
            "The number of agent option errors.";
        }
        leaf server-packet-received {
          type uint32;
          description
            "The number of server packets received.";
        }
        leaf client-packet-received {
          type uint32;
          description
            "The number of client packets received.";
        }
        leaf untrusted-if-drops {
          type uint32;
          description
            "The number of packets dropped because the interface is not trusted.";
        }
      }
    }
  }

  grouping ncs_rpc_notif_option-82 {
    leaf option-82 {
      type identityref {
        base option-82-setting;
      }
      description
        "Set option 82 to on/off/replace/remove/include.";
    }
    leaf encapsulate-option-82 {
      type boolean;
      description
        "Enable/disable encapsulation of option 82.";
    }
  }

  grouping live_ncs_remote-id {
    leaf remote-id-type {
      type identityref {
        base remote-id-type;
      }
      description
        "Use to specify remote ID as device-hostname/device-mac-address/rid-string.";
    }
    leaf rid-string {
      type string {
        length "0..64";
      }
      description
        "The string value for rid-string.";
    }
  }

  grouping live_ncs_circuit-id {
    leaf circuit-id-type {
      type identityref {
        base circuit-id-type;
      }
      description
        "Use to specify circuit ID as cid-string/interface-name.";
    }
  }

  grouping live_ncs_ip-interface {
    list ip-interfaces {
      key "ip-interface";
      description
        "A list of the ip-interfaces.";
      leaf ip-interface {
        type oc-if:live_ncs_base-interface-ref;
        description
          "The name of the ip-interface.";
      }
      leaf ip-interface-enabled {
        type boolean;
        description
          "Use to enable/disable ip-interface.";
      }
      leaf ip-interface-trusted {
        type boolean;
        description
          "Use to enable/disable trusted ip-interface.";
      }
      leaf cid-string {
        type string {
          length "0..64";
        }
        description
          "The string value for cid-string.";
      }
      list flow-points {
        key "flow-point";
        description
          "A list of flow points.";
        leaf flow-point {
          type mef-fp:live_ncs_fp-ref;
          description
            "The name of a flow point.";
        }
        leaf flow-point-trusted {
          type boolean;
          description
            "Use to enable/disable trust for flow point.";
        }
      }
      container state {
        description
          "Operational data for DHCP L3 Relay Agent instance.";
        leaf server-packets-relayed {
          type uint32;
          description
            "The number of server packets relayed to the server.";
        }
        leaf server-packet-errors {
          type uint32;
          description
            "The number of server packet errors.";
        }
        leaf agent-option-errors {
          type uint32;
          description
            "The number of agent option errors.";
        }
        leaf server-packet-received {
          type uint32;
          description
            "The number of server packets received.";
        }
        leaf client-packet-received {
          type uint32;
          description
            "The number of client packets received.";
        }
        leaf untrusted-if-drops {
          type uint32;
          description
            "The number of packets dropped because the interface is not trusted.";
        }
      }
    }
  }

  grouping live_ncs_option-82 {
    leaf option-82 {
      type identityref {
        base option-82-setting;
      }
      description
        "Set option 82 to on/off/replace/remove/include.";
    }
    leaf encapsulate-option-82 {
      type boolean;
      description
        "Enable/disable encapsulation of option 82.";
    }
  }

  grouping remote-id {
    leaf remote-id-type {
      type identityref {
        base remote-id-type;
      }
      description
        "Use to specify remote ID as device-hostname/device-mac-address/rid-string.";
    }
    leaf rid-string {
      type string {
        length "0..64";
      }
      description
        "The string value for rid-string.";
    }
  }

  grouping circuit-id {
    leaf circuit-id-type {
      type identityref {
        base circuit-id-type;
      }
      description
        "Use to specify circuit ID as cid-string/interface-name.";
    }
  }

  grouping ip-interface {
    list ip-interfaces {
      key "ip-interface";
      description
        "A list of the ip-interfaces.";
      leaf ip-interface {
        type oc-if:base-interface-ref;
        description
          "The name of the ip-interface.";
      }
      leaf ip-interface-enabled {
        type boolean;
        description
          "Use to enable/disable ip-interface.";
      }
      leaf ip-interface-trusted {
        type boolean;
        description
          "Use to enable/disable trusted ip-interface.";
      }
      leaf cid-string {
        type string {
          length "0..64";
        }
        description
          "The string value for cid-string.";
      }
      list flow-points {
        key "flow-point";
        description
          "A list of flow points.";
        leaf flow-point {
          type mef-fp:fp-ref;
          description
            "The name of a flow point.";
        }
        leaf flow-point-trusted {
          type boolean;
          description
            "Use to enable/disable trust for flow point.";
        }
      }
      // NCS drop config false container state
    }
  }

  grouping option-82 {
    leaf option-82 {
      type identityref {
        base option-82-setting;
      }
      description
        "Set option 82 to on/off/replace/remove/include.";
    }
    leaf encapsulate-option-82 {
      type boolean;
      description
        "Enable/disable encapsulation of option 82.";
    }
  }

  augment "/ncs:devices/ncs:device/ncs:rpc" {
    container rpc-dhcp-relay-agent-stats-clear {
      tailf:ncs-device-type "netconf";
      tailf:display-when "not(../../ncs:module) or ../../ncs:module[ncs:name='ciena-dhcp-l3-relay']";
      tailf:action dhcp-relay-agent-stats-clear {
        tailf:actionpoint ncsproxy {
          tailf:internal;
        }
        description
          "Clear dhcp-l3-relay statistics.";
      }
    }
  }
  augment "/ncs:devices/ncs:device-group/ncs:ned-id/ncs:rpc" {
    container rpc-dhcp-relay-agent-stats-clear {
      tailf:ncs-device-type "netconf";
      tailf:display-when "/ncs:devices/ncs:device[ncs:name=current()/../../../ncs:member]/ncs:module[ncs:name='ciena-dhcp-l3-relay']";
      tailf:action dhcp-relay-agent-stats-clear {
        tailf:actionpoint ncsproxy {
          tailf:internal;
        }
        description
          "Clear dhcp-l3-relay statistics.";
      }
    }
  }
  augment "/ncs:devices/ncs:device/ncs:config" {
    container l3-relay-agent {
      tailf:ncs-device-type "netconf";
      tailf:display-when "not(../../ncs:module) or ../../ncs:module[ncs:name='ciena-dhcp-l3-relay']";
      description
        "Top-level grouping for each dhcp l3 relay.";
      list instance {
        key "relay-name";
        description
          "A list of dhcp-l3-relay instances.";
        leaf relay-name {
          type string;
          description
            "The name of an individual dhcp-l3-relay instance.";
        }
        leaf admin-enabled {
          type boolean;
          description
            "Use to enable/disable dhcp-l3-relay.";
        }
        list dhcp-server-addresses {
          key "dhcp-server-address";
          description
            "A list of dhcp-servers.";
          leaf dhcp-server-address {
            type string;
            description
              "The address of a dhcp server.";
          }
          // NCS drop config false container state
        }
        leaf verify-dhcp-reply {
          type boolean;
          description
            "Verify validity of DHCP server reply.";
        }
        uses ip-interface;
        uses remote-id;
        uses circuit-id;
        uses option-82;
        // NCS drop config false container state
      }
    }
  }
  augment "/ncs:devices/ncs:device/ncs:live-status" {
    container l3-relay-agent {
      tailf:ncs-device-type "netconf";
      tailf:display-when "not(../../ncs:module) or ../../ncs:module[ncs:name='ciena-dhcp-l3-relay'] or (../../ncs:live-status-protocol[not(ncs:capability)]) or (../../ncs:live-status-protocol/ncs:capability/ncs:module[.='ciena-dhcp-l3-relay'])";
      description
        "Top-level grouping for each dhcp l3 relay.";
      list instance {
        key "relay-name";
        description
          "A list of dhcp-l3-relay instances.";
        leaf relay-name {
          type string;
          description
            "The name of an individual dhcp-l3-relay instance.";
        }
        leaf admin-enabled {
          type boolean;
          description
            "Use to enable/disable dhcp-l3-relay.";
        }
        list dhcp-server-addresses {
          key "dhcp-server-address";
          description
            "A list of dhcp-servers.";
          leaf dhcp-server-address {
            type string;
            description
              "The address of a dhcp server.";
          }
          container state {
            description
              "Operational data for DHCP L3 Relay Agent instance.";
            leaf packets-relayed {
              type uint32;
              description
                "The number of packets relayed to the server.";
            }
            leaf packets-relay-error {
              type uint32;
              description
                "The number of packets relay errors.";
            }
          }
        }
        leaf verify-dhcp-reply {
          type boolean;
          description
            "Verify validity of DHCP server reply.";
        }
        uses live_ncs_ip-interface;
        uses live_ncs_remote-id;
        uses live_ncs_circuit-id;
        uses live_ncs_option-82;
        container state {
          description
            "Operational data for DHCP L3 Relay Agent instance.";
          leaf oper-status {
            type ciena:live_ncs_oper-state;
            description
              "The operational state of the dhcp-l3-relay instance.";
          }
          leaf status-message {
            type string;
            description
              "The current status of the dhcp-l3-relay instance.";
          }
          leaf option-82-replaced {
            type uint32;
            description
              "Option 82 Replaced data.";
          }
          leaf option-82-added {
            type uint32;
            description
              "Option 82 Added data.";
          }
          leaf option-82-off {
            type uint32;
            description
              "Option 82 Off data.";
          }
          leaf bad-cid {
            type uint32;
            description
              "Bad Circuit ID data.";
          }
          leaf client-spoofed-packets {
            type uint32;
            description
              "The number of packets spoofed by the client.";
          }
          leaf server-spoofed-packets {
            type uint32;
            description
              "The number of packets spoofed by the server.";
          }
          leaf untrusted-fp-drops {
            type uint32;
            description
              "The number of packets dropped because the flow point is not trusted.";
          }
        }
      }
    }
  }
  augment "/ncs:devices/ncs:template/ncs:ned-id/ncs:config" {
    container l3-relay-agent {
      description
        "Top-level grouping for each dhcp l3 relay.";
      list instance {
        // NCS patched for predictable order
        ordered-by user;
        key "relay-name";
        description
          "A list of dhcp-l3-relay instances.";
        leaf relay-name {
          type string;
          description
            "The name of an individual dhcp-l3-relay instance.";
        }
        leaf admin-enabled {
          type string;
          description
            "Use to enable/disable dhcp-l3-relay.";
        }
        list dhcp-server-addresses {
          // NCS patched for predictable order
          ordered-by user;
          key "dhcp-server-address";
          description
            "A list of dhcp-servers.";
          leaf dhcp-server-address {
            type string;
            description
              "The address of a dhcp server.";
          }
          // NCS drop config false container state
        }
        leaf verify-dhcp-reply {
          type string;
          description
            "Verify validity of DHCP server reply.";
        }
        uses ncs_template_ip-interface;
        uses ncs_template_remote-id;
        uses ncs_template_circuit-id;
        uses ncs_template_option-82;
        // NCS drop config false container state
      }
    }
  }

  identity circuit-id-cid-string {
    base circuit-id-type;
    description
      "Set circuit-id-type to use an cid-string.";
  }

  identity circuit-id-interface-name {
    base circuit-id-type;
    description
      "Set circuit-id-type to use interface-name.";
  }

  identity circuit-id-type {
    description
      "Type for circuit-id-type.";
  }

  identity remote-id-rid-string {
    base remote-id-type;
    description
      "Set remote-id-type to use an rid-string.";
  }

  identity remote-id-device-mac-address {
    base remote-id-type;
    description
      "Set remote-id-type to use device-mac-address.";
  }

  identity remote-id-device-hostname {
    base remote-id-type;
    description
      "Set remote-id-type to use device-hostname.";
  }

  identity remote-id-type {
    description
      "Type for remote-id-type.";
  }

  identity option-82-replace {
    base option-82-setting;
    description
      "Set option-82 to replace.";
  }

  identity option-82-off {
    base option-82-setting;
    description
      "Turn off option-82.";
  }

  identity option-82-on {
    base option-82-setting;
    description
      "Turn on option-82.";
  }

  identity option-82-setting {
    description
      "Settings for option-82.";
  }
}
