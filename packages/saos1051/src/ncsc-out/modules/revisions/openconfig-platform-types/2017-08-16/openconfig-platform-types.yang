module openconfig-platform-types {
  // Generated by yanger -t ncs
  tailf:mount-id "saos1051-nc-1.0:saos1051-nc-1.0";
  tailf:ncs-device-type "netconf";

  yang-version 1;
  namespace "http://openconfig.net/yang/platform-types";
  prefix oc-platform-types;

  import openconfig-extensions {
    prefix oc-ext;
  }
  import tailf-common {
    prefix tailf;
  }
  import tailf-ncs {
    prefix ncs;
  }

  organization
    "OpenConfig working group";
  contact
    "OpenConfig working group
     www.openconfig.net";
  description
    "This module defines data types (e.g., YANG identities)
     to support the OpenConfig component inventory model.";
  oc-ext:openconfig-version "0.6.0";

  revision 2017-08-16 {
    description
      "Added power state enumerated type";
    reference "0.6.0";
  }
  revision 2016-12-22 {
    description
      "Added temperature state variable to component";
    reference "0.5.0";
  }

  typedef ncs_template_component-power-type {
    type string;
    description
      "A generic type reflecting whether a hardware component
       is powered on or off";
  }

  typedef ncs_rpc_notif_component-power-type {
    type enumeration {
      enum "POWER_ENABLED" {
        description
          "Enable power on the component";
      }
      enum "POWER_DISABLED" {
        description
          "Disable power on the component";
      }
    }
    description
      "A generic type reflecting whether a hardware component
       is powered on or off";
  }

  typedef live_ncs_component-power-type {
    type enumeration {
      enum "POWER_ENABLED" {
        description
          "Enable power on the component";
      }
      enum "POWER_DISABLED" {
        description
          "Disable power on the component";
      }
    }
    description
      "A generic type reflecting whether a hardware component
       is powered on or off";
  }

  typedef component-power-type {
    type enumeration {
      enum "POWER_ENABLED" {
        description
          "Enable power on the component";
      }
      enum "POWER_DISABLED" {
        description
          "Disable power on the component";
      }
    }
    description
      "A generic type reflecting whether a hardware component
       is powered on or off";
  }

  grouping ncs_template_avg-min-max-instant-stats-precision1-celsius {
    description
      "Common grouping for recording temperature values in
       Celsius with 1 decimal precision. Values include the
       instantaneous, average, minimum, and maximum statistics";
    leaf instant {
      type string;
      units "celsius";
      description
        "The instantaneous value of the statistic.";
    }
    leaf avg {
      type string;
      units "celsius";
      description
        "The arithmetic mean value of the statistic over the
         sampling period.";
    }
    leaf min {
      type string;
      units "celsius";
      description
        "The minimum value of the statistic over the sampling
         period";
    }
    leaf max {
      type string;
      units "celsius";
      description
        "The maximum value of the statistic over the sampling
         period";
    }
  }

  grouping ncs_rpc_notif_avg-min-max-instant-stats-precision1-celsius {
    description
      "Common grouping for recording temperature values in
       Celsius with 1 decimal precision. Values include the
       instantaneous, average, minimum, and maximum statistics";
    leaf instant {
      type decimal64 {
        fraction-digits 1;
      }
      units "celsius";
      description
        "The instantaneous value of the statistic.";
    }
    leaf avg {
      type decimal64 {
        fraction-digits 1;
      }
      units "celsius";
      description
        "The arithmetic mean value of the statistic over the
         sampling period.";
    }
    leaf min {
      type decimal64 {
        fraction-digits 1;
      }
      units "celsius";
      description
        "The minimum value of the statistic over the sampling
         period";
    }
    leaf max {
      type decimal64 {
        fraction-digits 1;
      }
      units "celsius";
      description
        "The maximum value of the statistic over the sampling
         period";
    }
  }

  grouping live_ncs_avg-min-max-instant-stats-precision1-celsius {
    description
      "Common grouping for recording temperature values in
       Celsius with 1 decimal precision. Values include the
       instantaneous, average, minimum, and maximum statistics";
    leaf instant {
      type decimal64 {
        fraction-digits 1;
      }
      units "celsius";
      description
        "The instantaneous value of the statistic.";
    }
    leaf avg {
      type decimal64 {
        fraction-digits 1;
      }
      units "celsius";
      description
        "The arithmetic mean value of the statistic over the
         sampling period.";
    }
    leaf min {
      type decimal64 {
        fraction-digits 1;
      }
      units "celsius";
      description
        "The minimum value of the statistic over the sampling
         period";
    }
    leaf max {
      type decimal64 {
        fraction-digits 1;
      }
      units "celsius";
      description
        "The maximum value of the statistic over the sampling
         period";
    }
  }

  grouping avg-min-max-instant-stats-precision1-celsius {
    description
      "Common grouping for recording temperature values in
       Celsius with 1 decimal precision. Values include the
       instantaneous, average, minimum, and maximum statistics";
    leaf instant {
      type decimal64 {
        fraction-digits 1;
      }
      units "celsius";
      description
        "The instantaneous value of the statistic.";
    }
    leaf avg {
      type decimal64 {
        fraction-digits 1;
      }
      units "celsius";
      description
        "The arithmetic mean value of the statistic over the
         sampling period.";
    }
    leaf min {
      type decimal64 {
        fraction-digits 1;
      }
      units "celsius";
      description
        "The minimum value of the statistic over the sampling
         period";
    }
    leaf max {
      type decimal64 {
        fraction-digits 1;
      }
      units "celsius";
      description
        "The maximum value of the statistic over the sampling
         period";
    }
  }

  identity OPERATING_SYSTEM {
    base OPENCONFIG_SOFTWARE_COMPONENT;
    description
      "Operating system running on a component";
  }

  identity CPU {
    base OPENCONFIG_HARDWARE_COMPONENT;
    description
      "Processing unit, e.g., a management processor";
  }

  identity TRANSCEIVER {
    base OPENCONFIG_HARDWARE_COMPONENT;
    description
      "Pluggable module present in a port";
  }

  identity PORT {
    base OPENCONFIG_HARDWARE_COMPONENT;
    description
      "Physical port, e.g., for attaching pluggables and networking
       cables";
  }

  identity LINECARD {
    base OPENCONFIG_HARDWARE_COMPONENT;
    description
      "Linecard component, typically inserted into a chassis slot";
  }

  identity MODULE {
    base OPENCONFIG_HARDWARE_COMPONENT;
    description
      "Replaceable hardware module, e.g., a daughtercard";
  }

  identity SENSOR {
    base OPENCONFIG_HARDWARE_COMPONENT;
    description
      "Physical sensor, e.g., a temperature sensor in a chassis";
  }

  identity FAN {
    base OPENCONFIG_HARDWARE_COMPONENT;
    description
      "Cooling fan, or could be some other heat-reduction component";
  }

  identity POWER_SUPPLY {
    base OPENCONFIG_HARDWARE_COMPONENT;
    description
      "Component that is supplying power to the device";
  }

  identity BACKPLANE {
    base OPENCONFIG_HARDWARE_COMPONENT;
    description
      "Backplane component for aggregating traffic, typically
       contained in a chassis component";
  }

  identity CHASSIS {
    base OPENCONFIG_HARDWARE_COMPONENT;
    description
      "Chassis component, typically with multiple slots / shelves";
  }

  identity OPENCONFIG_SOFTWARE_COMPONENT {
    description
      "Base identity for software-related components in a managed
       device";
  }

  identity OPENCONFIG_HARDWARE_COMPONENT {
    description
      "Base identity for hardware related components in a managed
       device.  Derived identities are partially based on contents
       of the IANA Entity MIB.";
    reference "IANA Entity MIB and RFC 6933";
  }
}
