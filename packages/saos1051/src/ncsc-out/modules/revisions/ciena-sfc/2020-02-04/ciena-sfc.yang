module ciena-sfc {
  // Generated by yanger -t ncs
  tailf:mount-id "saos1051-nc-1.0:saos1051-nc-1.0";
  tailf:ncs-device-type "netconf";

  namespace "urn:ciena:params:xml:ns:yang:ciena-pn::ciena-sfc";
  prefix sfc;

  import ciena-mef-classifier {
    prefix classifier;
  }
  import ciena-mef-fp {
    prefix fp;
  }
  import ciena-mef-logical-port {
    prefix mef-logical-port;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines data for management of service function chaining";

  revision 2020-02-04 {
    description
      "Updated description field";
  }
  revision 2019-04-05 {
    description
      "Add tx statistics for Service function forwarder interface
       Add rpc sff-clear-statistics to clear sffs statistics";
  }
  revision 2016-07-28 {
    description
      "1.0";
  }

  augment "/ncs:devices/ncs:device/ncs:rpc" {
    container rpc-sff-clear-statistics {
      tailf:ncs-device-type "netconf";
      tailf:display-when "not(../../ncs:module) or ../../ncs:module[ncs:name='ciena-sfc']";
      tailf:action sff-clear-statistics {
        tailf:actionpoint ncsproxy {
          tailf:internal;
        }
        description
          "RPC command to clear sffs statistics";
        input {
          choice clear-scope {
            case instance {
              leaf sff {
                type string;
                description
                  "Name of sff";
              }
              leaf sff-interface {
                mandatory true;
                type string;
                description
                  "Name of sff-interface";
              }
            }
            case all {
              leaf all {
                type empty;
              }
              description
                "Clear all sff-interface stats";
            }
          }
        }
        output {
          leaf status {
            type string;
            description
              "Status of the clear stats operation";
          }
        }
      }
    }
  }
  augment "/ncs:devices/ncs:device-group/ncs:ned-id/ncs:rpc" {
    container rpc-sff-clear-statistics {
      tailf:ncs-device-type "netconf";
      tailf:display-when "/ncs:devices/ncs:device[ncs:name=current()/../../../ncs:member]/ncs:module[ncs:name='ciena-sfc']";
      tailf:action sff-clear-statistics {
        tailf:actionpoint ncsproxy {
          tailf:internal;
        }
        description
          "RPC command to clear sffs statistics";
        input {
          choice clear-scope {
            case instance {
              leaf sff {
                type string;
                description
                  "Name of sff";
              }
              leaf sff-interface {
                mandatory true;
                type string;
                description
                  "Name of sff-interface";
              }
            }
            case all {
              leaf all {
                type empty;
              }
              description
                "Clear all sff-interface stats";
            }
          }
        }
        output {
          container "device" {
            leaf "name" {
              type string;
            }
            leaf "info" {
              type string;
            }
            container "result" {
              leaf status {
                type string;
                description
                  "Status of the clear stats operation";
              }
            }
          }
        }
      }
    }
  }
  augment "/ncs:devices/ncs:device/ncs:config" {
    container sffs {
      tailf:ncs-device-type "netconf";
      tailf:display-when "not(../../ncs:module) or ../../ncs:module[ncs:name='ciena-sfc']";
      description
        "Service function forwarder (sff) is responsible for delivering
         traffic from network to a connected service function (SF) or from
         a SF to another SF";
      list sff {
        key "sff-name";
        description
          "List of all sff and its configuration";
        leaf sff-name {
          type string;
          description
            "Name of sff";
        }
        leaf sff-mode {
          type enumeration {
            enum "vpls" {
              description
                "Virtual private LAN service";
            }
            enum "vpws" {
              description
                "Virtual private wired service";
            }
          }
          description
            "Sff mode";
          default "vpws";
        }
        list interface {
          key "name";
          description
            "List of interface that are part of this sff";
          leaf name {
            type string;
            description
              "String used to identify a interface";
          }
          leaf logical-port {
            type mef-logical-port:logical-port-ref;
            mandatory true;
            description
              "Text string that is used to identify a logical port";
          }
          leaf-list classifier-list {
            type classifier:classifier-ref;
            description
              "List of classifiers";
          }
          leaf stats-enabled {
            type boolean;
            default "false";
            description
              "Enable statistics collection on this interface in the hardware";
          }
          list ingress-transform {
            key "ingress-name";
            leaf ingress-name {
              type string;
              description
                "Name of ingress transform";
            }
            description
              "List of ingress transforms";
            uses fp:transform;
          }
          list egress-transform {
            key "egress-name";
            leaf egress-name {
              type string;
              description
                "Name of egress transform";
            }
            description
              "List of egress transforms";
            uses fp:transform;
          }
          // NCS drop config false container statistics
        }
      }
    }
  }
  augment "/ncs:devices/ncs:device/ncs:live-status" {
    container sffs {
      tailf:ncs-device-type "netconf";
      tailf:display-when "not(../../ncs:module) or ../../ncs:module[ncs:name='ciena-sfc'] or (../../ncs:live-status-protocol[not(ncs:capability)]) or (../../ncs:live-status-protocol/ncs:capability/ncs:module[.='ciena-sfc'])";
      description
        "Service function forwarder (sff) is responsible for delivering
         traffic from network to a connected service function (SF) or from
         a SF to another SF";
      list sff {
        key "sff-name";
        description
          "List of all sff and its configuration";
        leaf sff-name {
          type string;
          description
            "Name of sff";
        }
        leaf sff-mode {
          type enumeration {
            enum "vpls" {
              description
                "Virtual private LAN service";
            }
            enum "vpws" {
              description
                "Virtual private wired service";
            }
          }
          description
            "Sff mode";
          // NCS drop default statement
        }
        list interface {
          key "name";
          description
            "List of interface that are part of this sff";
          leaf name {
            type string;
            description
              "String used to identify a interface";
          }
          leaf logical-port {
            type mef-logical-port:live_ncs_logical-port-ref;
            // NCS drop mandatory statement
            description
              "Text string that is used to identify a logical port";
          }
          leaf-list classifier-list {
            type classifier:live_ncs_classifier-ref;
            description
              "List of classifiers";
          }
          leaf stats-enabled {
            type boolean;
            // NCS drop default statement
            description
              "Enable statistics collection on this interface in the hardware";
          }
          list ingress-transform {
            key "ingress-name";
            leaf ingress-name {
              type string;
              description
                "Name of ingress transform";
            }
            description
              "List of ingress transforms";
            uses fp:live_ncs_transform;
          }
          list egress-transform {
            key "egress-name";
            leaf egress-name {
              type string;
              description
                "Name of egress transform";
            }
            description
              "List of egress transforms";
            uses fp:live_ncs_transform;
          }
          container statistics {
            description
              "A collection of SFF interface related statistics objects.";
            leaf rxBytes {
              type uint64;
              description
                "Ingress byte count";
            }
            leaf rxPkts {
              type uint64;
              description
                "Ingress packet count";
            }
            leaf droppedBytes {
              type uint64;
              description
                "Ingress dropped byte count";
            }
            leaf txBytes {
              type uint64;
              description
                "Egress byte count";
            }
            leaf txPkts {
              type uint64;
              description
                "Egress packet count";
            }
          }
        }
      }
    }
  }
  augment "/ncs:devices/ncs:template/ncs:ned-id/ncs:config" {
    container sffs {
      description
        "Service function forwarder (sff) is responsible for delivering
         traffic from network to a connected service function (SF) or from
         a SF to another SF";
      list sff {
        // NCS patched for predictable order
        ordered-by user;
        key "sff-name";
        description
          "List of all sff and its configuration";
        leaf sff-name {
          type string;
          description
            "Name of sff";
        }
        leaf sff-mode {
          type string;
          description
            "Sff mode";
          // NCS drop default statement
        }
        list interface {
          // NCS patched for predictable order
          ordered-by user;
          key "name";
          description
            "List of interface that are part of this sff";
          leaf name {
            type string;
            description
              "String used to identify a interface";
          }
          leaf logical-port {
            type mef-logical-port:ncs_template_logical-port-ref;
            // NCS drop mandatory statement
            description
              "Text string that is used to identify a logical port";
          }
          leaf-list classifier-list {
            // NCS patched for predictable order
            ordered-by user;
            type classifier:ncs_template_classifier-ref;
            description
              "List of classifiers";
          }
          leaf stats-enabled {
            type string;
            // NCS drop default statement
            description
              "Enable statistics collection on this interface in the hardware";
          }
          list ingress-transform {
            // NCS patched for predictable order
            ordered-by user;
            key "ingress-name";
            leaf ingress-name {
              type string;
              description
                "Name of ingress transform";
            }
            description
              "List of ingress transforms";
            uses fp:ncs_template_transform;
          }
          list egress-transform {
            // NCS patched for predictable order
            ordered-by user;
            key "egress-name";
            leaf egress-name {
              type string;
              description
                "Name of egress transform";
            }
            description
              "List of egress transforms";
            uses fp:ncs_template_transform;
          }
          // NCS drop config false container statistics
        }
      }
    }
  }
}
