module yang-attributes {
  // Generated by yanger -t ncs
  tailf:mount-id "saos1051-nc-1.0:saos1051-nc-1.0";
  tailf:ncs-device-type "netconf";

  yang-version 1;
  namespace "urn:ietf:params:xml:ns:yang:1";
  prefix y;

  import yuma-ncx {
    prefix ncx;
  }
  import tailf-common {
    prefix tailf;
  }
  import tailf-ncs {
    prefix ncs;
  }

  organization
    "YumaWorks, Inc.";
  contact
    "Support <support at yumaworks.com>";
  description
    "YANG language XML attribute definitions in YANG format.
     Used for internal parsing.

     Copyright (c) 2013 - 2016 YumaWorks, Inc. All rights reserved.

     Redistribution and use in source and binary forms, with or
     without modification, is permitted pursuant to, and subject
     to the license terms contained in, the BSD 3-Clause License
     http://opensource.org/licenses/BSD-3-Clause";

  revision 2016-01-06 {
    description
      "Add YANG 1.1 action rpc.";
  }
  revision 2013-02-18 {
    description
      "Initial version";
  }

  augment "/ncs:devices/ncs:device/ncs:rpc" {
    container rpc-action {
      tailf:ncs-device-type "netconf";
      tailf:display-when "not(../../ncs:module) or ../../ncs:module[ncs:name='yang-attributes']";
      tailf:action action {
        tailf:actionpoint ncsproxy {
          tailf:internal;
        }
        ncx:hidden;
        description
          "YANG 1.1 action.  This node is specially parsed.
           It does not follow any YANG-supportable schema.

           The action container should have 1 subtree starting
           with a top-level data node.  There should be 1 subtree
           that matches an action-stmt definition.";
      }
    }
  }
  augment "/ncs:devices/ncs:device-group/ncs:ned-id/ncs:rpc" {
    container rpc-action {
      tailf:ncs-device-type "netconf";
      tailf:display-when "/ncs:devices/ncs:device[ncs:name=current()/../../../ncs:member]/ncs:module[ncs:name='yang-attributes']";
      tailf:action action {
        tailf:actionpoint ncsproxy {
          tailf:internal;
        }
        ncx:hidden;
        description
          "YANG 1.1 action.  This node is specially parsed.
           It does not follow any YANG-supportable schema.

           The action container should have 1 subtree starting
           with a top-level data node.  There should be 1 subtree
           that matches an action-stmt definition.";
      }
    }
  }
  augment "/ncs:devices/ncs:device/ncs:config" {
    leaf insert {
      tailf:ncs-device-type "netconf";
      tailf:display-when "not(../../ncs:module) or ../../ncs:module[ncs:name='yang-attributes']";
      ncx:abstract;
      ncx:hidden;
      type enumeration {
        enum "first";
        enum "last";
        enum "before";
        enum "after";
      }
      default "last";
      description
        "YANG insert attribute";
      reference "RFC 6020, sec. 7.8.6";
    }
    leaf key {
      tailf:ncs-device-type "netconf";
      tailf:display-when "not(../../ncs:module) or ../../ncs:module[ncs:name='yang-attributes']";
      ncx:abstract;
      ncx:hidden;
      type string;
      description
        "YANG key attribute";
      reference "RFC 6020, sec. 7.8.6";
    }
    leaf value {
      tailf:ncs-device-type "netconf";
      tailf:display-when "not(../../ncs:module) or ../../ncs:module[ncs:name='yang-attributes']";
      ncx:abstract;
      ncx:hidden;
      type string;
      description
        "YANG value attribute";
      reference "RFC 6020, sec. 7.7.7";
    }
  }
  augment "/ncs:devices/ncs:device/ncs:live-status" {
    leaf insert {
      tailf:ncs-device-type "netconf";
      tailf:display-when "not(../../ncs:module) or ../../ncs:module[ncs:name='yang-attributes'] or (../../ncs:live-status-protocol[not(ncs:capability)]) or (../../ncs:live-status-protocol/ncs:capability/ncs:module[.='yang-attributes'])";
      ncx:abstract;
      ncx:hidden;
      type enumeration {
        enum "first";
        enum "last";
        enum "before";
        enum "after";
      }
      // NCS drop default statement
      description
        "YANG insert attribute";
      reference "RFC 6020, sec. 7.8.6";
    }
    leaf key {
      tailf:ncs-device-type "netconf";
      tailf:display-when "not(../../ncs:module) or ../../ncs:module[ncs:name='yang-attributes'] or (../../ncs:live-status-protocol[not(ncs:capability)]) or (../../ncs:live-status-protocol/ncs:capability/ncs:module[.='yang-attributes'])";
      ncx:abstract;
      ncx:hidden;
      type string;
      description
        "YANG key attribute";
      reference "RFC 6020, sec. 7.8.6";
    }
    leaf value {
      tailf:ncs-device-type "netconf";
      tailf:display-when "not(../../ncs:module) or ../../ncs:module[ncs:name='yang-attributes'] or (../../ncs:live-status-protocol[not(ncs:capability)]) or (../../ncs:live-status-protocol/ncs:capability/ncs:module[.='yang-attributes'])";
      ncx:abstract;
      ncx:hidden;
      type string;
      description
        "YANG value attribute";
      reference "RFC 6020, sec. 7.7.7";
    }
  }
  augment "/ncs:devices/ncs:template/ncs:ned-id/ncs:config" {
    leaf insert {
      ncx:abstract;
      ncx:hidden;
      type string;
      // NCS drop default statement
      description
        "YANG insert attribute";
      reference "RFC 6020, sec. 7.8.6";
    }
    leaf key {
      ncx:abstract;
      ncx:hidden;
      type string;
      description
        "YANG key attribute";
      reference "RFC 6020, sec. 7.8.6";
    }
    leaf value {
      ncx:abstract;
      ncx:hidden;
      type string;
      description
        "YANG value attribute";
      reference "RFC 6020, sec. 7.7.7";
    }
  }
}
