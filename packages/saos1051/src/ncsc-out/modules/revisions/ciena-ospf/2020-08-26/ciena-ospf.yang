module ciena-ospf {
  // Generated by yanger -t ncs
  tailf:mount-id "saos1051-nc-1.0:saos1051-nc-1.0";
  tailf:ncs-device-type "netconf";

  namespace "http://ciena.com/ns/yang/ciena-ospf";
  prefix ospf;

  import ietf-inet-types {
    prefix inet;
  }
  import yuma-ncx {
    prefix ncx;
  }
  import openconfig-interfaces {
    prefix oc-if;
  }
  import ciena-routing-policy {
    prefix rt-pol;
  }
  import ciena-bfd-types {
    prefix bfd-types;
  }
  import ietf-routing-types {
    prefix rt-types;
  }
  import ciena-l3-types {
    prefix cn-l3-types;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's IPv4 Open Shortest Path First (ospf) protocol

     Copyright (c) 2019  Ciena Corporation.  All rights
     reserved.

     All information contained herein is, and remains the
     property of Ciena Corporation. Dissemination of this
     information or reproduction of this material is strictly
     forbidden unless prior written permission is obtained
     from Ciena Corporation.";

  revision 2020-08-26 {
    description
      "Added neighbour state change notification.
       Added OSPF instance state change notification.
       Added OSPF micro-loop avoidance state parameters";
  }
  revision 2020-02-06 {
    description
      "Including OSPF LDP FRR, TI-LFA, SR extensions
       Added changes for OSPF Virtual link feture
       Added changes for OSPF ldp igp sync operation data
       Updated OSPF LSDB Hierarchy
       Added changes for OSPF ldp igp sync operation data.
       Added Changes for Ospf Virtual link feture.
       Including OSPF LDP FRR, TI-LFA, SR extensions.
       Incorporating Route Map support into OSPF.
       Added OSPF micro-loop avoidance parameters.";
  }
  revision 2019-10-08 {
    description
      "Initial version of ciena-ospf config, state and rpc yang model";
  }

  grouping ncs_template_instance-config {
    description
      "OSPF instance config state.";
    leaf router-id {
      // NCS drop if-feature statement
      type rt-types:ncs_template_router-id;
      description
        "Defined in RFC 2328. A 32-bit number
         that uniquely identifies the router.";
    }
    leaf spf-min-delay {
      type string;
      // NCS drop default statement
      units "milliseconds";
      description
        "The minimum SPF delay time in milliseconds: 500 milliseconds.";
    }
    leaf spf-max-delay {
      type string;
      // NCS drop default statement
      units "milliseconds";
      description
        "The maximum SPF hold delay time in milliseconds: 50000
         milliseconds (50 seconds)";
    }
    leaf admin-distance {
      type string;
      description
        "OSPF administrative distance";
    }
    list redistribute {
      // NCS patched for predictable order
      ordered-by user;
      key "protocol";
      description
        "redistribute routes to external process";
      leaf protocol {
        type cn-l3-types:ncs_template_ospf-route-source;
        description
          "Redistibute protocol name";
      }
      leaf metric-type {
        type cn-l3-types:ncs_template_ospf-metric-type;
        description
          "Metric type";
      }
      leaf metric {
        type string;
        // NCS drop default statement
        description
          "Metric value";
      }
      leaf policy {
        type string;
        description
          "Name of the routemap to apply the filter to.";
      }
    }
    container fast-reroute {
      description
        "Configurations for OSPF LFA fast reroute";
      container lfa {
        leaf per-prefix-enable {
          type string;
          // NCS drop default statement
          description
            "Enables/disables LFA FRR";
        }
      }
    }
  }

  grouping ncs_template_interface-common-config {
    description
      "Common configuration for all types of interfaces,
       including virtual links and sham links.";
    leaf hello-interval {
      type string;
      units "seconds";
      // NCS drop default statement
      description
        "Interval between hello packets (seconds). It must
         be the same for all routers on the same network.
         Different networks, implementations, and deployments
         will use different hello-intervals. A sample value
         for a LAN network would be 10 seconds.";
      reference "RFC 2328: OSPF Version 2, Appendix C.3";
    }
    leaf dead-interval {
      type string;
      units "seconds";
      // NCS drop must statement
      // NCS drop default statement
      description
        "Interval after which a neighbor is declared down
         (seconds) if hello packets are not received. It is

         typically 3 or 4 times the hello-interval. A typical
         value for LAN networks is 40 seconds.";
      reference "RFC 2328: OSPF Version 2, Appendix C.3";
    }
    leaf retransmit-interval {
      type string;
      units "seconds";
      // NCS drop default statement
      description
        "Interval between retransmitting unacknowledged Link
         State Advertisements (LSAs) (seconds). This should
         be well over the round-trip transmit delay for
         any two routers on the network. A sample value
         would be 5 seconds.";
      reference "RFC 2328: OSPF Version 2, Appendix C.3";
    }
    leaf transmit-delay {
      type string;
      units "seconds";
      // NCS drop default statement
      description
        "Estimated time needed to transmit Link State Update
         (LSU) packets on the interface (seconds). LSAs have
         their age incremented by this amount when advertised
         on the interface. A sample value would be 1 second.";
      reference "RFC 2328: OSPF Version 2, Appendix C.3";
    }
    leaf disable {
      type string;
      // NCS drop default statement
      description
        "Disable OSPF protocol on the interface.";
    }
    leaf metric {
      type cn-l3-types:ncs_template_ospf-link-metric;
      description
        "Interface cost.";
    }
    leaf lfa-candidate-enable {
      type string;
      description
        "Enable/disable the interface from being used as the next hop in a repair path";
      // NCS drop default statement
    }
    container ldp-igp-sync {
      presence "Configures LDP/IGP Sync parameters";
      description
        "Enables IGP/LDP synchronization";
      leaf hold-down {
        type cn-l3-types:ncs_template_ldp-igp-sync-holddown;
        // NCS drop mandatory statement
        description
          "Hold-down timer for the OSPF ldp-igp synchronization configuration 
            range: [1-69999]/none/infinite";
      }
    }
  }

  grouping ncs_template_interface-config {
    description
      "Configuration for real interfaces.";
    leaf type {
      type string;
      // NCS drop default statement
      description
        "Interface type.";
    }
    leaf passive {
      type string;
      // NCS drop default statement
      description
        "Enable/Disable passive interface - a passive interface's
         prefix will be advertised but no neighbor adjacencies
         will be formed on the interface.";
    }
    list authentication {
      // NCS patched for predictable order
      ordered-by user;
      key "id";
      // NCS drop max-elements statement
      description
        "OSPF message-digest-key (MD5) related operations";
      leaf id {
        type string;
        description
          "Key ID";
      }
      leaf password {
        type string;
        // NCS drop mandatory statement
        ncx:password;
        description
          "MD5 Authentiation key (password)";
      }
    }
    leaf priority {
      type string;
      // NCS drop default statement
      description
        "Configure OSPF router priority. On multi-access network
         this value is for Designated Router (DR) election. The
         priority is ignored on other interface types. A router
         with a higher priority will be preferred in the election
         and a value of 0 indicates the router is not eligible to
         become Designated Router or Backup Designated Router
         (BDR).";
    }
    container bfd {
      // NCS drop if-feature statement
      description
        "BFD Client Configuration.";
      uses bfd-types:ncs_template_client-cfg-parms;
      reference
        "RFC YYYY: YANG Data Model for Bidirectional
         Forwarding Detection (BFD). Please replace YYYY with
         published RFC number for draft-ietf-bfd-yang.";
    }
    leaf mtu {
      type string;
      description
        "Set the ospf packet MTU size. By default, ospf uses the
         interface MTU size";
    }
    uses ncs_template_interface-common-config;
  }

  grouping ncs_template_srlr {
    description
      "Grouping for SR label range configuration.";
    leaf lower-bound {
      type string;
      description
        "Lower value in the block.";
    }
    leaf upper-bound {
      type string;
      description
        "Upper value in the block.";
    }
  }

  grouping ncs_template_srgb-cfg {
    description
      "Grouping for SR global block configuration";
    list srgb {
      // NCS patched for predictable order
      ordered-by user;
      key "lower-bound upper-bound";
      // NCS drop max-elements statement
      description
        "List of global blocks to be advertised.";
      uses ncs_template_srlr;
    }
  }

  grouping ncs_template_area-common-config {
    container fast-reroute {
      description
        "Configurations for OSPF remote LFA fast reroute";
      container remote-lfa {
        leaf enable {
          type string;
          // NCS drop default statement
          description
            "Enables/disables remote LFA FRR. Must be enabled with instance-level LFA configuration.";
        }
        leaf tunnel-cost {
          type string;
          // NCS drop default statement
          description
            "Maximum cost of the repair tunnel.";
        }
        list protection {
          // NCS patched for predictable order
          ordered-by user;
          key "protection-type";
          description
            "Protection provided to the repair tunnel";
          leaf protection-type {
            type cn-l3-types:ncs_template_ospf-rlfa-protection-type;
            description
              "The protection type";
          }
          leaf enable {
            type string;
            // NCS drop default statement
            description
              "Enable/disable the protection type";
          }
        }
      }
      container ti-lfa {
        leaf enable {
          type string;
          // NCS drop default statement
          description
            "Enables/disables TI-LFA FRR, Must be enabled with instance-level LFA configuration";
        }
      }
    }
  }

  grouping ncs_template_neighbors-state-grouping {
    leaf area-id {
      type string;
      description
        "Area ID";
    }
    list neighbor-state {
      // NCS patched for predictable order
      ordered-by user;
      key "router-id";
      description
        "OSPF neighbor state";
      leaf router-id {
        type rt-types:ncs_template_router-id;
        description
          "Neighbor router ID";
      }
      leaf state-type {
        type string;
        description
          "Neighbor state type";
      }
      leaf neighbor-event-count {
        type string;
        description
          "The number of times this neighbor has changed
           state or an error has occurred. Discontinuities in the
           value of this counter can occur when the OSPF neighbor
           is re-initialized.";
      }
      leaf neighbor-retrans-qlen {
        type string;
        description
          "The current length of the retransmission queue.";
      }
      leaf lsdb-count {
        type string;
        description
          "Link state Database Count";
      }
      leaf ls-request-count {
        type string;
        description
          "Link State request count";
      }
      leaf ls-retransmit-count {
        type string;
        description
          "Link State retransmission count";
      }
      leaf neighbor-up-time {
        type string;
        description
          "The length of time in seconds the neighbor has been in
           the full adjacency state";
      }
      leaf dr-router-id {
        type rt-types:ncs_template_router-id;
        description
          "Neighbor's Designated Router (DR) Router ID.";
      }
      leaf bdr-router-id {
        type rt-types:ncs_template_router-id;
        description
          "The Backup Designated Router (BDR) Router ID.";
      }
      leaf dead-timer {
        type string;
        description
          "This timer tracks the remaining time before
           the neighbor is declared dead.";
      }
      leaf priority {
        type string;
        description
          "Configured OSPF router priority. On multi-access network
           this value is for Designated Router (DR) election. The
           priority is ignored on other interface types. A router
           with a higher priority will be preferred in the election
           and a value of 0 indicates the router is not eligible to
           become Designated Router or Backup Designated Router
           (BDR).";
      }
    }
  }

  grouping ncs_template_pdu-statistics-grouping {
    leaf total-sent {
      type string;
      description
        "Total number of packets sent.";
    }
    leaf total-received {
      type string;
      description
        "Total number of packets received.";
    }
    leaf hello-sent {
      type string;
      description
        "Hello's sent.";
    }
    leaf hello-received {
      type string;
      description
        "Hello's received.";
    }
    leaf dd-sent {
      type string;
      description
        "Total number of database description packets sent.";
    }
    leaf dd-received {
      type string;
      description
        "Total number of database description packets received.";
    }
    leaf ls-request-sent {
      type string;
      description
        "Total number of LS requests sent.";
    }
    leaf ls-request-received {
      type string;
      description
        "Total number of LS requests received.";
    }
    leaf ls-update-sent {
      type string;
      description
        "Total number of LS updates sent.";
    }
    leaf ls-update-received {
      type string;
      description
        "Total number of LS updates received.";
    }
    leaf ls-ack-sent {
      type string;
      description
        "Total number of LS acknowledgements sent.";
    }
    leaf ls-ack-received {
      type string;
      description
        "Total number of LS acknowledgements received.";
    }
    leaf error-packet-tx-count {
      type string;
      description
        "Number of packets not transmitted due to error.";
    }
    leaf error-packet-rx-count {
      type string;
      description
        "Number of incoming packets with error.";
    }
  }

  grouping ncs_template_interface-state-grouping {
    list interface-state {
      // NCS patched for predictable order
      ordered-by user;
      key "name";
      description
        "OSPF interface related operations";
      leaf name {
        type string;
        description
          "Interface name";
      }
      leaf state {
        type cn-l3-types:ncs_template_ospf-intf-state-type;
        description
          "Interface state";
      }
      leaf events {
        type string;
        description
          "The number of times this interface has changed its
           state or an error has occurred. Discontinuities in the
           value of this counter can occur when the OSPF interface
           is re-initialized.";
      }
      leaf lsa-count {
        type string;
        description
          "The number of link-scope LSAs";
      }
      leaf lsa-cksum-sum {
        type string;
        description
          "The modulo 2**32 sum of the LSA checksums
           for link-scope LSAs. The value should be treated as
           unsigned when comparing two sums of checksums. While
           differing checksums indicate a different combination
           of LSAs, equivalent checksums don't guarantee that the
           LSAs are the same given that multiple combinations of
           LSAs can result in the same checksum.";
      }
      leaf dr-router-id {
        type rt-types:ncs_template_router-id;
        description
          "Neighbor's Designated Router (DR) Router ID.";
      }
      leaf dr-ip-addr {
        type string;
        description
          "The Designated Router (DR) IP address.";
      }
      leaf bdr-router-id {
        type rt-types:ncs_template_router-id;
        description
          "The Backup Designated Router (BDR) Router ID.";
      }
      leaf ldp-igp-sync-status {
        type string;
        description
          "Status of ldp-igp-sync (Configured or Not Configured).";
      }
      leaf remaining-hold-down-time {
        type string;
        units "milliseconds";
        description
          "Time in milliseconds before LDP notifies OSPF to advertise original cost.";
      }
      leaf bdr-ip-addr {
        type string;
        description
          "The Backup Designated Router (BDR) IP Address.";
      }
      uses ncs_template_pdu-statistics-grouping;
      uses ncs_template_neighbors-state-grouping;
    }
  }

  grouping ncs_template_ospf-route-grouping {
    // NCS drop config false list 'route-state'
  }

  grouping ncs_template_lsdb-area-summary-grouping {
    // NCS drop config false list 'lsdb-area-entry-summary'
  }

  grouping ncs_template_lsdb-instance-summary-grouping {
    // NCS drop config false list 'lsdb-instance-entry-summary'
  }

  grouping ncs_template_lsa-header {
    description
      "Common LSA for OSPFv2 and OSPFv3";
    leaf lsa-type {
      type cn-l3-types:ncs_template_ospf-lsa-type;
      description
        "LSA type";
    }
    leaf lsa-id {
      type string;
      description
        "Link-State ID.";
    }
    leaf adv-router {
      type rt-types:ncs_template_router-id;
      description
        "LSA advertising router.";
    }
    leaf ls-age {
      type string;
      description
        "LSA age.";
    }
    leaf seq-num {
      type string;
      description
        "LSA sequence number.";
    }
    leaf checksum {
      type string;
      description
        "LSA checksum.";
    }
  }

  grouping ncs_template_lsa-header-detail {
    leaf length {
      type string;
      description
        "LSA length including the header.";
    }
    leaf options {
      type string;
      description
        "The Options field enables OSPF routers to support
         (or not support) optional capabilities, and to
         communicate their capability level to other OSPF routers";
    }
  }

  grouping ncs_template_lsdb-area-detail-grouping {
    // NCS drop config false list 'lsdb-area-entry-detail'
  }

  grouping ncs_template_prefix-sid-sub-tlvs {
    description
      "Prefix Segment ID (SID) sub-TLVs.";
    container prefix-sid-sub-tlvs {
      description
        "Prefix SID sub-TLV.";
      list prefix-sid-sub-tlv {
        // NCS patched for predictable order
        ordered-by user;
        description
          "Prefix SID sub-TLV.";
        key "sid";
        leaf sid {
          type string;
          description
            "An index or label.";
        }
        leaf flags {
          type string;
          description
            "Prefix SID Segment Identifier (SID) Flags.

             NP-Flag:  No-PHP (Penultimate Hop Popping) Flag.  If set,
                       then the penultimate hop MUST NOT pop the Prefix-SID
                       before delivering packets to the node that advertised the
                       Prefix-SID.

             M-Flag:  Mapping Server Flag.  If set, the SID was
                      advertised by an SR Mapping Server as described in
                      [RFC8661].

             E-Flag:  Explicit Null Flag.  If set, any upstream neighbor
                      of the Prefix-SID originator MUST replace the Prefix-SID
                      with the Explicit NULL label (0 for IPv4) before
                      forwarding the packet.

             V-Flag:  Value/Index Flag.  If set, then the Prefix-SID
                      carries an absolute value.  If not set, then the Prefix-
                      SID carries an index.

             L-Flag:  Local/Global Flag.  If set, then the value/index
                      carried by the Prefix-SID has local significance.  If not
                      set, then the value/index carried by this sub-TLV has
                      global significance.";
        }
        leaf mt-id {
          type string;
          description
            "Multi-topology ID.";
        }
        leaf algorithm {
          type string;
          description
            "The algorithm associated with the prefix-SID.";
        }
      }
    }
  }

  grouping ncs_template_sr-algorithm-tlv {
    description
      "SR algorithm TLV grouping.";
    container sr-algorithm-tlv {
      description
        "All SR algorithm TLVs.";
      leaf-list sr-algorithm {
        // NCS patched for predictable order
        ordered-by user;
        type string;
        description
          "The Segment Routing (SR) algorithms that the router is
           currently using.";
      }
    }
  }

  grouping ncs_template_sid-range-tlvs {
    description
      "SID Range TLV grouping.";
    container sid-range-tlvs {
      description
        "List of SID range TLVs.";
      list sid-range-tlv {
        // NCS patched for predictable order
        ordered-by user;
        description
          "SID range TLV.";
        key "index";
        leaf index {
          type string;
          description
            "The SID Range Index";
        }
        leaf range-size {
          type string;
          description
            "The SID range.";
        }
        uses ncs_template_sid-sub-tlv;
      }
    }
  }

  grouping ncs_template_ospfv2-router-link {
    description
      "OSPFv2 router link.";
    leaf link-id {
      type string;
      description
        "Router-LSA Link ID";
    }
    leaf link-data {
      type string;
      description
        "Router-LSA Link data.";
    }
    leaf type {
      type cn-l3-types:ncs_template_ospf-router-link-type;
      description
        "Router-LSA Link type.";
    }
  }

  grouping ncs_template_summary-lsa {
    description
      "Summary LSA";
    leaf network-mask {
      type string;
      description
        "The IP address mask for the network";
    }
    leaf metric {
      type string;
      description
        "Metric";
    }
  }

  grouping ncs_template_lsdb-instance-detail-grouping {
    // NCS drop config false list 'lsdb-instance-entry-detail'
  }

  grouping ncs_template_segment-routing-state-grouping {
    description
      "Grouping of OSPF SR state elements.";
    // NCS drop config false leaf state
    list sr-capability {
      // NCS patched for predictable order
      ordered-by user;
      key "router-ip";
      description
        "List of SR-Capability Info";
      leaf router-ip {
        type string;
        description
          "Router IP.";
      }
      leaf total-sid {
        type string;
        description
          "Total SIDs supported";
      }
      leaf sid-range-list-count {
        type string;
        description
          "SID range list count";
      }
      list sid-range {
        // NCS patched for predictable order
        ordered-by user;
        key "index";
        description
          "List of Ranges";
        leaf index {
          type string;
          description
            "SID range index for indexing";
        }
        leaf start {
          type string;
          description
            "SID range start";
        }
        leaf end {
          type string;
          description
            "SID range end";
        }
      }
      leaf algorithm {
        type string;
        description
          "SR algorithm";
      }
    }
  }

  grouping ncs_template_microloop-avoidance-state-grouping {
    description
      "Grouping of OSPF microloop state elements.";
    leaf enable {
      type string;
      description
        "Microloop state enabled/disabled";
    }
    leaf rib-update-delay {
      type string;
      units "milliseconds";
      description
        "Microloop rib-update-delay timer total configured value";
    }
    leaf running-state {
      type string;
      description
        "Microloop rib-update-delay running state";
    }
    leaf pending-rib-update-delay {
      type string;
      units "milliseconds";
      description
        "Microloop rib-update-delay timer remaining value";
    }
  }

  grouping ncs_template_sid-sub-tlv {
    description
      "SID/Label sub-TLV grouping.";
    container sid-sub-tlv {
      description
        "Used to advertise the SID/Label associated with a prefix or adjacency.";
      leaf sid {
        type string;
        description
          "Segment Identifier (SID) - A 20 bit label or 32 bit SID.";
      }
    }
  }

  grouping ncs_template_ospf-instance-state-grouping {
    leaf up-time {
      type string;
      description
        "The length of time in seconds the protocol instance has been
         in the up state";
    }
    leaf lsa-count {
      type string;
      description
        "External Link State Advertisement count";
    }
    leaf lsa-cksum-sum {
      type string;
      description
        "External LSA checksum";
    }
    leaf originate-new-lsa-count {
      type string;
      description
        "Number of self-originating LSAs";
    }
    leaf rx-new-lsas-count {
      type string;
      description
        "Number of new LSAs received";
    }
    leaf area-count {
      type string;
      description
        "Number of areas in the OSPF instance";
    }
    leaf instance-creation-time {
      type string;
      description
        "OSPF Statistics Up Time";
    }
    leaf router-id-change-count {
      type string;
      description
        "The number of times the router ID was modified";
    }
    leaf dr-election-counter {
      type string;
      description
        "Number of DR elections";
    }
    leaf neighbor-expiration-count {
      type string;
      description
        "Number of expired neighbors";
    }
    leaf neighbor-bad-ls-reqs-count {
      type string;
      description
        "Number of bad LS Requests received";
    }
    leaf neighbor-seq-num-mismatch-count {
      type string;
      description
        "Number of packets received from neighbors with mismatched
         sequence number";
    }
    leaf router-id {
      type rt-types:ncs_template_router-id;
      description
        "The router identifier";
    }
    uses ncs_template_pdu-statistics-grouping;
  }

  grouping ncs_template_virtual-link-state-grouping {
    list virtual-link-state {
      // NCS patched for predictable order
      ordered-by user;
      key "name";
      description
        "Grouping of virtual link parameters";
      leaf name {
        type string;
        description
          "Virtual link identifier, unique name assigned for the virtual link";
      }
      leaf vlink-state {
        type cn-l3-types:ncs_template_ospf-vlink-state-type;
        description
          "Virtual link state";
      }
      leaf vlink-router-id {
        type rt-types:ncs_template_router-id;
        description
          "Router ID of remote device.";
      }
      leaf vlink-transit-area {
        type string;
        description
          "The transit area address of virtual link.";
      }
      leaf vlink-interface-name {
        type string;
        description
          "Interface name from where Virtual link is connected";
      }
      leaf vlink-local-addr {
        type string;
        description
          "The address of local node.";
      }
      leaf vlink-remote-addr {
        type string;
        description
          "The address of remote node.";
      }
      leaf vlink-hello-due {
        type string;
        description
          "This is to get the timer that tracks the remaining time before
           the neighbor is declared dead (in seconds).";
      }
      leaf vlink-hello-timer {
        type string;
        description
          "This is to get the configured vlink hello timer (in seconds)";
      }
      leaf vlink-dead-timer {
        type string;
        units "seconds";
        description
          "This is to get the vlink dead timer (in seconds)";
      }
      leaf vlink-transmit-timer {
        type string;
        units "seconds";
        description
          "This is to get the vlink transmit timer (in seconds)";
      }
      leaf vlink-retransmit-timer {
        type string;
        units "seconds";
        description
          "This is to get the vlink retransmit timer (in seconds)";
      }
    }
  }

  grouping ncs_template_notification-instance-hdr {
    description
      "This grouping describes common instance specific,
       data for OSPF notifications.";
    leaf instance-tag {
      type string;
      description
        "OSPF instance ID";
    }
  }

  grouping ncs_template_notification-interface {
    description
      "This grouping provides interface information,
       for the OSPF interface specific notification.";
    leaf interface {
      type string;
      description
        "OSPF interface name.";
    }
    leaf if-link-type {
      type cn-l3-types:ncs_template_ospf-network-type;
      description
        "Link type of OSPF interface.";
    }
  }

  grouping ncs_template_notification-neighbor {
    description
      "This grouping provides the neighbor information,
       for neighbor specific notifications.";
    leaf neighbor-router-id {
      // NCS drop if-feature statement
      type rt-types:ncs_template_router-id;
      description
        "Neighbor router ID.";
    }
    leaf neighbor-ip-addr {
      type string;
      description
        "Neighbor address.";
    }
  }

  grouping ncs_rpc_notif_instance-config {
    description
      "OSPF instance config state.";
    leaf router-id {
      tailf:display-when "not(../ncs:module) or boolean(/ncs:devices/ncs:device[ncs:name=current()/../ncs:name]/capability/feature='router-id')";
      type rt-types:ncs_rpc_notif_router-id;
      description
        "Defined in RFC 2328. A 32-bit number
         that uniquely identifies the router.";
    }
    leaf spf-min-delay {
      type uint32 {
        range "1..600000";
      }
      default "500";
      units "milliseconds";
      description
        "The minimum SPF delay time in milliseconds: 500 milliseconds.";
    }
    leaf spf-max-delay {
      type uint32 {
        range "1..600000";
      }
      default "5000";
      units "milliseconds";
      description
        "The maximum SPF hold delay time in milliseconds: 50000
         milliseconds (50 seconds)";
    }
    leaf admin-distance {
      type uint32 {
        range "1..255";
      }
      description
        "OSPF administrative distance";
    }
    list redistribute {
      key "protocol";
      description
        "redistribute routes to external process";
      leaf protocol {
        type cn-l3-types:ncs_rpc_notif_ospf-route-source;
        description
          "Redistibute protocol name";
      }
      leaf metric-type {
        type cn-l3-types:ncs_rpc_notif_ospf-metric-type;
        description
          "Metric type";
      }
      leaf metric {
        type uint32 {
          range "0..16777214";
        }
        default "20";
        description
          "Metric value";
      }
      leaf policy {
        type string;
        description
          "Name of the routemap to apply the filter to.";
      }
    }
    container fast-reroute {
      description
        "Configurations for OSPF LFA fast reroute";
      container lfa {
        leaf per-prefix-enable {
          type boolean;
          default "false";
          description
            "Enables/disables LFA FRR";
        }
      }
    }
  }

  grouping ncs_rpc_notif_interface-common-config {
    description
      "Common configuration for all types of interfaces,
       including virtual links and sham links.";
    leaf hello-interval {
      type uint16 {
        range "1..65535";
      }
      units "seconds";
      default "10";
      description
        "Interval between hello packets (seconds). It must
         be the same for all routers on the same network.
         Different networks, implementations, and deployments
         will use different hello-intervals. A sample value
         for a LAN network would be 10 seconds.";
      reference "RFC 2328: OSPF Version 2, Appendix C.3";
    }
    leaf dead-interval {
      type uint16 {
        range "1..65535";
      }
      units "seconds";
      must '../dead-interval > ../hello-interval' {
        tailf:xpath-root 3;
        error-message "The dead interval must be larger than the hello interval";
        description
          "The value must be greater than the 'hello-interval'.";
      }
      default "40";
      description
        "Interval after which a neighbor is declared down
         (seconds) if hello packets are not received. It is

         typically 3 or 4 times the hello-interval. A typical
         value for LAN networks is 40 seconds.";
      reference "RFC 2328: OSPF Version 2, Appendix C.3";
    }
    leaf retransmit-interval {
      type uint16 {
        range "1..1800";
      }
      units "seconds";
      default "5";
      description
        "Interval between retransmitting unacknowledged Link
         State Advertisements (LSAs) (seconds). This should
         be well over the round-trip transmit delay for
         any two routers on the network. A sample value
         would be 5 seconds.";
      reference "RFC 2328: OSPF Version 2, Appendix C.3";
    }
    leaf transmit-delay {
      type uint16 {
        range "1..3600";
      }
      units "seconds";
      default "1";
      description
        "Estimated time needed to transmit Link State Update
         (LSU) packets on the interface (seconds). LSAs have
         their age incremented by this amount when advertised
         on the interface. A sample value would be 1 second.";
      reference "RFC 2328: OSPF Version 2, Appendix C.3";
    }
    leaf disable {
      type boolean;
      default "false";
      description
        "Disable OSPF protocol on the interface.";
    }
    leaf metric {
      type cn-l3-types:ncs_rpc_notif_ospf-link-metric;
      description
        "Interface cost.";
    }
    leaf lfa-candidate-enable {
      type boolean;
      description
        "Enable/disable the interface from being used as the next hop in a repair path";
      default "true";
    }
    container ldp-igp-sync {
      presence "Configures LDP/IGP Sync parameters";
      description
        "Enables IGP/LDP synchronization";
      leaf hold-down {
        type cn-l3-types:ncs_rpc_notif_ldp-igp-sync-holddown;
        mandatory true;
        description
          "Hold-down timer for the OSPF ldp-igp synchronization configuration 
            range: [1-69999]/none/infinite";
      }
    }
  }

  grouping ncs_rpc_notif_interface-config {
    description
      "Configuration for real interfaces.";
    leaf type {
      type enumeration {
        enum "broadcast" {
          description
            "Specify OSPF broadcast multi-access network.";
        }
        enum "point-to-point" {
          description
            "Specify OSPF point-to-point network.";
        }
      }
      default "broadcast";
      description
        "Interface type.";
    }
    leaf passive {
      type boolean;
      default "false";
      description
        "Enable/Disable passive interface - a passive interface's
         prefix will be advertised but no neighbor adjacencies
         will be formed on the interface.";
    }
    list authentication {
      key "id";
      max-elements 1;
      description
        "OSPF message-digest-key (MD5) related operations";
      leaf id {
        type uint32 {
          range "1..255";
        }
        description
          "Key ID";
      }
      leaf password {
        type string {
          length "1..8";
        }
        mandatory true;
        ncx:password;
        description
          "MD5 Authentiation key (password)";
      }
    }
    leaf priority {
      type uint8 {
        range "0..255";
      }
      default "1";
      description
        "Configure OSPF router priority. On multi-access network
         this value is for Designated Router (DR) election. The
         priority is ignored on other interface types. A router
         with a higher priority will be preferred in the election
         and a value of 0 indicates the router is not eligible to
         become Designated Router or Backup Designated Router
         (BDR).";
    }
    container bfd {
      tailf:display-when "not(../ncs:module) or boolean(/ncs:devices/ncs:device[ncs:name=current()/../ncs:name]/capability/feature='bfd')";
      description
        "BFD Client Configuration.";
      uses bfd-types:ncs_rpc_notif_client-cfg-parms;
      reference
        "RFC YYYY: YANG Data Model for Bidirectional
         Forwarding Detection (BFD). Please replace YYYY with
         published RFC number for draft-ietf-bfd-yang.";
    }
    leaf mtu {
      type uint16 {
        range "576..65535";
      }
      description
        "Set the ospf packet MTU size. By default, ospf uses the
         interface MTU size";
    }
    uses ncs_rpc_notif_interface-common-config;
  }

  grouping ncs_rpc_notif_srlr {
    description
      "Grouping for SR label range configuration.";
    leaf lower-bound {
      type uint32 {
        range "16000..1048575";
      }
      description
        "Lower value in the block.";
    }
    leaf upper-bound {
      type uint32 {
        range "16000..1048575";
      }
      description
        "Upper value in the block.";
    }
  }

  grouping ncs_rpc_notif_srgb-cfg {
    description
      "Grouping for SR global block configuration";
    list srgb {
      key "lower-bound upper-bound";
      max-elements 1;
      ordered-by user;
      description
        "List of global blocks to be advertised.";
      uses ncs_rpc_notif_srlr;
    }
  }

  grouping ncs_rpc_notif_area-common-config {
    container fast-reroute {
      description
        "Configurations for OSPF remote LFA fast reroute";
      container remote-lfa {
        leaf enable {
          type boolean;
          default "false";
          description
            "Enables/disables remote LFA FRR. Must be enabled with instance-level LFA configuration.";
        }
        leaf tunnel-cost {
          type uint32 {
            range "1..16777214";
          }
          default "60";
          description
            "Maximum cost of the repair tunnel.";
        }
        list protection {
          key "protection-type";
          description
            "Protection provided to the repair tunnel";
          leaf protection-type {
            type cn-l3-types:ncs_rpc_notif_ospf-rlfa-protection-type;
            description
              "The protection type";
          }
          leaf enable {
            type boolean;
            default "false";
            description
              "Enable/disable the protection type";
          }
        }
      }
      container ti-lfa {
        leaf enable {
          type boolean;
          default "false";
          description
            "Enables/disables TI-LFA FRR, Must be enabled with instance-level LFA configuration";
        }
      }
    }
  }

  grouping ncs_rpc_notif_neighbors-state-grouping {
    leaf area-id {
      type yang:dotted-quad;
      description
        "Area ID";
    }
    list neighbor-state {
      key "router-id";
      description
        "OSPF neighbor state";
      leaf router-id {
        type rt-types:ncs_rpc_notif_router-id;
        description
          "Neighbor router ID";
      }
      leaf state-type {
        type string {
          length "0..255";
        }
        description
          "Neighbor state type";
      }
      leaf neighbor-event-count {
        type yang:counter32;
        description
          "The number of times this neighbor has changed
           state or an error has occurred. Discontinuities in the
           value of this counter can occur when the OSPF neighbor
           is re-initialized.";
      }
      leaf neighbor-retrans-qlen {
        type uint32;
        description
          "The current length of the retransmission queue.";
      }
      leaf lsdb-count {
        type yang:counter32;
        description
          "Link state Database Count";
      }
      leaf ls-request-count {
        type yang:counter32;
        description
          "Link State request count";
      }
      leaf ls-retransmit-count {
        type yang:counter32;
        description
          "Link State retransmission count";
      }
      leaf neighbor-up-time {
        type string {
          length "0..255";
        }
        description
          "The length of time in seconds the neighbor has been in
           the full adjacency state";
      }
      leaf dr-router-id {
        type rt-types:ncs_rpc_notif_router-id;
        description
          "Neighbor's Designated Router (DR) Router ID.";
      }
      leaf bdr-router-id {
        type rt-types:ncs_rpc_notif_router-id;
        description
          "The Backup Designated Router (BDR) Router ID.";
      }
      leaf dead-timer {
        type string {
          length "0..255";
        }
        description
          "This timer tracks the remaining time before
           the neighbor is declared dead.";
      }
      leaf priority {
        type uint32;
        description
          "Configured OSPF router priority. On multi-access network
           this value is for Designated Router (DR) election. The
           priority is ignored on other interface types. A router
           with a higher priority will be preferred in the election
           and a value of 0 indicates the router is not eligible to
           become Designated Router or Backup Designated Router
           (BDR).";
      }
    }
  }

  grouping ncs_rpc_notif_pdu-statistics-grouping {
    leaf total-sent {
      type uint32;
      description
        "Total number of packets sent.";
    }
    leaf total-received {
      type uint32;
      description
        "Total number of packets received.";
    }
    leaf hello-sent {
      type uint32;
      description
        "Hello's sent.";
    }
    leaf hello-received {
      type uint32;
      description
        "Hello's received.";
    }
    leaf dd-sent {
      type uint32;
      description
        "Total number of database description packets sent.";
    }
    leaf dd-received {
      type uint32;
      description
        "Total number of database description packets received.";
    }
    leaf ls-request-sent {
      type uint32;
      description
        "Total number of LS requests sent.";
    }
    leaf ls-request-received {
      type uint32;
      description
        "Total number of LS requests received.";
    }
    leaf ls-update-sent {
      type uint32;
      description
        "Total number of LS updates sent.";
    }
    leaf ls-update-received {
      type uint32;
      description
        "Total number of LS updates received.";
    }
    leaf ls-ack-sent {
      type uint32;
      description
        "Total number of LS acknowledgements sent.";
    }
    leaf ls-ack-received {
      type uint32;
      description
        "Total number of LS acknowledgements received.";
    }
    leaf error-packet-tx-count {
      type uint32;
      description
        "Number of packets not transmitted due to error.";
    }
    leaf error-packet-rx-count {
      type uint32;
      description
        "Number of incoming packets with error.";
    }
  }

  grouping ncs_rpc_notif_interface-state-grouping {
    list interface-state {
      key "name";
      description
        "OSPF interface related operations";
      leaf name {
        type string {
          length "0..255";
        }
        description
          "Interface name";
      }
      leaf state {
        type cn-l3-types:ncs_rpc_notif_ospf-intf-state-type;
        description
          "Interface state";
      }
      leaf events {
        type uint32;
        description
          "The number of times this interface has changed its
           state or an error has occurred. Discontinuities in the
           value of this counter can occur when the OSPF interface
           is re-initialized.";
      }
      leaf lsa-count {
        type yang:counter32;
        description
          "The number of link-scope LSAs";
      }
      leaf lsa-cksum-sum {
        type uint32;
        description
          "The modulo 2**32 sum of the LSA checksums
           for link-scope LSAs. The value should be treated as
           unsigned when comparing two sums of checksums. While
           differing checksums indicate a different combination
           of LSAs, equivalent checksums don't guarantee that the
           LSAs are the same given that multiple combinations of
           LSAs can result in the same checksum.";
      }
      leaf dr-router-id {
        type rt-types:ncs_rpc_notif_router-id;
        description
          "Neighbor's Designated Router (DR) Router ID.";
      }
      leaf dr-ip-addr {
        type inet:ip-address;
        description
          "The Designated Router (DR) IP address.";
      }
      leaf bdr-router-id {
        type rt-types:ncs_rpc_notif_router-id;
        description
          "The Backup Designated Router (BDR) Router ID.";
      }
      leaf ldp-igp-sync-status {
        type string;
        description
          "Status of ldp-igp-sync (Configured or Not Configured).";
      }
      leaf remaining-hold-down-time {
        type uint32;
        units "milliseconds";
        description
          "Time in milliseconds before LDP notifies OSPF to advertise original cost.";
      }
      leaf bdr-ip-addr {
        type inet:ip-address;
        description
          "The Backup Designated Router (BDR) IP Address.";
      }
      uses ncs_rpc_notif_pdu-statistics-grouping;
      uses ncs_rpc_notif_neighbors-state-grouping;
    }
  }

  grouping ncs_rpc_notif_ospf-route-grouping {
    list route-state {
      key "prefix";
      config false;
      description
        "OSPF IPv4 route-table";
      leaf prefix {
        type inet:ipv4-prefix;
        description
          "Destination prefix of the route";
      }
      leaf type {
        type string;
        description
          "Path type attribute";
      }
      list next-hop {
        key "neighbor-ip-addr";
        config false;
        description
          "OSPF IPv4 route next hop";
        leaf neighbor-ip-addr {
          type inet:ipv4-address;
          description
            "IP address of the neighbor";
        }
        leaf outgoing-interface {
          type string;
          description
            "Name of the outgoing interface";
        }
        leaf area-id {
          type yang:dotted-quad;
          description
            "Area Id in quad-dotted notation";
        }
        leaf area-transit {
          type boolean;
          description
            "Transit area";
        }
        leaf path-cost {
          type uint32;
          description
            "Path cost of the route";
        }
        leaf ext-type-cost {
          type uint32;
          description
            "Path cost of the External route";
        }
      }
    }
  }

  grouping ncs_rpc_notif_lsdb-area-summary-grouping {
    list lsdb-area-entry-summary {
      key "lsa-type lsa-id adv-router";
      config false;
      description
        "Summary of LSAs in Area Level LSDB ";
      uses ncs_rpc_notif_lsa-header;
      leaf do-not-age {
        type boolean;
        description
          "If true, LSA shall not be removed from the LSDB";
      }
      leaf link-count {
        type uint32;
        description
          "The number of attached links";
      }
    }
  }

  grouping ncs_rpc_notif_lsdb-instance-summary-grouping {
    list lsdb-instance-entry-summary {
      key "lsa-type lsa-id adv-router";
      config false;
      description
        "Summary of LSAs in Instance Level LSDB";
      uses ncs_rpc_notif_lsa-header;
      leaf do-not-age {
        type boolean;
        description
          "If true, LSA shall not be removed from the LSDB";
      }
      leaf link-count {
        type uint32;
        description
          "The number of attached links";
      }
    }
  }

  grouping ncs_rpc_notif_lsa-header {
    description
      "Common LSA for OSPFv2 and OSPFv3";
    leaf lsa-type {
      type cn-l3-types:ncs_rpc_notif_ospf-lsa-type;
      description
        "LSA type";
    }
    leaf lsa-id {
      type yang:dotted-quad;
      description
        "Link-State ID.";
    }
    leaf adv-router {
      type rt-types:ncs_rpc_notif_router-id;
      description
        "LSA advertising router.";
    }
    leaf ls-age {
      type uint16;
      description
        "LSA age.";
    }
    leaf seq-num {
      type uint32;
      description
        "LSA sequence number.";
    }
    leaf checksum {
      type string;
      description
        "LSA checksum.";
    }
  }

  grouping ncs_rpc_notif_lsa-header-detail {
    leaf length {
      type uint16;
      description
        "LSA length including the header.";
    }
    leaf options {
      type string;
      description
        "The Options field enables OSPF routers to support
         (or not support) optional capabilities, and to
         communicate their capability level to other OSPF routers";
    }
  }

  grouping ncs_rpc_notif_lsdb-area-detail-grouping {
    list lsdb-area-entry-detail {
      key "lsa-type lsa-id adv-router";
      config false;
      description
        "List OSPF LSAs.";
      uses ncs_rpc_notif_lsa-header;
      uses ncs_rpc_notif_lsa-header-detail;
      container opaque-lsa {
        leaf opaque-type {
          type uint8;
          description
            "Opaque type.";
        }
        leaf opaque-id {
          type uint32;
          description
            "Opaque ID.";
        }
        container extended-prefix-opaque {
          description
            "All extended prefix TLVs in the LSA.";
          list extended-prefix-tlv {
            key "prefix";
            description
              "Extended prefix TLV.";
            leaf prefix {
              type inet:ipv4-prefix;
              description
                "Address prefix.";
            }
            leaf route-type {
              type cn-l3-types:ncs_rpc_notif_ospf-route-type;
              description
                "Route type.";
            }
            leaf flags {
              type string;
              description
                "Extended prefix TLV flags list. This list will
                 contain identities for the prefix flags that
                 are set in the extended prefix flags.

                 A: Attach Flag. Set when Area Border Router (ABR)
                    generating an OSPFv2 Extended Prefix TLV for an inter-area
                    prefix that is locally connected or attached in another
                    connected area.

                 N: Node Flag. Set when the prefix identifies the advertising router,
                    i.e., the prefix is a host prefix advertising a globally reachable
                    address typically associated with a loopback address. The advertising
                    router MAY choose to not set this flag even when the above conditions are met.";
            }
            uses ncs_rpc_notif_prefix-sid-sub-tlvs;
          }
        }
        container extended-link-opaque {
          description
            "All extended link TLVs in the LSA.";
          list extended-link-tlv {
            key "link-id";
            description
              "Extended link TLV.";
            uses ncs_rpc_notif_ospfv2-router-link;
            container adj-sid-sub-tlvs {
              description
                "Adjacency SID optional sub-TLVs.";
              list adj-sid-sub-tlv {
                description
                  "List of Adjacency SID sub-TLVs.";
                key "sid";
                leaf sid {
                  type uint32;
                  description
                    "Segment Identifier (SID) index/label.";
                }
                leaf flags {
                  type string;
                  description
                    "Adj-sid sub-tlv flags.

                     B-Flag:  Backup Flag.  If set, the Adj-SID refers to an
                              adjacency that is eligible for protection (e.g., using IP
                              Fast Reroute or MPLS-FRR (MPLS-Fast Reroute) as described
                              in Section 2.1 of [RFC8402].

                     V-Flag:  Value/Index Flag.  If set, then the Adj-SID carries
                              an absolute value.  If not set, then the Adj-SID carries
                              an index.

                     L-Flag:  Local/Global Flag.  If set, then the value/index
                              carried by the Adj-SID has local significance.  If not
                              set, then the value/index carried by this sub-TLV has
                              global significance.

                     S-Flag.  Set Flag. When set, the S-Flag indicates that the Adj-SID
                              refers to a set of adjacencies (and therefore MAY be assigned
                              to other adjacencies as well).";
                }
                leaf mt-id {
                  type uint8;
                  description
                    "Multi-topology ID.";
                }
                leaf weight {
                  type uint8;
                  description
                    "Weight used for load-balancing.";
                }
              }
            }
            container lan-adj-sid-sub-tlvs {
              description
                "LAN Adjacency SID optional sub-TLVs.";
              list lan-adj-sid-sub-tlv {
                description
                  "List of LAN adjacency SID sub-TLVs.";
                key "sid";
                leaf sid {
                  type uint32;
                  description
                    "Segment Identifier (SID) index/label.";
                }
                leaf flags {
                  type string;
                  description
                    "LAN adj-sid sub-tlv flags.

                     B-Flag:  Backup Flag.  If set, the Lan-Adj-SID refers to an
                              adjacency that is eligible for protection (e.g., using IP
                              Fast Reroute or MPLS-FRR (MPLS-Fast Reroute) as described
                              in Section 2.1 of [RFC8402].

                     V-Flag:  Value/Index Flag.  If set, then the Lan-Adj-SID carries
                              an absolute value.  If not set, then the Lan-Adj-SID carries
                              an index.

                     L-Flag:  Local/Global Flag.  If set, then the value/index
                              carried by the Lan-Adj-SID has local significance.  If not
                              set, then the value/index carried by this sub-TLV has
                              global significance.

                     S-Flag.  Set Flag. When set, the S-Flag indicates that the Lan-Adj-SID
                              refers to a set of adjacencies (and therefore MAY be assigned
                              to other adjacencies as well).";
                }
                leaf mt-id {
                  type uint8;
                  description
                    "Multi-topology ID.";
                }
                leaf weight {
                  type uint8;
                  description
                    "Weight used for load-balancing.";
                }
                leaf neighbor-router-id {
                  type yang:dotted-quad;
                  description
                    "Neighbor router ID.";
                }
              }
            }
          }
        }
        container ri-opaque {
          description
            "OSPF Router Information (RI) opaque LSA.";
          reference "RFC 7770: OSPF Router Capabilities";
          uses ncs_rpc_notif_sr-algorithm-tlv;
          uses ncs_rpc_notif_sid-range-tlvs;
        }
      }
      container router-lsa {
        description
          "Router-LSAs are the Type 1 LSAs.
           The LSA describes the state and cost of the router's
           links (i.e., interfaces) to the area";
        leaf flags {
          type string;
          description
            "Router LSA bits list.
             bit V : If set, the router is an endpoint of one or
                     more virtual link.

             bit E : If set, the router is an AS Boundary Router (ASBR).

             bit B : If set, the router is an Area Border Router (ABR).";
        }
        leaf link-count {
          type uint16;
          description
            "The number of links in the router LSA";
        }
        list link {
          key "link-id";
          description
            "Router LSA link.";
          uses ncs_rpc_notif_ospfv2-router-link;
          leaf num-tos-metric {
            type uint8;
            description
              "The number of different TOS metrics given for this link";
          }
          leaf tos-0-metric {
            type uint16;
            description
              "The cost of using this router link.";
          }
        }
      }
      container network-lsa {
        description
          "Network-LSAs are the Type 2 LSAs.
           The LSA describes all routers attached to the
           network, including the Designated Router itself.";
        leaf network-mask {
          type inet:ipv4-address;
          description
            "The IP address mask for the network.";
        }
        leaf-list attached-router {
          type inet:ipv4-address;
          description
            "List of the routers attached to the network.";
        }
      }
      container summary-lsa {
        description
          "Summary-LSAs are the Type 3 LSAs.
           Type3 LSAs are used when the destination is an IP network.";
        uses ncs_rpc_notif_summary-lsa;
      }
      container asbr-summary-lsa {
        description
          "Asbr-summary LSAa are the Type 4 LSAs.
           Type 4 LSAs are used when the destination is an AS boundary router.";
        uses ncs_rpc_notif_summary-lsa;
      }
    }
  }

  grouping ncs_rpc_notif_prefix-sid-sub-tlvs {
    description
      "Prefix Segment ID (SID) sub-TLVs.";
    container prefix-sid-sub-tlvs {
      description
        "Prefix SID sub-TLV.";
      list prefix-sid-sub-tlv {
        description
          "Prefix SID sub-TLV.";
        key "sid";
        leaf sid {
          type uint32;
          description
            "An index or label.";
        }
        leaf flags {
          type string;
          description
            "Prefix SID Segment Identifier (SID) Flags.

             NP-Flag:  No-PHP (Penultimate Hop Popping) Flag.  If set,
                       then the penultimate hop MUST NOT pop the Prefix-SID
                       before delivering packets to the node that advertised the
                       Prefix-SID.

             M-Flag:  Mapping Server Flag.  If set, the SID was
                      advertised by an SR Mapping Server as described in
                      [RFC8661].

             E-Flag:  Explicit Null Flag.  If set, any upstream neighbor
                      of the Prefix-SID originator MUST replace the Prefix-SID
                      with the Explicit NULL label (0 for IPv4) before
                      forwarding the packet.

             V-Flag:  Value/Index Flag.  If set, then the Prefix-SID
                      carries an absolute value.  If not set, then the Prefix-
                      SID carries an index.

             L-Flag:  Local/Global Flag.  If set, then the value/index
                      carried by the Prefix-SID has local significance.  If not
                      set, then the value/index carried by this sub-TLV has
                      global significance.";
        }
        leaf mt-id {
          type uint8;
          description
            "Multi-topology ID.";
        }
        leaf algorithm {
          type uint8;
          description
            "The algorithm associated with the prefix-SID.";
        }
      }
    }
  }

  grouping ncs_rpc_notif_sr-algorithm-tlv {
    description
      "SR algorithm TLV grouping.";
    container sr-algorithm-tlv {
      description
        "All SR algorithm TLVs.";
      leaf-list sr-algorithm {
        type uint8;
        description
          "The Segment Routing (SR) algorithms that the router is
           currently using.";
      }
    }
  }

  grouping ncs_rpc_notif_sid-range-tlvs {
    description
      "SID Range TLV grouping.";
    container sid-range-tlvs {
      description
        "List of SID range TLVs.";
      list sid-range-tlv {
        description
          "SID range TLV.";
        key "index";
        leaf index {
          type uint32;
          description
            "The SID Range Index";
        }
        leaf range-size {
          type uint32;
          description
            "The SID range.";
        }
        uses ncs_rpc_notif_sid-sub-tlv;
      }
    }
  }

  grouping ncs_rpc_notif_ospfv2-router-link {
    description
      "OSPFv2 router link.";
    leaf link-id {
      type inet:ipv4-address;
      description
        "Router-LSA Link ID";
    }
    leaf link-data {
      type inet:ipv4-address;
      description
        "Router-LSA Link data.";
    }
    leaf type {
      type cn-l3-types:ncs_rpc_notif_ospf-router-link-type;
      description
        "Router-LSA Link type.";
    }
  }

  grouping ncs_rpc_notif_summary-lsa {
    description
      "Summary LSA";
    leaf network-mask {
      type inet:ipv4-address;
      description
        "The IP address mask for the network";
    }
    leaf metric {
      type uint32;
      description
        "Metric";
    }
  }

  grouping ncs_rpc_notif_lsdb-instance-detail-grouping {
    list lsdb-instance-entry-detail {
      key "lsa-type lsa-id adv-router";
      config false;
      description
        "List OSPF LSAs.";
      uses ncs_rpc_notif_lsa-header;
      uses ncs_rpc_notif_lsa-header-detail;
      container as-external-lsa {
        description
          "AS-external-LSAs are the Type 5 LSAs.";
        leaf network-mask {
          type inet:ipv4-address;
          description
            "IP Address mask.";
        }
        leaf metric-type {
          type cn-l3-types:ncs_rpc_notif_ospf-metric-type;
          description
            "Metric Type";
        }
        leaf metric {
          type uint32;
          description
            "Metric";
        }
        leaf forwarding-addr {
          type inet:ipv4-address;
          description
            "Forwarding IP Address";
        }
        leaf route-tag {
          type uint32;
          description
            "A 32-bit field attached to each external route";
        }
      }
    }
  }

  grouping ncs_rpc_notif_segment-routing-state-grouping {
    description
      "Grouping of OSPF SR state elements.";
    leaf state {
      type string;
      config false;
      description
        "SR state enabled/disabled";
    }
    list sr-capability {
      key "router-ip";
      description
        "List of SR-Capability Info";
      leaf router-ip {
        type inet:ipv4-address;
        description
          "Router IP.";
      }
      leaf total-sid {
        type uint32;
        description
          "Total SIDs supported";
      }
      leaf sid-range-list-count {
        type uint32;
        description
          "SID range list count";
      }
      list sid-range {
        key "index";
        description
          "List of Ranges";
        leaf index {
          type uint32;
          description
            "SID range index for indexing";
        }
        leaf start {
          type uint32;
          description
            "SID range start";
        }
        leaf end {
          type uint32;
          description
            "SID range end";
        }
      }
      leaf algorithm {
        type uint8;
        description
          "SR algorithm";
      }
    }
  }

  grouping ncs_rpc_notif_microloop-avoidance-state-grouping {
    description
      "Grouping of OSPF microloop state elements.";
    leaf enable {
      type boolean;
      description
        "Microloop state enabled/disabled";
    }
    leaf rib-update-delay {
      type uint32;
      units "milliseconds";
      description
        "Microloop rib-update-delay timer total configured value";
    }
    leaf running-state {
      type boolean;
      description
        "Microloop rib-update-delay running state";
    }
    leaf pending-rib-update-delay {
      type uint32;
      units "milliseconds";
      description
        "Microloop rib-update-delay timer remaining value";
    }
  }

  grouping ncs_rpc_notif_sid-sub-tlv {
    description
      "SID/Label sub-TLV grouping.";
    container sid-sub-tlv {
      description
        "Used to advertise the SID/Label associated with a prefix or adjacency.";
      leaf sid {
        type uint32;
        description
          "Segment Identifier (SID) - A 20 bit label or 32 bit SID.";
      }
    }
  }

  grouping ncs_rpc_notif_ospf-instance-state-grouping {
    leaf up-time {
      type string {
        length "0..255";
      }
      description
        "The length of time in seconds the protocol instance has been
         in the up state";
    }
    leaf lsa-count {
      type yang:counter32;
      description
        "External Link State Advertisement count";
    }
    leaf lsa-cksum-sum {
      type string {
        length "0..255";
      }
      description
        "External LSA checksum";
    }
    leaf originate-new-lsa-count {
      type yang:counter32;
      description
        "Number of self-originating LSAs";
    }
    leaf rx-new-lsas-count {
      type yang:counter32;
      description
        "Number of new LSAs received";
    }
    leaf area-count {
      type yang:counter32;
      description
        "Number of areas in the OSPF instance";
    }
    leaf instance-creation-time {
      type string {
        length "0..255";
      }
      description
        "OSPF Statistics Up Time";
    }
    leaf router-id-change-count {
      type yang:counter32;
      description
        "The number of times the router ID was modified";
    }
    leaf dr-election-counter {
      type yang:counter32;
      description
        "Number of DR elections";
    }
    leaf neighbor-expiration-count {
      type yang:counter32;
      description
        "Number of expired neighbors";
    }
    leaf neighbor-bad-ls-reqs-count {
      type yang:counter32;
      description
        "Number of bad LS Requests received";
    }
    leaf neighbor-seq-num-mismatch-count {
      type yang:counter32;
      description
        "Number of packets received from neighbors with mismatched
         sequence number";
    }
    leaf router-id {
      type rt-types:ncs_rpc_notif_router-id;
      description
        "The router identifier";
    }
    uses ncs_rpc_notif_pdu-statistics-grouping;
  }

  grouping ncs_rpc_notif_virtual-link-state-grouping {
    list virtual-link-state {
      key "name";
      description
        "Grouping of virtual link parameters";
      leaf name {
        type string {
          length "0..255";
        }
        description
          "Virtual link identifier, unique name assigned for the virtual link";
      }
      leaf vlink-state {
        type cn-l3-types:ncs_rpc_notif_ospf-vlink-state-type;
        description
          "Virtual link state";
      }
      leaf vlink-router-id {
        type rt-types:ncs_rpc_notif_router-id;
        description
          "Router ID of remote device.";
      }
      leaf vlink-transit-area {
        type inet:ip-address;
        description
          "The transit area address of virtual link.";
      }
      leaf vlink-interface-name {
        type string {
          length "0..255";
        }
        description
          "Interface name from where Virtual link is connected";
      }
      leaf vlink-local-addr {
        type inet:ip-address;
        description
          "The address of local node.";
      }
      leaf vlink-remote-addr {
        type inet:ip-address;
        description
          "The address of remote node.";
      }
      leaf vlink-hello-due {
        type string {
          length "0..255";
        }
        description
          "This is to get the timer that tracks the remaining time before
           the neighbor is declared dead (in seconds).";
      }
      leaf vlink-hello-timer {
        type uint32;
        description
          "This is to get the configured vlink hello timer (in seconds)";
      }
      leaf vlink-dead-timer {
        type uint32;
        units "seconds";
        description
          "This is to get the vlink dead timer (in seconds)";
      }
      leaf vlink-transmit-timer {
        type uint32;
        units "seconds";
        description
          "This is to get the vlink transmit timer (in seconds)";
      }
      leaf vlink-retransmit-timer {
        type uint32;
        units "seconds";
        description
          "This is to get the vlink retransmit timer (in seconds)";
      }
    }
  }

  grouping ncs_rpc_notif_notification-instance-hdr {
    description
      "This grouping describes common instance specific,
       data for OSPF notifications.";
    leaf instance-tag {
      type uint32 {
        range "0..65535";
      }
      description
        "OSPF instance ID";
    }
  }

  grouping ncs_rpc_notif_notification-interface {
    description
      "This grouping provides interface information,
       for the OSPF interface specific notification.";
    leaf interface {
      type string {
        length "0..255";
      }
      description
        "OSPF interface name.";
    }
    leaf if-link-type {
      type cn-l3-types:ncs_rpc_notif_ospf-network-type;
      description
        "Link type of OSPF interface.";
    }
  }

  grouping ncs_rpc_notif_notification-neighbor {
    description
      "This grouping provides the neighbor information,
       for neighbor specific notifications.";
    leaf neighbor-router-id {
      tailf:display-when "not(../ncs:module) or boolean(/ncs:devices/ncs:device[ncs:name=current()/../ncs:name]/capability/feature='router-id')";
      type rt-types:ncs_rpc_notif_router-id;
      description
        "Neighbor router ID.";
    }
    leaf neighbor-ip-addr {
      type inet:ip-address;
      description
        "Neighbor address.";
    }
  }

  grouping live_ncs_instance-config {
    description
      "OSPF instance config state.";
    leaf router-id {
      // NCS drop if-feature statement
      type rt-types:live_ncs_router-id;
      description
        "Defined in RFC 2328. A 32-bit number
         that uniquely identifies the router.";
    }
    leaf spf-min-delay {
      type uint32 {
        range "1..600000";
      }
      // NCS drop default statement
      units "milliseconds";
      description
        "The minimum SPF delay time in milliseconds: 500 milliseconds.";
    }
    leaf spf-max-delay {
      type uint32 {
        range "1..600000";
      }
      // NCS drop default statement
      units "milliseconds";
      description
        "The maximum SPF hold delay time in milliseconds: 50000
         milliseconds (50 seconds)";
    }
    leaf admin-distance {
      type uint32 {
        range "1..255";
      }
      description
        "OSPF administrative distance";
    }
    list redistribute {
      key "protocol";
      description
        "redistribute routes to external process";
      leaf protocol {
        type cn-l3-types:live_ncs_ospf-route-source;
        description
          "Redistibute protocol name";
      }
      leaf metric-type {
        type cn-l3-types:live_ncs_ospf-metric-type;
        description
          "Metric type";
      }
      leaf metric {
        type uint32 {
          range "0..16777214";
        }
        // NCS drop default statement
        description
          "Metric value";
      }
      leaf policy {
        type leafref {
          path "/ncs:devices/ncs:device/ncs:live-status/rt-pol:routing-policy/rt-pol:policies/rt-pol:policy/rt-pol:name" {
            tailf:xpath-root 3;
          }
        }
        description
          "Name of the routemap to apply the filter to.";
      }
    }
    container fast-reroute {
      description
        "Configurations for OSPF LFA fast reroute";
      container lfa {
        leaf per-prefix-enable {
          type boolean;
          // NCS drop default statement
          description
            "Enables/disables LFA FRR";
        }
      }
    }
  }

  grouping live_ncs_interface-common-config {
    description
      "Common configuration for all types of interfaces,
       including virtual links and sham links.";
    leaf hello-interval {
      type uint16 {
        range "1..65535";
      }
      units "seconds";
      // NCS drop default statement
      description
        "Interval between hello packets (seconds). It must
         be the same for all routers on the same network.
         Different networks, implementations, and deployments
         will use different hello-intervals. A sample value
         for a LAN network would be 10 seconds.";
      reference "RFC 2328: OSPF Version 2, Appendix C.3";
    }
    leaf dead-interval {
      type uint16 {
        range "1..65535";
      }
      units "seconds";
      // NCS drop must statement
      // NCS drop default statement
      description
        "Interval after which a neighbor is declared down
         (seconds) if hello packets are not received. It is

         typically 3 or 4 times the hello-interval. A typical
         value for LAN networks is 40 seconds.";
      reference "RFC 2328: OSPF Version 2, Appendix C.3";
    }
    leaf retransmit-interval {
      type uint16 {
        range "1..1800";
      }
      units "seconds";
      // NCS drop default statement
      description
        "Interval between retransmitting unacknowledged Link
         State Advertisements (LSAs) (seconds). This should
         be well over the round-trip transmit delay for
         any two routers on the network. A sample value
         would be 5 seconds.";
      reference "RFC 2328: OSPF Version 2, Appendix C.3";
    }
    leaf transmit-delay {
      type uint16 {
        range "1..3600";
      }
      units "seconds";
      // NCS drop default statement
      description
        "Estimated time needed to transmit Link State Update
         (LSU) packets on the interface (seconds). LSAs have
         their age incremented by this amount when advertised
         on the interface. A sample value would be 1 second.";
      reference "RFC 2328: OSPF Version 2, Appendix C.3";
    }
    leaf disable {
      type boolean;
      // NCS drop default statement
      description
        "Disable OSPF protocol on the interface.";
    }
    leaf metric {
      type cn-l3-types:live_ncs_ospf-link-metric;
      description
        "Interface cost.";
    }
    leaf lfa-candidate-enable {
      type boolean;
      description
        "Enable/disable the interface from being used as the next hop in a repair path";
      // NCS drop default statement
    }
    container ldp-igp-sync {
      presence "Configures LDP/IGP Sync parameters";
      description
        "Enables IGP/LDP synchronization";
      leaf hold-down {
        type cn-l3-types:live_ncs_ldp-igp-sync-holddown;
        // NCS drop mandatory statement
        description
          "Hold-down timer for the OSPF ldp-igp synchronization configuration 
            range: [1-69999]/none/infinite";
      }
    }
  }

  grouping live_ncs_interface-config {
    description
      "Configuration for real interfaces.";
    leaf type {
      type enumeration {
        enum "broadcast" {
          description
            "Specify OSPF broadcast multi-access network.";
        }
        enum "point-to-point" {
          description
            "Specify OSPF point-to-point network.";
        }
      }
      // NCS drop default statement
      description
        "Interface type.";
    }
    leaf passive {
      type boolean;
      // NCS drop default statement
      description
        "Enable/Disable passive interface - a passive interface's
         prefix will be advertised but no neighbor adjacencies
         will be formed on the interface.";
    }
    list authentication {
      key "id";
      // NCS drop max-elements statement
      description
        "OSPF message-digest-key (MD5) related operations";
      leaf id {
        type uint32 {
          range "1..255";
        }
        description
          "Key ID";
      }
      leaf password {
        type string {
          length "1..8";
        }
        // NCS drop mandatory statement
        ncx:password;
        description
          "MD5 Authentiation key (password)";
      }
    }
    leaf priority {
      type uint8 {
        range "0..255";
      }
      // NCS drop default statement
      description
        "Configure OSPF router priority. On multi-access network
         this value is for Designated Router (DR) election. The
         priority is ignored on other interface types. A router
         with a higher priority will be preferred in the election
         and a value of 0 indicates the router is not eligible to
         become Designated Router or Backup Designated Router
         (BDR).";
    }
    container bfd {
      // NCS drop if-feature statement
      description
        "BFD Client Configuration.";
      uses bfd-types:live_ncs_client-cfg-parms;
      reference
        "RFC YYYY: YANG Data Model for Bidirectional
         Forwarding Detection (BFD). Please replace YYYY with
         published RFC number for draft-ietf-bfd-yang.";
    }
    leaf mtu {
      type uint16 {
        range "576..65535";
      }
      description
        "Set the ospf packet MTU size. By default, ospf uses the
         interface MTU size";
    }
    uses live_ncs_interface-common-config;
  }

  grouping live_ncs_srlr {
    description
      "Grouping for SR label range configuration.";
    leaf lower-bound {
      type uint32 {
        range "16000..1048575";
      }
      description
        "Lower value in the block.";
    }
    leaf upper-bound {
      type uint32 {
        range "16000..1048575";
      }
      description
        "Upper value in the block.";
    }
  }

  grouping live_ncs_srgb-cfg {
    description
      "Grouping for SR global block configuration";
    list srgb {
      key "lower-bound upper-bound";
      // NCS drop max-elements statement
      ordered-by user;
      description
        "List of global blocks to be advertised.";
      uses live_ncs_srlr;
    }
  }

  grouping live_ncs_area-common-config {
    container fast-reroute {
      description
        "Configurations for OSPF remote LFA fast reroute";
      container remote-lfa {
        leaf enable {
          type boolean;
          // NCS drop default statement
          description
            "Enables/disables remote LFA FRR. Must be enabled with instance-level LFA configuration.";
        }
        leaf tunnel-cost {
          type uint32 {
            range "1..16777214";
          }
          // NCS drop default statement
          description
            "Maximum cost of the repair tunnel.";
        }
        list protection {
          key "protection-type";
          description
            "Protection provided to the repair tunnel";
          leaf protection-type {
            type cn-l3-types:live_ncs_ospf-rlfa-protection-type;
            description
              "The protection type";
          }
          leaf enable {
            type boolean;
            // NCS drop default statement
            description
              "Enable/disable the protection type";
          }
        }
      }
      container ti-lfa {
        leaf enable {
          type boolean;
          // NCS drop default statement
          description
            "Enables/disables TI-LFA FRR, Must be enabled with instance-level LFA configuration";
        }
      }
    }
  }

  grouping live_ncs_neighbors-state-grouping {
    leaf area-id {
      type yang:dotted-quad;
      description
        "Area ID";
    }
    list neighbor-state {
      key "router-id";
      description
        "OSPF neighbor state";
      leaf router-id {
        type rt-types:live_ncs_router-id;
        description
          "Neighbor router ID";
      }
      leaf state-type {
        type string {
          length "0..255";
        }
        description
          "Neighbor state type";
      }
      leaf neighbor-event-count {
        type yang:counter32;
        description
          "The number of times this neighbor has changed
           state or an error has occurred. Discontinuities in the
           value of this counter can occur when the OSPF neighbor
           is re-initialized.";
      }
      leaf neighbor-retrans-qlen {
        type uint32;
        description
          "The current length of the retransmission queue.";
      }
      leaf lsdb-count {
        type yang:counter32;
        description
          "Link state Database Count";
      }
      leaf ls-request-count {
        type yang:counter32;
        description
          "Link State request count";
      }
      leaf ls-retransmit-count {
        type yang:counter32;
        description
          "Link State retransmission count";
      }
      leaf neighbor-up-time {
        type string {
          length "0..255";
        }
        description
          "The length of time in seconds the neighbor has been in
           the full adjacency state";
      }
      leaf dr-router-id {
        type rt-types:live_ncs_router-id;
        description
          "Neighbor's Designated Router (DR) Router ID.";
      }
      leaf bdr-router-id {
        type rt-types:live_ncs_router-id;
        description
          "The Backup Designated Router (BDR) Router ID.";
      }
      leaf dead-timer {
        type string {
          length "0..255";
        }
        description
          "This timer tracks the remaining time before
           the neighbor is declared dead.";
      }
      leaf priority {
        type uint32;
        description
          "Configured OSPF router priority. On multi-access network
           this value is for Designated Router (DR) election. The
           priority is ignored on other interface types. A router
           with a higher priority will be preferred in the election
           and a value of 0 indicates the router is not eligible to
           become Designated Router or Backup Designated Router
           (BDR).";
      }
    }
  }

  grouping live_ncs_pdu-statistics-grouping {
    leaf total-sent {
      type uint32;
      description
        "Total number of packets sent.";
    }
    leaf total-received {
      type uint32;
      description
        "Total number of packets received.";
    }
    leaf hello-sent {
      type uint32;
      description
        "Hello's sent.";
    }
    leaf hello-received {
      type uint32;
      description
        "Hello's received.";
    }
    leaf dd-sent {
      type uint32;
      description
        "Total number of database description packets sent.";
    }
    leaf dd-received {
      type uint32;
      description
        "Total number of database description packets received.";
    }
    leaf ls-request-sent {
      type uint32;
      description
        "Total number of LS requests sent.";
    }
    leaf ls-request-received {
      type uint32;
      description
        "Total number of LS requests received.";
    }
    leaf ls-update-sent {
      type uint32;
      description
        "Total number of LS updates sent.";
    }
    leaf ls-update-received {
      type uint32;
      description
        "Total number of LS updates received.";
    }
    leaf ls-ack-sent {
      type uint32;
      description
        "Total number of LS acknowledgements sent.";
    }
    leaf ls-ack-received {
      type uint32;
      description
        "Total number of LS acknowledgements received.";
    }
    leaf error-packet-tx-count {
      type uint32;
      description
        "Number of packets not transmitted due to error.";
    }
    leaf error-packet-rx-count {
      type uint32;
      description
        "Number of incoming packets with error.";
    }
  }

  grouping live_ncs_interface-state-grouping {
    list interface-state {
      key "name";
      description
        "OSPF interface related operations";
      leaf name {
        type string {
          length "0..255";
        }
        description
          "Interface name";
      }
      leaf state {
        type cn-l3-types:live_ncs_ospf-intf-state-type;
        description
          "Interface state";
      }
      leaf events {
        type uint32;
        description
          "The number of times this interface has changed its
           state or an error has occurred. Discontinuities in the
           value of this counter can occur when the OSPF interface
           is re-initialized.";
      }
      leaf lsa-count {
        type yang:counter32;
        description
          "The number of link-scope LSAs";
      }
      leaf lsa-cksum-sum {
        type uint32;
        description
          "The modulo 2**32 sum of the LSA checksums
           for link-scope LSAs. The value should be treated as
           unsigned when comparing two sums of checksums. While
           differing checksums indicate a different combination
           of LSAs, equivalent checksums don't guarantee that the
           LSAs are the same given that multiple combinations of
           LSAs can result in the same checksum.";
      }
      leaf dr-router-id {
        type rt-types:live_ncs_router-id;
        description
          "Neighbor's Designated Router (DR) Router ID.";
      }
      leaf dr-ip-addr {
        type inet:ip-address;
        description
          "The Designated Router (DR) IP address.";
      }
      leaf bdr-router-id {
        type rt-types:live_ncs_router-id;
        description
          "The Backup Designated Router (BDR) Router ID.";
      }
      leaf ldp-igp-sync-status {
        type string;
        description
          "Status of ldp-igp-sync (Configured or Not Configured).";
      }
      leaf remaining-hold-down-time {
        type uint32;
        units "milliseconds";
        description
          "Time in milliseconds before LDP notifies OSPF to advertise original cost.";
      }
      leaf bdr-ip-addr {
        type inet:ip-address;
        description
          "The Backup Designated Router (BDR) IP Address.";
      }
      uses live_ncs_pdu-statistics-grouping;
      uses live_ncs_neighbors-state-grouping;
    }
  }

  grouping live_ncs_ospf-route-grouping {
    list route-state {
      key "prefix";
      description
        "OSPF IPv4 route-table";
      leaf prefix {
        type inet:ipv4-prefix;
        description
          "Destination prefix of the route";
      }
      leaf type {
        type string;
        description
          "Path type attribute";
      }
      list next-hop {
        key "neighbor-ip-addr";
        description
          "OSPF IPv4 route next hop";
        leaf neighbor-ip-addr {
          type inet:ipv4-address;
          description
            "IP address of the neighbor";
        }
        leaf outgoing-interface {
          type string;
          description
            "Name of the outgoing interface";
        }
        leaf area-id {
          type yang:dotted-quad;
          description
            "Area Id in quad-dotted notation";
        }
        leaf area-transit {
          type boolean;
          description
            "Transit area";
        }
        leaf path-cost {
          type uint32;
          description
            "Path cost of the route";
        }
        leaf ext-type-cost {
          type uint32;
          description
            "Path cost of the External route";
        }
      }
    }
  }

  grouping live_ncs_lsdb-area-summary-grouping {
    list lsdb-area-entry-summary {
      key "lsa-type lsa-id adv-router";
      description
        "Summary of LSAs in Area Level LSDB ";
      uses live_ncs_lsa-header;
      leaf do-not-age {
        type boolean;
        description
          "If true, LSA shall not be removed from the LSDB";
      }
      leaf link-count {
        type uint32;
        description
          "The number of attached links";
      }
    }
  }

  grouping live_ncs_lsdb-instance-summary-grouping {
    list lsdb-instance-entry-summary {
      key "lsa-type lsa-id adv-router";
      description
        "Summary of LSAs in Instance Level LSDB";
      uses live_ncs_lsa-header;
      leaf do-not-age {
        type boolean;
        description
          "If true, LSA shall not be removed from the LSDB";
      }
      leaf link-count {
        type uint32;
        description
          "The number of attached links";
      }
    }
  }

  grouping live_ncs_lsa-header {
    description
      "Common LSA for OSPFv2 and OSPFv3";
    leaf lsa-type {
      type cn-l3-types:live_ncs_ospf-lsa-type;
      description
        "LSA type";
    }
    leaf lsa-id {
      type yang:dotted-quad;
      description
        "Link-State ID.";
    }
    leaf adv-router {
      type rt-types:live_ncs_router-id;
      description
        "LSA advertising router.";
    }
    leaf ls-age {
      type uint16;
      description
        "LSA age.";
    }
    leaf seq-num {
      type uint32;
      description
        "LSA sequence number.";
    }
    leaf checksum {
      type string;
      description
        "LSA checksum.";
    }
  }

  grouping live_ncs_lsa-header-detail {
    leaf length {
      type uint16;
      description
        "LSA length including the header.";
    }
    leaf options {
      type string;
      description
        "The Options field enables OSPF routers to support
         (or not support) optional capabilities, and to
         communicate their capability level to other OSPF routers";
    }
  }

  grouping live_ncs_lsdb-area-detail-grouping {
    list lsdb-area-entry-detail {
      key "lsa-type lsa-id adv-router";
      description
        "List OSPF LSAs.";
      uses live_ncs_lsa-header;
      uses live_ncs_lsa-header-detail;
      container opaque-lsa {
        leaf opaque-type {
          type uint8;
          description
            "Opaque type.";
        }
        leaf opaque-id {
          type uint32;
          description
            "Opaque ID.";
        }
        container extended-prefix-opaque {
          description
            "All extended prefix TLVs in the LSA.";
          list extended-prefix-tlv {
            key "prefix";
            description
              "Extended prefix TLV.";
            leaf prefix {
              type inet:ipv4-prefix;
              description
                "Address prefix.";
            }
            leaf route-type {
              type cn-l3-types:live_ncs_ospf-route-type;
              description
                "Route type.";
            }
            leaf flags {
              type string;
              description
                "Extended prefix TLV flags list. This list will
                 contain identities for the prefix flags that
                 are set in the extended prefix flags.

                 A: Attach Flag. Set when Area Border Router (ABR)
                    generating an OSPFv2 Extended Prefix TLV for an inter-area
                    prefix that is locally connected or attached in another
                    connected area.

                 N: Node Flag. Set when the prefix identifies the advertising router,
                    i.e., the prefix is a host prefix advertising a globally reachable
                    address typically associated with a loopback address. The advertising
                    router MAY choose to not set this flag even when the above conditions are met.";
            }
            uses live_ncs_prefix-sid-sub-tlvs;
          }
        }
        container extended-link-opaque {
          description
            "All extended link TLVs in the LSA.";
          list extended-link-tlv {
            key "link-id";
            description
              "Extended link TLV.";
            uses live_ncs_ospfv2-router-link;
            container adj-sid-sub-tlvs {
              description
                "Adjacency SID optional sub-TLVs.";
              list adj-sid-sub-tlv {
                description
                  "List of Adjacency SID sub-TLVs.";
                key "sid";
                leaf sid {
                  type uint32;
                  description
                    "Segment Identifier (SID) index/label.";
                }
                leaf flags {
                  type string;
                  description
                    "Adj-sid sub-tlv flags.

                     B-Flag:  Backup Flag.  If set, the Adj-SID refers to an
                              adjacency that is eligible for protection (e.g., using IP
                              Fast Reroute or MPLS-FRR (MPLS-Fast Reroute) as described
                              in Section 2.1 of [RFC8402].

                     V-Flag:  Value/Index Flag.  If set, then the Adj-SID carries
                              an absolute value.  If not set, then the Adj-SID carries
                              an index.

                     L-Flag:  Local/Global Flag.  If set, then the value/index
                              carried by the Adj-SID has local significance.  If not
                              set, then the value/index carried by this sub-TLV has
                              global significance.

                     S-Flag.  Set Flag. When set, the S-Flag indicates that the Adj-SID
                              refers to a set of adjacencies (and therefore MAY be assigned
                              to other adjacencies as well).";
                }
                leaf mt-id {
                  type uint8;
                  description
                    "Multi-topology ID.";
                }
                leaf weight {
                  type uint8;
                  description
                    "Weight used for load-balancing.";
                }
              }
            }
            container lan-adj-sid-sub-tlvs {
              description
                "LAN Adjacency SID optional sub-TLVs.";
              list lan-adj-sid-sub-tlv {
                description
                  "List of LAN adjacency SID sub-TLVs.";
                key "sid";
                leaf sid {
                  type uint32;
                  description
                    "Segment Identifier (SID) index/label.";
                }
                leaf flags {
                  type string;
                  description
                    "LAN adj-sid sub-tlv flags.

                     B-Flag:  Backup Flag.  If set, the Lan-Adj-SID refers to an
                              adjacency that is eligible for protection (e.g., using IP
                              Fast Reroute or MPLS-FRR (MPLS-Fast Reroute) as described
                              in Section 2.1 of [RFC8402].

                     V-Flag:  Value/Index Flag.  If set, then the Lan-Adj-SID carries
                              an absolute value.  If not set, then the Lan-Adj-SID carries
                              an index.

                     L-Flag:  Local/Global Flag.  If set, then the value/index
                              carried by the Lan-Adj-SID has local significance.  If not
                              set, then the value/index carried by this sub-TLV has
                              global significance.

                     S-Flag.  Set Flag. When set, the S-Flag indicates that the Lan-Adj-SID
                              refers to a set of adjacencies (and therefore MAY be assigned
                              to other adjacencies as well).";
                }
                leaf mt-id {
                  type uint8;
                  description
                    "Multi-topology ID.";
                }
                leaf weight {
                  type uint8;
                  description
                    "Weight used for load-balancing.";
                }
                leaf neighbor-router-id {
                  type yang:dotted-quad;
                  description
                    "Neighbor router ID.";
                }
              }
            }
          }
        }
        container ri-opaque {
          description
            "OSPF Router Information (RI) opaque LSA.";
          reference "RFC 7770: OSPF Router Capabilities";
          uses live_ncs_sr-algorithm-tlv;
          uses live_ncs_sid-range-tlvs;
        }
      }
      container router-lsa {
        description
          "Router-LSAs are the Type 1 LSAs.
           The LSA describes the state and cost of the router's
           links (i.e., interfaces) to the area";
        leaf flags {
          type string;
          description
            "Router LSA bits list.
             bit V : If set, the router is an endpoint of one or
                     more virtual link.

             bit E : If set, the router is an AS Boundary Router (ASBR).

             bit B : If set, the router is an Area Border Router (ABR).";
        }
        leaf link-count {
          type uint16;
          description
            "The number of links in the router LSA";
        }
        list link {
          key "link-id";
          description
            "Router LSA link.";
          uses live_ncs_ospfv2-router-link;
          leaf num-tos-metric {
            type uint8;
            description
              "The number of different TOS metrics given for this link";
          }
          leaf tos-0-metric {
            type uint16;
            description
              "The cost of using this router link.";
          }
        }
      }
      container network-lsa {
        description
          "Network-LSAs are the Type 2 LSAs.
           The LSA describes all routers attached to the
           network, including the Designated Router itself.";
        leaf network-mask {
          type inet:ipv4-address;
          description
            "The IP address mask for the network.";
        }
        leaf-list attached-router {
          type inet:ipv4-address;
          description
            "List of the routers attached to the network.";
        }
      }
      container summary-lsa {
        description
          "Summary-LSAs are the Type 3 LSAs.
           Type3 LSAs are used when the destination is an IP network.";
        uses live_ncs_summary-lsa;
      }
      container asbr-summary-lsa {
        description
          "Asbr-summary LSAa are the Type 4 LSAs.
           Type 4 LSAs are used when the destination is an AS boundary router.";
        uses live_ncs_summary-lsa;
      }
    }
  }

  grouping live_ncs_prefix-sid-sub-tlvs {
    description
      "Prefix Segment ID (SID) sub-TLVs.";
    container prefix-sid-sub-tlvs {
      description
        "Prefix SID sub-TLV.";
      list prefix-sid-sub-tlv {
        description
          "Prefix SID sub-TLV.";
        key "sid";
        leaf sid {
          type uint32;
          description
            "An index or label.";
        }
        leaf flags {
          type string;
          description
            "Prefix SID Segment Identifier (SID) Flags.

             NP-Flag:  No-PHP (Penultimate Hop Popping) Flag.  If set,
                       then the penultimate hop MUST NOT pop the Prefix-SID
                       before delivering packets to the node that advertised the
                       Prefix-SID.

             M-Flag:  Mapping Server Flag.  If set, the SID was
                      advertised by an SR Mapping Server as described in
                      [RFC8661].

             E-Flag:  Explicit Null Flag.  If set, any upstream neighbor
                      of the Prefix-SID originator MUST replace the Prefix-SID
                      with the Explicit NULL label (0 for IPv4) before
                      forwarding the packet.

             V-Flag:  Value/Index Flag.  If set, then the Prefix-SID
                      carries an absolute value.  If not set, then the Prefix-
                      SID carries an index.

             L-Flag:  Local/Global Flag.  If set, then the value/index
                      carried by the Prefix-SID has local significance.  If not
                      set, then the value/index carried by this sub-TLV has
                      global significance.";
        }
        leaf mt-id {
          type uint8;
          description
            "Multi-topology ID.";
        }
        leaf algorithm {
          type uint8;
          description
            "The algorithm associated with the prefix-SID.";
        }
      }
    }
  }

  grouping live_ncs_sr-algorithm-tlv {
    description
      "SR algorithm TLV grouping.";
    container sr-algorithm-tlv {
      description
        "All SR algorithm TLVs.";
      leaf-list sr-algorithm {
        type uint8;
        description
          "The Segment Routing (SR) algorithms that the router is
           currently using.";
      }
    }
  }

  grouping live_ncs_sid-range-tlvs {
    description
      "SID Range TLV grouping.";
    container sid-range-tlvs {
      description
        "List of SID range TLVs.";
      list sid-range-tlv {
        description
          "SID range TLV.";
        key "index";
        leaf index {
          type uint32;
          description
            "The SID Range Index";
        }
        leaf range-size {
          type uint32;
          description
            "The SID range.";
        }
        uses live_ncs_sid-sub-tlv;
      }
    }
  }

  grouping live_ncs_ospfv2-router-link {
    description
      "OSPFv2 router link.";
    leaf link-id {
      type inet:ipv4-address;
      description
        "Router-LSA Link ID";
    }
    leaf link-data {
      type inet:ipv4-address;
      description
        "Router-LSA Link data.";
    }
    leaf type {
      type cn-l3-types:live_ncs_ospf-router-link-type;
      description
        "Router-LSA Link type.";
    }
  }

  grouping live_ncs_summary-lsa {
    description
      "Summary LSA";
    leaf network-mask {
      type inet:ipv4-address;
      description
        "The IP address mask for the network";
    }
    leaf metric {
      type uint32;
      description
        "Metric";
    }
  }

  grouping live_ncs_lsdb-instance-detail-grouping {
    list lsdb-instance-entry-detail {
      key "lsa-type lsa-id adv-router";
      description
        "List OSPF LSAs.";
      uses live_ncs_lsa-header;
      uses live_ncs_lsa-header-detail;
      container as-external-lsa {
        description
          "AS-external-LSAs are the Type 5 LSAs.";
        leaf network-mask {
          type inet:ipv4-address;
          description
            "IP Address mask.";
        }
        leaf metric-type {
          type cn-l3-types:live_ncs_ospf-metric-type;
          description
            "Metric Type";
        }
        leaf metric {
          type uint32;
          description
            "Metric";
        }
        leaf forwarding-addr {
          type inet:ipv4-address;
          description
            "Forwarding IP Address";
        }
        leaf route-tag {
          type uint32;
          description
            "A 32-bit field attached to each external route";
        }
      }
    }
  }

  grouping live_ncs_segment-routing-state-grouping {
    description
      "Grouping of OSPF SR state elements.";
    leaf state {
      type string;
      description
        "SR state enabled/disabled";
    }
    list sr-capability {
      key "router-ip";
      description
        "List of SR-Capability Info";
      leaf router-ip {
        type inet:ipv4-address;
        description
          "Router IP.";
      }
      leaf total-sid {
        type uint32;
        description
          "Total SIDs supported";
      }
      leaf sid-range-list-count {
        type uint32;
        description
          "SID range list count";
      }
      list sid-range {
        key "index";
        description
          "List of Ranges";
        leaf index {
          type uint32;
          description
            "SID range index for indexing";
        }
        leaf start {
          type uint32;
          description
            "SID range start";
        }
        leaf end {
          type uint32;
          description
            "SID range end";
        }
      }
      leaf algorithm {
        type uint8;
        description
          "SR algorithm";
      }
    }
  }

  grouping live_ncs_microloop-avoidance-state-grouping {
    description
      "Grouping of OSPF microloop state elements.";
    leaf enable {
      type boolean;
      description
        "Microloop state enabled/disabled";
    }
    leaf rib-update-delay {
      type uint32;
      units "milliseconds";
      description
        "Microloop rib-update-delay timer total configured value";
    }
    leaf running-state {
      type boolean;
      description
        "Microloop rib-update-delay running state";
    }
    leaf pending-rib-update-delay {
      type uint32;
      units "milliseconds";
      description
        "Microloop rib-update-delay timer remaining value";
    }
  }

  grouping live_ncs_sid-sub-tlv {
    description
      "SID/Label sub-TLV grouping.";
    container sid-sub-tlv {
      description
        "Used to advertise the SID/Label associated with a prefix or adjacency.";
      leaf sid {
        type uint32;
        description
          "Segment Identifier (SID) - A 20 bit label or 32 bit SID.";
      }
    }
  }

  grouping live_ncs_ospf-instance-state-grouping {
    leaf up-time {
      type string {
        length "0..255";
      }
      description
        "The length of time in seconds the protocol instance has been
         in the up state";
    }
    leaf lsa-count {
      type yang:counter32;
      description
        "External Link State Advertisement count";
    }
    leaf lsa-cksum-sum {
      type string {
        length "0..255";
      }
      description
        "External LSA checksum";
    }
    leaf originate-new-lsa-count {
      type yang:counter32;
      description
        "Number of self-originating LSAs";
    }
    leaf rx-new-lsas-count {
      type yang:counter32;
      description
        "Number of new LSAs received";
    }
    leaf area-count {
      type yang:counter32;
      description
        "Number of areas in the OSPF instance";
    }
    leaf instance-creation-time {
      type string {
        length "0..255";
      }
      description
        "OSPF Statistics Up Time";
    }
    leaf router-id-change-count {
      type yang:counter32;
      description
        "The number of times the router ID was modified";
    }
    leaf dr-election-counter {
      type yang:counter32;
      description
        "Number of DR elections";
    }
    leaf neighbor-expiration-count {
      type yang:counter32;
      description
        "Number of expired neighbors";
    }
    leaf neighbor-bad-ls-reqs-count {
      type yang:counter32;
      description
        "Number of bad LS Requests received";
    }
    leaf neighbor-seq-num-mismatch-count {
      type yang:counter32;
      description
        "Number of packets received from neighbors with mismatched
         sequence number";
    }
    leaf router-id {
      type rt-types:live_ncs_router-id;
      description
        "The router identifier";
    }
    uses live_ncs_pdu-statistics-grouping;
  }

  grouping live_ncs_virtual-link-state-grouping {
    list virtual-link-state {
      key "name";
      description
        "Grouping of virtual link parameters";
      leaf name {
        type string {
          length "0..255";
        }
        description
          "Virtual link identifier, unique name assigned for the virtual link";
      }
      leaf vlink-state {
        type cn-l3-types:live_ncs_ospf-vlink-state-type;
        description
          "Virtual link state";
      }
      leaf vlink-router-id {
        type rt-types:live_ncs_router-id;
        description
          "Router ID of remote device.";
      }
      leaf vlink-transit-area {
        type inet:ip-address;
        description
          "The transit area address of virtual link.";
      }
      leaf vlink-interface-name {
        type string {
          length "0..255";
        }
        description
          "Interface name from where Virtual link is connected";
      }
      leaf vlink-local-addr {
        type inet:ip-address;
        description
          "The address of local node.";
      }
      leaf vlink-remote-addr {
        type inet:ip-address;
        description
          "The address of remote node.";
      }
      leaf vlink-hello-due {
        type string {
          length "0..255";
        }
        description
          "This is to get the timer that tracks the remaining time before
           the neighbor is declared dead (in seconds).";
      }
      leaf vlink-hello-timer {
        type uint32;
        description
          "This is to get the configured vlink hello timer (in seconds)";
      }
      leaf vlink-dead-timer {
        type uint32;
        units "seconds";
        description
          "This is to get the vlink dead timer (in seconds)";
      }
      leaf vlink-transmit-timer {
        type uint32;
        units "seconds";
        description
          "This is to get the vlink transmit timer (in seconds)";
      }
      leaf vlink-retransmit-timer {
        type uint32;
        units "seconds";
        description
          "This is to get the vlink retransmit timer (in seconds)";
      }
    }
  }

  grouping live_ncs_notification-instance-hdr {
    description
      "This grouping describes common instance specific,
       data for OSPF notifications.";
    leaf instance-tag {
      type uint32 {
        range "0..65535";
      }
      description
        "OSPF instance ID";
    }
  }

  grouping live_ncs_notification-interface {
    description
      "This grouping provides interface information,
       for the OSPF interface specific notification.";
    leaf interface {
      type string {
        length "0..255";
      }
      description
        "OSPF interface name.";
    }
    leaf if-link-type {
      type cn-l3-types:live_ncs_ospf-network-type;
      description
        "Link type of OSPF interface.";
    }
  }

  grouping live_ncs_notification-neighbor {
    description
      "This grouping provides the neighbor information,
       for neighbor specific notifications.";
    leaf neighbor-router-id {
      // NCS drop if-feature statement
      type rt-types:live_ncs_router-id;
      description
        "Neighbor router ID.";
    }
    leaf neighbor-ip-addr {
      type inet:ip-address;
      description
        "Neighbor address.";
    }
  }

  grouping instance-config {
    description
      "OSPF instance config state.";
    leaf router-id {
      tailf:display-when "not(../ncs:module) or boolean(/ncs:devices/ncs:device[ncs:name=current()/../ncs:name]/capability/feature='router-id')";
      type rt-types:router-id;
      description
        "Defined in RFC 2328. A 32-bit number
         that uniquely identifies the router.";
    }
    leaf spf-min-delay {
      type uint32 {
        range "1..600000";
      }
      default "500";
      units "milliseconds";
      description
        "The minimum SPF delay time in milliseconds: 500 milliseconds.";
    }
    leaf spf-max-delay {
      type uint32 {
        range "1..600000";
      }
      default "5000";
      units "milliseconds";
      description
        "The maximum SPF hold delay time in milliseconds: 50000
         milliseconds (50 seconds)";
    }
    leaf admin-distance {
      type uint32 {
        range "1..255";
      }
      description
        "OSPF administrative distance";
    }
    list redistribute {
      key "protocol";
      description
        "redistribute routes to external process";
      leaf protocol {
        type cn-l3-types:ospf-route-source;
        description
          "Redistibute protocol name";
      }
      leaf metric-type {
        type cn-l3-types:ospf-metric-type;
        description
          "Metric type";
      }
      leaf metric {
        type uint32 {
          range "0..16777214";
        }
        default "20";
        description
          "Metric value";
      }
      leaf policy {
        type leafref {
          path "/ncs:devices/ncs:device/ncs:config/rt-pol:routing-policy/rt-pol:policies/rt-pol:policy/rt-pol:name" {
            tailf:xpath-root 3;
          }
        }
        description
          "Name of the routemap to apply the filter to.";
      }
    }
    container fast-reroute {
      description
        "Configurations for OSPF LFA fast reroute";
      container lfa {
        leaf per-prefix-enable {
          type boolean;
          default "false";
          description
            "Enables/disables LFA FRR";
        }
      }
    }
  }

  grouping interface-common-config {
    description
      "Common configuration for all types of interfaces,
       including virtual links and sham links.";
    leaf hello-interval {
      type uint16 {
        range "1..65535";
      }
      units "seconds";
      default "10";
      description
        "Interval between hello packets (seconds). It must
         be the same for all routers on the same network.
         Different networks, implementations, and deployments
         will use different hello-intervals. A sample value
         for a LAN network would be 10 seconds.";
      reference "RFC 2328: OSPF Version 2, Appendix C.3";
    }
    leaf dead-interval {
      type uint16 {
        range "1..65535";
      }
      units "seconds";
      must '../dead-interval > ../hello-interval' {
        tailf:xpath-root 3;
        error-message "The dead interval must be larger than the hello interval";
        description
          "The value must be greater than the 'hello-interval'.";
      }
      default "40";
      description
        "Interval after which a neighbor is declared down
         (seconds) if hello packets are not received. It is

         typically 3 or 4 times the hello-interval. A typical
         value for LAN networks is 40 seconds.";
      reference "RFC 2328: OSPF Version 2, Appendix C.3";
    }
    leaf retransmit-interval {
      type uint16 {
        range "1..1800";
      }
      units "seconds";
      default "5";
      description
        "Interval between retransmitting unacknowledged Link
         State Advertisements (LSAs) (seconds). This should
         be well over the round-trip transmit delay for
         any two routers on the network. A sample value
         would be 5 seconds.";
      reference "RFC 2328: OSPF Version 2, Appendix C.3";
    }
    leaf transmit-delay {
      type uint16 {
        range "1..3600";
      }
      units "seconds";
      default "1";
      description
        "Estimated time needed to transmit Link State Update
         (LSU) packets on the interface (seconds). LSAs have
         their age incremented by this amount when advertised
         on the interface. A sample value would be 1 second.";
      reference "RFC 2328: OSPF Version 2, Appendix C.3";
    }
    leaf disable {
      type boolean;
      default "false";
      description
        "Disable OSPF protocol on the interface.";
    }
    leaf metric {
      type cn-l3-types:ospf-link-metric;
      description
        "Interface cost.";
    }
    leaf lfa-candidate-enable {
      type boolean;
      description
        "Enable/disable the interface from being used as the next hop in a repair path";
      default "true";
    }
    container ldp-igp-sync {
      presence "Configures LDP/IGP Sync parameters";
      description
        "Enables IGP/LDP synchronization";
      leaf hold-down {
        type cn-l3-types:ldp-igp-sync-holddown;
        mandatory true;
        description
          "Hold-down timer for the OSPF ldp-igp synchronization configuration 
            range: [1-69999]/none/infinite";
      }
    }
  }

  grouping interface-config {
    description
      "Configuration for real interfaces.";
    leaf type {
      type enumeration {
        enum "broadcast" {
          description
            "Specify OSPF broadcast multi-access network.";
        }
        enum "point-to-point" {
          description
            "Specify OSPF point-to-point network.";
        }
      }
      default "broadcast";
      description
        "Interface type.";
    }
    leaf passive {
      type boolean;
      default "false";
      description
        "Enable/Disable passive interface - a passive interface's
         prefix will be advertised but no neighbor adjacencies
         will be formed on the interface.";
    }
    list authentication {
      key "id";
      max-elements 1;
      description
        "OSPF message-digest-key (MD5) related operations";
      leaf id {
        type uint32 {
          range "1..255";
        }
        description
          "Key ID";
      }
      leaf password {
        type string {
          length "1..8";
        }
        mandatory true;
        ncx:password;
        description
          "MD5 Authentiation key (password)";
      }
    }
    leaf priority {
      type uint8 {
        range "0..255";
      }
      default "1";
      description
        "Configure OSPF router priority. On multi-access network
         this value is for Designated Router (DR) election. The
         priority is ignored on other interface types. A router
         with a higher priority will be preferred in the election
         and a value of 0 indicates the router is not eligible to
         become Designated Router or Backup Designated Router
         (BDR).";
    }
    container bfd {
      tailf:display-when "not(../ncs:module) or boolean(/ncs:devices/ncs:device[ncs:name=current()/../ncs:name]/capability/feature='bfd')";
      description
        "BFD Client Configuration.";
      uses bfd-types:client-cfg-parms;
      reference
        "RFC YYYY: YANG Data Model for Bidirectional
         Forwarding Detection (BFD). Please replace YYYY with
         published RFC number for draft-ietf-bfd-yang.";
    }
    leaf mtu {
      type uint16 {
        range "576..65535";
      }
      description
        "Set the ospf packet MTU size. By default, ospf uses the
         interface MTU size";
    }
    uses interface-common-config;
  }

  grouping srlr {
    description
      "Grouping for SR label range configuration.";
    leaf lower-bound {
      type uint32 {
        range "16000..1048575";
      }
      description
        "Lower value in the block.";
    }
    leaf upper-bound {
      type uint32 {
        range "16000..1048575";
      }
      description
        "Upper value in the block.";
    }
  }

  grouping srgb-cfg {
    description
      "Grouping for SR global block configuration";
    list srgb {
      key "lower-bound upper-bound";
      max-elements 1;
      ordered-by user;
      description
        "List of global blocks to be advertised.";
      uses srlr;
    }
  }

  grouping area-common-config {
    container fast-reroute {
      description
        "Configurations for OSPF remote LFA fast reroute";
      container remote-lfa {
        leaf enable {
          type boolean;
          default "false";
          description
            "Enables/disables remote LFA FRR. Must be enabled with instance-level LFA configuration.";
        }
        leaf tunnel-cost {
          type uint32 {
            range "1..16777214";
          }
          default "60";
          description
            "Maximum cost of the repair tunnel.";
        }
        list protection {
          key "protection-type";
          description
            "Protection provided to the repair tunnel";
          leaf protection-type {
            type cn-l3-types:ospf-rlfa-protection-type;
            description
              "The protection type";
          }
          leaf enable {
            type boolean;
            default "false";
            description
              "Enable/disable the protection type";
          }
        }
      }
      container ti-lfa {
        leaf enable {
          type boolean;
          default "false";
          description
            "Enables/disables TI-LFA FRR, Must be enabled with instance-level LFA configuration";
        }
      }
    }
  }

  grouping neighbors-state-grouping {
    leaf area-id {
      type yang:dotted-quad;
      description
        "Area ID";
    }
    list neighbor-state {
      key "router-id";
      description
        "OSPF neighbor state";
      leaf router-id {
        type rt-types:router-id;
        description
          "Neighbor router ID";
      }
      leaf state-type {
        type string {
          length "0..255";
        }
        description
          "Neighbor state type";
      }
      leaf neighbor-event-count {
        type yang:counter32;
        description
          "The number of times this neighbor has changed
           state or an error has occurred. Discontinuities in the
           value of this counter can occur when the OSPF neighbor
           is re-initialized.";
      }
      leaf neighbor-retrans-qlen {
        type uint32;
        description
          "The current length of the retransmission queue.";
      }
      leaf lsdb-count {
        type yang:counter32;
        description
          "Link state Database Count";
      }
      leaf ls-request-count {
        type yang:counter32;
        description
          "Link State request count";
      }
      leaf ls-retransmit-count {
        type yang:counter32;
        description
          "Link State retransmission count";
      }
      leaf neighbor-up-time {
        type string {
          length "0..255";
        }
        description
          "The length of time in seconds the neighbor has been in
           the full adjacency state";
      }
      leaf dr-router-id {
        type rt-types:router-id;
        description
          "Neighbor's Designated Router (DR) Router ID.";
      }
      leaf bdr-router-id {
        type rt-types:router-id;
        description
          "The Backup Designated Router (BDR) Router ID.";
      }
      leaf dead-timer {
        type string {
          length "0..255";
        }
        description
          "This timer tracks the remaining time before
           the neighbor is declared dead.";
      }
      leaf priority {
        type uint32;
        description
          "Configured OSPF router priority. On multi-access network
           this value is for Designated Router (DR) election. The
           priority is ignored on other interface types. A router
           with a higher priority will be preferred in the election
           and a value of 0 indicates the router is not eligible to
           become Designated Router or Backup Designated Router
           (BDR).";
      }
    }
  }

  grouping pdu-statistics-grouping {
    leaf total-sent {
      type uint32;
      description
        "Total number of packets sent.";
    }
    leaf total-received {
      type uint32;
      description
        "Total number of packets received.";
    }
    leaf hello-sent {
      type uint32;
      description
        "Hello's sent.";
    }
    leaf hello-received {
      type uint32;
      description
        "Hello's received.";
    }
    leaf dd-sent {
      type uint32;
      description
        "Total number of database description packets sent.";
    }
    leaf dd-received {
      type uint32;
      description
        "Total number of database description packets received.";
    }
    leaf ls-request-sent {
      type uint32;
      description
        "Total number of LS requests sent.";
    }
    leaf ls-request-received {
      type uint32;
      description
        "Total number of LS requests received.";
    }
    leaf ls-update-sent {
      type uint32;
      description
        "Total number of LS updates sent.";
    }
    leaf ls-update-received {
      type uint32;
      description
        "Total number of LS updates received.";
    }
    leaf ls-ack-sent {
      type uint32;
      description
        "Total number of LS acknowledgements sent.";
    }
    leaf ls-ack-received {
      type uint32;
      description
        "Total number of LS acknowledgements received.";
    }
    leaf error-packet-tx-count {
      type uint32;
      description
        "Number of packets not transmitted due to error.";
    }
    leaf error-packet-rx-count {
      type uint32;
      description
        "Number of incoming packets with error.";
    }
  }

  grouping interface-state-grouping {
    list interface-state {
      key "name";
      description
        "OSPF interface related operations";
      leaf name {
        type string {
          length "0..255";
        }
        description
          "Interface name";
      }
      leaf state {
        type cn-l3-types:ospf-intf-state-type;
        description
          "Interface state";
      }
      leaf events {
        type uint32;
        description
          "The number of times this interface has changed its
           state or an error has occurred. Discontinuities in the
           value of this counter can occur when the OSPF interface
           is re-initialized.";
      }
      leaf lsa-count {
        type yang:counter32;
        description
          "The number of link-scope LSAs";
      }
      leaf lsa-cksum-sum {
        type uint32;
        description
          "The modulo 2**32 sum of the LSA checksums
           for link-scope LSAs. The value should be treated as
           unsigned when comparing two sums of checksums. While
           differing checksums indicate a different combination
           of LSAs, equivalent checksums don't guarantee that the
           LSAs are the same given that multiple combinations of
           LSAs can result in the same checksum.";
      }
      leaf dr-router-id {
        type rt-types:router-id;
        description
          "Neighbor's Designated Router (DR) Router ID.";
      }
      leaf dr-ip-addr {
        type inet:ip-address;
        description
          "The Designated Router (DR) IP address.";
      }
      leaf bdr-router-id {
        type rt-types:router-id;
        description
          "The Backup Designated Router (BDR) Router ID.";
      }
      leaf ldp-igp-sync-status {
        type string;
        description
          "Status of ldp-igp-sync (Configured or Not Configured).";
      }
      leaf remaining-hold-down-time {
        type uint32;
        units "milliseconds";
        description
          "Time in milliseconds before LDP notifies OSPF to advertise original cost.";
      }
      leaf bdr-ip-addr {
        type inet:ip-address;
        description
          "The Backup Designated Router (BDR) IP Address.";
      }
      uses pdu-statistics-grouping;
      uses neighbors-state-grouping;
    }
  }

  grouping ospf-route-grouping {
    // NCS drop config false list 'route-state'
  }

  grouping lsdb-area-summary-grouping {
    // NCS drop config false list 'lsdb-area-entry-summary'
  }

  grouping lsdb-instance-summary-grouping {
    // NCS drop config false list 'lsdb-instance-entry-summary'
  }

  grouping lsa-header {
    description
      "Common LSA for OSPFv2 and OSPFv3";
    leaf lsa-type {
      type cn-l3-types:ospf-lsa-type;
      description
        "LSA type";
    }
    leaf lsa-id {
      type yang:dotted-quad;
      description
        "Link-State ID.";
    }
    leaf adv-router {
      type rt-types:router-id;
      description
        "LSA advertising router.";
    }
    leaf ls-age {
      type uint16;
      description
        "LSA age.";
    }
    leaf seq-num {
      type uint32;
      description
        "LSA sequence number.";
    }
    leaf checksum {
      type string;
      description
        "LSA checksum.";
    }
  }

  grouping lsa-header-detail {
    leaf length {
      type uint16;
      description
        "LSA length including the header.";
    }
    leaf options {
      type string;
      description
        "The Options field enables OSPF routers to support
         (or not support) optional capabilities, and to
         communicate their capability level to other OSPF routers";
    }
  }

  grouping lsdb-area-detail-grouping {
    // NCS drop config false list 'lsdb-area-entry-detail'
  }

  grouping prefix-sid-sub-tlvs {
    description
      "Prefix Segment ID (SID) sub-TLVs.";
    container prefix-sid-sub-tlvs {
      description
        "Prefix SID sub-TLV.";
      list prefix-sid-sub-tlv {
        description
          "Prefix SID sub-TLV.";
        key "sid";
        leaf sid {
          type uint32;
          description
            "An index or label.";
        }
        leaf flags {
          type string;
          description
            "Prefix SID Segment Identifier (SID) Flags.

             NP-Flag:  No-PHP (Penultimate Hop Popping) Flag.  If set,
                       then the penultimate hop MUST NOT pop the Prefix-SID
                       before delivering packets to the node that advertised the
                       Prefix-SID.

             M-Flag:  Mapping Server Flag.  If set, the SID was
                      advertised by an SR Mapping Server as described in
                      [RFC8661].

             E-Flag:  Explicit Null Flag.  If set, any upstream neighbor
                      of the Prefix-SID originator MUST replace the Prefix-SID
                      with the Explicit NULL label (0 for IPv4) before
                      forwarding the packet.

             V-Flag:  Value/Index Flag.  If set, then the Prefix-SID
                      carries an absolute value.  If not set, then the Prefix-
                      SID carries an index.

             L-Flag:  Local/Global Flag.  If set, then the value/index
                      carried by the Prefix-SID has local significance.  If not
                      set, then the value/index carried by this sub-TLV has
                      global significance.";
        }
        leaf mt-id {
          type uint8;
          description
            "Multi-topology ID.";
        }
        leaf algorithm {
          type uint8;
          description
            "The algorithm associated with the prefix-SID.";
        }
      }
    }
  }

  grouping sr-algorithm-tlv {
    description
      "SR algorithm TLV grouping.";
    container sr-algorithm-tlv {
      description
        "All SR algorithm TLVs.";
      leaf-list sr-algorithm {
        type uint8;
        description
          "The Segment Routing (SR) algorithms that the router is
           currently using.";
      }
    }
  }

  grouping sid-range-tlvs {
    description
      "SID Range TLV grouping.";
    container sid-range-tlvs {
      description
        "List of SID range TLVs.";
      list sid-range-tlv {
        description
          "SID range TLV.";
        key "index";
        leaf index {
          type uint32;
          description
            "The SID Range Index";
        }
        leaf range-size {
          type uint32;
          description
            "The SID range.";
        }
        uses sid-sub-tlv;
      }
    }
  }

  grouping ospfv2-router-link {
    description
      "OSPFv2 router link.";
    leaf link-id {
      type inet:ipv4-address;
      description
        "Router-LSA Link ID";
    }
    leaf link-data {
      type inet:ipv4-address;
      description
        "Router-LSA Link data.";
    }
    leaf type {
      type cn-l3-types:ospf-router-link-type;
      description
        "Router-LSA Link type.";
    }
  }

  grouping summary-lsa {
    description
      "Summary LSA";
    leaf network-mask {
      type inet:ipv4-address;
      description
        "The IP address mask for the network";
    }
    leaf metric {
      type uint32;
      description
        "Metric";
    }
  }

  grouping lsdb-instance-detail-grouping {
    // NCS drop config false list 'lsdb-instance-entry-detail'
  }

  grouping segment-routing-state-grouping {
    description
      "Grouping of OSPF SR state elements.";
    // NCS drop config false leaf state
    list sr-capability {
      key "router-ip";
      description
        "List of SR-Capability Info";
      leaf router-ip {
        type inet:ipv4-address;
        description
          "Router IP.";
      }
      leaf total-sid {
        type uint32;
        description
          "Total SIDs supported";
      }
      leaf sid-range-list-count {
        type uint32;
        description
          "SID range list count";
      }
      list sid-range {
        key "index";
        description
          "List of Ranges";
        leaf index {
          type uint32;
          description
            "SID range index for indexing";
        }
        leaf start {
          type uint32;
          description
            "SID range start";
        }
        leaf end {
          type uint32;
          description
            "SID range end";
        }
      }
      leaf algorithm {
        type uint8;
        description
          "SR algorithm";
      }
    }
  }

  grouping microloop-avoidance-state-grouping {
    description
      "Grouping of OSPF microloop state elements.";
    leaf enable {
      type boolean;
      description
        "Microloop state enabled/disabled";
    }
    leaf rib-update-delay {
      type uint32;
      units "milliseconds";
      description
        "Microloop rib-update-delay timer total configured value";
    }
    leaf running-state {
      type boolean;
      description
        "Microloop rib-update-delay running state";
    }
    leaf pending-rib-update-delay {
      type uint32;
      units "milliseconds";
      description
        "Microloop rib-update-delay timer remaining value";
    }
  }

  grouping sid-sub-tlv {
    description
      "SID/Label sub-TLV grouping.";
    container sid-sub-tlv {
      description
        "Used to advertise the SID/Label associated with a prefix or adjacency.";
      leaf sid {
        type uint32;
        description
          "Segment Identifier (SID) - A 20 bit label or 32 bit SID.";
      }
    }
  }

  grouping ospf-instance-state-grouping {
    leaf up-time {
      type string {
        length "0..255";
      }
      description
        "The length of time in seconds the protocol instance has been
         in the up state";
    }
    leaf lsa-count {
      type yang:counter32;
      description
        "External Link State Advertisement count";
    }
    leaf lsa-cksum-sum {
      type string {
        length "0..255";
      }
      description
        "External LSA checksum";
    }
    leaf originate-new-lsa-count {
      type yang:counter32;
      description
        "Number of self-originating LSAs";
    }
    leaf rx-new-lsas-count {
      type yang:counter32;
      description
        "Number of new LSAs received";
    }
    leaf area-count {
      type yang:counter32;
      description
        "Number of areas in the OSPF instance";
    }
    leaf instance-creation-time {
      type string {
        length "0..255";
      }
      description
        "OSPF Statistics Up Time";
    }
    leaf router-id-change-count {
      type yang:counter32;
      description
        "The number of times the router ID was modified";
    }
    leaf dr-election-counter {
      type yang:counter32;
      description
        "Number of DR elections";
    }
    leaf neighbor-expiration-count {
      type yang:counter32;
      description
        "Number of expired neighbors";
    }
    leaf neighbor-bad-ls-reqs-count {
      type yang:counter32;
      description
        "Number of bad LS Requests received";
    }
    leaf neighbor-seq-num-mismatch-count {
      type yang:counter32;
      description
        "Number of packets received from neighbors with mismatched
         sequence number";
    }
    leaf router-id {
      type rt-types:router-id;
      description
        "The router identifier";
    }
    uses pdu-statistics-grouping;
  }

  grouping virtual-link-state-grouping {
    list virtual-link-state {
      key "name";
      description
        "Grouping of virtual link parameters";
      leaf name {
        type string {
          length "0..255";
        }
        description
          "Virtual link identifier, unique name assigned for the virtual link";
      }
      leaf vlink-state {
        type cn-l3-types:ospf-vlink-state-type;
        description
          "Virtual link state";
      }
      leaf vlink-router-id {
        type rt-types:router-id;
        description
          "Router ID of remote device.";
      }
      leaf vlink-transit-area {
        type inet:ip-address;
        description
          "The transit area address of virtual link.";
      }
      leaf vlink-interface-name {
        type string {
          length "0..255";
        }
        description
          "Interface name from where Virtual link is connected";
      }
      leaf vlink-local-addr {
        type inet:ip-address;
        description
          "The address of local node.";
      }
      leaf vlink-remote-addr {
        type inet:ip-address;
        description
          "The address of remote node.";
      }
      leaf vlink-hello-due {
        type string {
          length "0..255";
        }
        description
          "This is to get the timer that tracks the remaining time before
           the neighbor is declared dead (in seconds).";
      }
      leaf vlink-hello-timer {
        type uint32;
        description
          "This is to get the configured vlink hello timer (in seconds)";
      }
      leaf vlink-dead-timer {
        type uint32;
        units "seconds";
        description
          "This is to get the vlink dead timer (in seconds)";
      }
      leaf vlink-transmit-timer {
        type uint32;
        units "seconds";
        description
          "This is to get the vlink transmit timer (in seconds)";
      }
      leaf vlink-retransmit-timer {
        type uint32;
        units "seconds";
        description
          "This is to get the vlink retransmit timer (in seconds)";
      }
    }
  }

  grouping notification-instance-hdr {
    description
      "This grouping describes common instance specific,
       data for OSPF notifications.";
    leaf instance-tag {
      type uint32 {
        range "0..65535";
      }
      description
        "OSPF instance ID";
    }
  }

  grouping notification-interface {
    description
      "This grouping provides interface information,
       for the OSPF interface specific notification.";
    leaf interface {
      type string {
        length "0..255";
      }
      description
        "OSPF interface name.";
    }
    leaf if-link-type {
      type cn-l3-types:ospf-network-type;
      description
        "Link type of OSPF interface.";
    }
  }

  grouping notification-neighbor {
    description
      "This grouping provides the neighbor information,
       for neighbor specific notifications.";
    leaf neighbor-router-id {
      tailf:display-when "not(../ncs:module) or boolean(/ncs:devices/ncs:device[ncs:name=current()/../ncs:name]/capability/feature='router-id')";
      type rt-types:router-id;
      description
        "Neighbor router ID.";
    }
    leaf neighbor-ip-addr {
      type inet:ip-address;
      description
        "Neighbor address.";
    }
  }

  augment "/ncs:devices/ncs:device/ncs:rpc" {
    container rpc-ospf-clear-instance {
      tailf:ncs-device-type "netconf";
      tailf:display-when "not(../../ncs:module) or ../../ncs:module[ncs:name='ciena-ospf']";
      tailf:action ospf-clear-instance {
        tailf:actionpoint ncsproxy {
          tailf:internal;
        }
        input {
          leaf instance-tag {
            type uint32 {
              range "0..65535";
            }
            description
              "OSPF instance ID";
          }
        }
        output {
          leaf response {
            type string;
            description
              "The response could be 'success', or the reason for ospf-proc-clear failure";
          }
        }
      }
    }
  }
  augment "/ncs:devices/ncs:device-group/ncs:ned-id/ncs:rpc" {
    container rpc-ospf-clear-instance {
      tailf:ncs-device-type "netconf";
      tailf:display-when "/ncs:devices/ncs:device[ncs:name=current()/../../../ncs:member]/ncs:module[ncs:name='ciena-ospf']";
      tailf:action ospf-clear-instance {
        tailf:actionpoint ncsproxy {
          tailf:internal;
        }
        input {
          leaf instance-tag {
            type uint32 {
              range "0..65535";
            }
            description
              "OSPF instance ID";
          }
        }
        output {
          container "device" {
            leaf "name" {
              type string;
            }
            leaf "info" {
              type string;
            }
            container "result" {
              leaf response {
                type string;
                description
                  "The response could be 'success', or the reason for ospf-proc-clear failure";
              }
            }
          }
        }
      }
    }
  }
  augment "/ncs:devices/ncs:device/ncs:netconf-notifications/ncs:received-notifications/ncs:notification/ncs:data" {
    container ospf-instance-events {
      presence "";
      config false;
      list instance {
        description
          "Defines OSPF instance state change events and associated data used to publish change in the state";
        leaf tag {
          type uint32 {
            range "0..65535";
          }
          description
            "OSPF instance ID";
        }
        leaf router-id {
          tailf:display-when "not(../../ncs:module) or boolean(/ncs:devices/ncs:device[ncs:name=current()/../../ncs:name]/capability/feature='router-id')";
          type rt-types:ncs_rpc_notif_router-id;
          description
            "Defined in RFC 2328. A 32-bit number
             that uniquely identifies the router.";
        }
        leaf state {
          type cn-l3-types:ncs_rpc_notif_ospf-inst-state-type;
          description
            "OSPF instance state.";
        }
      }
    }
  }
  augment "/ncs:devices/ncs:device/ncs:netconf-notifications/ncs:received-notifications/ncs:notification/ncs:data" {
    container ospf-neighbor-events {
      presence "";
      config false;
      list neighbor {
        description
          "Defines OSPF neighbor state change events and associated data used to publish change in the state";
        uses ncs_rpc_notif_notification-interface;
        uses ncs_rpc_notif_notification-instance-hdr;
        uses ncs_rpc_notif_notification-neighbor;
        leaf old-state {
          type cn-l3-types:ncs_rpc_notif_ospf-nbr-state-type;
          description
            "Old OSPF neighbor state.";
        }
        leaf new-state {
          type cn-l3-types:ncs_rpc_notif_ospf-nbr-state-type;
          description
            "New OSPF neighbor state.";
        }
      }
    }
  }
  augment "/ncs:devices/ncs:device/ncs:config" {
    container ospf {
      tailf:ncs-device-type "netconf";
      tailf:display-when "not(../../ncs:module) or ../../ncs:module[ncs:name='ciena-ospf']";
      description
        "OSPF protocol Instance";
      list instance {
        key "tag";
        max-elements 1;
        leaf tag {
          type uint32 {
            range "0..65535";
          }
          description
            "OSPF instance ID";
        }
        uses instance-config;
        container interfaces {
          description
            "All interfaces.";
          list interface {
            key "name";
            description
              "List of OSPF interfaces.";
            leaf name {
              type leafref {
                path "/ncs:devices/ncs:device/ncs:config/oc-if:interfaces/oc-if:interface/oc-if:name" {
                  tailf:xpath-root 3;
                }
              }
              description
                "Interface name reference.";
            }
            uses interface-config;
          }
        }
        container areas {
          description
            "All areas.";
          list area {
            key "id";
            max-elements 16;
            description
              "List of OSPF areas";
            leaf id {
              type yang:dotted-quad;
              description
                "Area ID";
            }
            list network {
              key "prefix";
              description
                "ospf network";
              leaf prefix {
                type inet:ipv4-prefix;
                description
                  "Network prefix and length";
              }
            }
            list prefix-list {
              key "prefix-name";
              description
                "Name of the prefix list";
              leaf prefix-name {
                type leafref {
                  path "/ncs:devices/ncs:device/ncs:config/rt-pol:routing-policy/rt-pol:prefix-lists/rt-pol:prefix-list/rt-pol:name" {
                    tailf:xpath-root 3;
                  }
                }
                description
                  "Refers to prefix list name";
              }
              leaf prefixType {
                type cn-l3-types:ospf-prefix-filter;
                description
                  "Filter type ( filter-in | filter-out)";
              }
            }
            list range {
              key "prefix";
              description
                "Summarize routes matching address/mask
                 (Area Border Routers (ABRs) only)";
              leaf prefix {
                type inet:ipv4-prefix;
                description
                  "The network prefix";
              }
              leaf range-advertise {
                type cn-l3-types:ospf-range-advertise;
                default "advertise";
                description
                  "Advertise or not-advertise";
              }
            }
            list virtual-link {
              key "peer-id";
              description
                "Virtual link ID(IP addr) associated with neighbor";
              leaf peer-id {
                type rt-types:router-id;
                description
                  "The Virtual Link ID associated with neighbor";
              }
              leaf vlink-dead-interval {
                type uint32 {
                  range "1..65535";
                }
                units "seconds";
                default "40";
                description
                  "Vlink Dead interval (in seconds) for router detection time";
              }
              leaf vlink-hello-interval {
                type uint32 {
                  range "1..65535";
                }
                units "seconds";
                default "10";
                description
                  "Vlink Hello interval (in seconds)";
              }
              leaf vlink-retransmit-interval {
                type uint32 {
                  range "1..1800";
                }
                units "seconds";
                default "5";
                description
                  "Vlink LSA retransmit interval (in seconds)";
              }
              leaf vlink-transmit-delay {
                type uint32 {
                  range "1..3600";
                }
                units "seconds";
                default "1";
                description
                  "Vlink LSA transmission delay (in seconds)";
              }
              container bfd {
                tailf:display-when "not(../../../../../../ncs:module) or boolean(/ncs:devices/ncs:device[ncs:name=current()/../../../../../../ncs:name]/capability/feature='bfd')";
                description
                  "Enable BFD for virtual link.";
                uses bfd-types:client-cfg-parms;
              }
            }
            uses area-common-config;
          }
        }
        container segment-routing {
          description
            "Attribute to enable MPLS-based segment routing for an ISIS or OSPF process";
          leaf enabled {
            type boolean;
            default "false";
            description
              "Enable MPLS Segment Routing";
          }
          uses srgb-cfg;
        }
        container microloop-avoidance {
          description
            "OSPF microloop avoidance configuration.";
          leaf enable {
            type boolean;
            default "false";
            description
              "Enable/disable microloop avoidance for protected prefixes.";
          }
          leaf rib-update-delay {
            type uint32 {
              range "0..2147483647";
            }
            default "5000";
            units "milliseconds";
            description
              "Set route download delay for microloop avoidance on local interfaces.";
          }
        }
      }
    }
    // NCS drop config false container 'ospf-state'
  }
  augment "/ncs:devices/ncs:device/ncs:live-status" {
    container ospf {
      tailf:ncs-device-type "netconf";
      tailf:display-when "not(../../ncs:module) or ../../ncs:module[ncs:name='ciena-ospf'] or (../../ncs:live-status-protocol[not(ncs:capability)]) or (../../ncs:live-status-protocol/ncs:capability/ncs:module[.='ciena-ospf'])";
      description
        "OSPF protocol Instance";
      list instance {
        key "tag";
        // NCS drop max-elements statement
        leaf tag {
          type uint32 {
            range "0..65535";
          }
          description
            "OSPF instance ID";
        }
        uses live_ncs_instance-config;
        container interfaces {
          description
            "All interfaces.";
          list interface {
            key "name";
            description
              "List of OSPF interfaces.";
            leaf name {
              type leafref {
                path "/ncs:devices/ncs:device/ncs:live-status/oc-if:interfaces/oc-if:interface/oc-if:name" {
                  tailf:xpath-root 3;
                }
              }
              description
                "Interface name reference.";
            }
            uses live_ncs_interface-config;
          }
        }
        container areas {
          description
            "All areas.";
          list area {
            key "id";
            // NCS drop max-elements statement
            description
              "List of OSPF areas";
            leaf id {
              type yang:dotted-quad;
              description
                "Area ID";
            }
            list network {
              key "prefix";
              description
                "ospf network";
              leaf prefix {
                type inet:ipv4-prefix;
                description
                  "Network prefix and length";
              }
            }
            list prefix-list {
              key "prefix-name";
              description
                "Name of the prefix list";
              leaf prefix-name {
                type leafref {
                  path "/ncs:devices/ncs:device/ncs:live-status/rt-pol:routing-policy/rt-pol:prefix-lists/rt-pol:prefix-list/rt-pol:name" {
                    tailf:xpath-root 3;
                  }
                }
                description
                  "Refers to prefix list name";
              }
              leaf prefixType {
                type cn-l3-types:live_ncs_ospf-prefix-filter;
                description
                  "Filter type ( filter-in | filter-out)";
              }
            }
            list range {
              key "prefix";
              description
                "Summarize routes matching address/mask
                 (Area Border Routers (ABRs) only)";
              leaf prefix {
                type inet:ipv4-prefix;
                description
                  "The network prefix";
              }
              leaf range-advertise {
                type cn-l3-types:live_ncs_ospf-range-advertise;
                // NCS drop default statement
                description
                  "Advertise or not-advertise";
              }
            }
            list virtual-link {
              key "peer-id";
              description
                "Virtual link ID(IP addr) associated with neighbor";
              leaf peer-id {
                type rt-types:live_ncs_router-id;
                description
                  "The Virtual Link ID associated with neighbor";
              }
              leaf vlink-dead-interval {
                type uint32 {
                  range "1..65535";
                }
                units "seconds";
                // NCS drop default statement
                description
                  "Vlink Dead interval (in seconds) for router detection time";
              }
              leaf vlink-hello-interval {
                type uint32 {
                  range "1..65535";
                }
                units "seconds";
                // NCS drop default statement
                description
                  "Vlink Hello interval (in seconds)";
              }
              leaf vlink-retransmit-interval {
                type uint32 {
                  range "1..1800";
                }
                units "seconds";
                // NCS drop default statement
                description
                  "Vlink LSA retransmit interval (in seconds)";
              }
              leaf vlink-transmit-delay {
                type uint32 {
                  range "1..3600";
                }
                units "seconds";
                // NCS drop default statement
                description
                  "Vlink LSA transmission delay (in seconds)";
              }
              container bfd {
                // NCS drop if-feature statement
                description
                  "Enable BFD for virtual link.";
                uses bfd-types:live_ncs_client-cfg-parms;
              }
            }
            uses live_ncs_area-common-config;
          }
        }
        container segment-routing {
          description
            "Attribute to enable MPLS-based segment routing for an ISIS or OSPF process";
          leaf enabled {
            type boolean;
            // NCS drop default statement
            description
              "Enable MPLS Segment Routing";
          }
          uses live_ncs_srgb-cfg;
        }
        container microloop-avoidance {
          description
            "OSPF microloop avoidance configuration.";
          leaf enable {
            type boolean;
            // NCS drop default statement
            description
              "Enable/disable microloop avoidance for protected prefixes.";
          }
          leaf rib-update-delay {
            type uint32 {
              range "0..2147483647";
            }
            // NCS drop default statement
            units "milliseconds";
            description
              "Set route download delay for microloop avoidance on local interfaces.";
          }
        }
      }
    }
    container ospf-state {
      tailf:ncs-device-type "netconf";
      tailf:display-when "not(../../ncs:module) or ../../ncs:module[ncs:name='ciena-ospf'] or (../../ncs:live-status-protocol[not(ncs:capability)]) or (../../ncs:live-status-protocol/ncs:capability/ncs:module[.='ciena-ospf'])";
      list instance {
        key "tag";
        description
          "OSPF attributes for each ospf process id";
        leaf tag {
          type uint32;
          description
            "OSPF process ID";
        }
        uses live_ncs_ospf-instance-state-grouping;
        list area-state {
          key "id";
          description
            "List of ospf areas";
          leaf id {
            type yang:dotted-quad;
            description
              "area to which the network belongs";
          }
          leaf interface-count {
            type yang:counter32;
            description
              "Number of interface in the area";
          }
          leaf neighbor-count {
            type yang:counter32;
            description
              "Number of neighbors in the area";
          }
          leaf spf-last-exec-time {
            type string {
              length "0..255";
            }
            description
              "SPF last executed time";
          }
          leaf spf-runs-count {
            type yang:counter32;
            description
              "The number of times the intra-area SPF has run.
               Discontinuities in the value of this counter can occur
               when the OSPF area is re-initialized.";
          }
          leaf lsa-count {
            type yang:counter32;
            description
              "The number of LSAs of the LSA type.";
          }
          leaf lsa-checksum {
            type string {
              length "0..255";
            }
            description
              "The modulo 2**32 sum of the LSA checksums
               for the LSAs of this type. The value should be
               treated as unsigned when comparing two sums of
               checksums. While differing checksums indicate a
               different combination of LSAs, equivalent checksums
               don't guarantee that the LSAs are the same given that
               multiple combinations of LSAs can result in the same
               checksum.";
          }
          container lsdb-summary-state {
            uses live_ncs_lsdb-area-summary-grouping;
          }
          container lsdb-detail-state {
            uses live_ncs_lsdb-area-detail-grouping;
          }
          container microloop-avoidance-state {
            uses live_ncs_microloop-avoidance-state-grouping;
          }
        }
        container interfaces-state {
          uses live_ncs_interface-state-grouping;
        }
        container routes-state {
          uses live_ncs_ospf-route-grouping;
        }
        list lfa-route {
          key "dest-prefix";
          description
            "List of ip LFA routes";
          leaf dest-prefix {
            type inet:ip-prefix;
            description
              "Destination prefix of the LFA route";
          }
          leaf dest-path-type {
            type string;
            description
              "Destination path type attribute";
          }
          list next-hop {
            key "primary-address";
            description
              "IPv4 next hops of the primary and alternate routes";
            leaf primary-address {
              type inet:ip-address;
              description
                "Next hop ip address of the primary route";
            }
            leaf primary-interface-name {
              type string;
              description
                "Name of the outgoing interface for the primary route";
            }
            leaf alternate-address {
              type inet:ip-address;
              description
                "Next hop ip address of the alternate route";
            }
            leaf alternate-interface-name {
              type string;
              description
                "Name of the outgoing interface for the alternate route";
            }
            leaf area-id {
              type yang:dotted-quad;
              description
                "OSPF Area ID";
            }
            leaf path-metric {
              type uint32;
              description
                "Link cost of the alternate route";
            }
            leaf protection-provided {
              type string;
              description
                "The possible protection types provided by the alternate route";
            }
          }
        }
        list remote-lfa-route {
          key "dest-prefix";
          description
            "List of remote LFA routes";
          leaf dest-prefix {
            type inet:ip-prefix;
            description
              "Destination prefix of the remote LFA route";
          }
          leaf dest-path-type {
            type string;
            description
              "Destination path type attribute";
          }
          list repair-path {
            key "primary-gateway-address";
            description
              "IPv4 next hops of the primary and repair paths";
            leaf primary-gateway-address {
              type inet:ip-address;
              description
                "Next hop ip address of the primary route";
            }
            leaf primary-interface-name {
              type string;
              description
                "Name of the outgoing interface for the primary route";
            }
            leaf tunnel-router-id {
              type string;
              description
                "Router id of the repair tunnel";
            }
            leaf tunnel-peer-address {
              type inet:ip-address;
              description
                "Peer ip address of the repair tunnel";
            }
            leaf tunnel-gateway {
              type inet:ip-address;
              description
                "Gateway ip address of the repair tunnel";
            }
            leaf tunnel-gateway-interface-name {
              type string;
              description
                "Outgoing interface name of the repair tunnel";
            }
            leaf area-id {
              type yang:dotted-quad;
              description
                "OSPF Area ID";
            }
            leaf tunnel-metric {
              type uint32;
              description
                "Metric of the repair tunnel";
            }
            leaf protection-provided {
              type string;
              description
                "The protection scheme provided in selecting the repair tunnel";
            }
          }
        }
        list ti-lfa-route {
          key "dest-prefix";
          description
            "List of TI LFA routes";
          leaf dest-prefix {
            type inet:ip-prefix;
            description
              "Destination prefix of the TI LFA route";
          }
          leaf dest-path-type {
            type string;
            description
              "Destination path type attribute";
          }
          list next-hop {
            key "primary-address";
            description
              "IPv4 next hops of the primary and alternate routes";
            leaf primary-address {
              type inet:ip-address;
              description
                "Next hop ip address of the primary route";
            }
            leaf primary-interface-name {
              type string;
              description
                "Name of the outgoing interface for the primary route";
            }
            leaf primary-router-id {
              type string;
              description
                "The primary route router id";
            }
            leaf alternate-address {
              type inet:ip-address;
              description
                "Next hop ip address of the alternate route";
            }
            leaf alternate-interface-name {
              type string;
              description
                "Name of the outgoing interface for the alternate route";
            }
            leaf alternate-router-id {
              type string;
              description
                "The alternate route router id";
            }
            leaf area-id {
              type yang:dotted-quad;
              description
                "OSPF Area ID";
            }
            leaf alternate-path-metric {
              type uint32;
              description
                "Link cost of the alternate route";
            }
            leaf protection-provided {
              type string;
              description
                "The protection scheme provided by the alternate route";
            }
          }
        }
        container lsdb-summary-state {
          uses live_ncs_lsdb-instance-summary-grouping;
        }
        container lsdb-detail-state {
          uses live_ncs_lsdb-instance-detail-grouping;
        }
        container segment-routing-state {
          uses live_ncs_segment-routing-state-grouping;
        }
        container vlink-state {
          uses live_ncs_virtual-link-state-grouping;
        }
      }
    }
  }
  augment "/ncs:devices/ncs:template/ncs:ned-id/ncs:config" {
    container ospf {
      description
        "OSPF protocol Instance";
      list instance {
        // NCS patched for predictable order
        ordered-by user;
        key "tag";
        // NCS drop max-elements statement
        leaf tag {
          type string;
          description
            "OSPF instance ID";
        }
        uses ncs_template_instance-config;
        container interfaces {
          description
            "All interfaces.";
          list interface {
            // NCS patched for predictable order
            ordered-by user;
            key "name";
            description
              "List of OSPF interfaces.";
            leaf name {
              type string;
              description
                "Interface name reference.";
            }
            uses ncs_template_interface-config;
          }
        }
        container areas {
          description
            "All areas.";
          list area {
            // NCS patched for predictable order
            ordered-by user;
            key "id";
            // NCS drop max-elements statement
            description
              "List of OSPF areas";
            leaf id {
              type string;
              description
                "Area ID";
            }
            list network {
              // NCS patched for predictable order
              ordered-by user;
              key "prefix";
              description
                "ospf network";
              leaf prefix {
                type string;
                description
                  "Network prefix and length";
              }
            }
            list prefix-list {
              // NCS patched for predictable order
              ordered-by user;
              key "prefix-name";
              description
                "Name of the prefix list";
              leaf prefix-name {
                type string;
                description
                  "Refers to prefix list name";
              }
              leaf prefixType {
                type cn-l3-types:ncs_template_ospf-prefix-filter;
                description
                  "Filter type ( filter-in | filter-out)";
              }
            }
            list range {
              // NCS patched for predictable order
              ordered-by user;
              key "prefix";
              description
                "Summarize routes matching address/mask
                 (Area Border Routers (ABRs) only)";
              leaf prefix {
                type string;
                description
                  "The network prefix";
              }
              leaf range-advertise {
                type cn-l3-types:ncs_template_ospf-range-advertise;
                // NCS drop default statement
                description
                  "Advertise or not-advertise";
              }
            }
            list virtual-link {
              // NCS patched for predictable order
              ordered-by user;
              key "peer-id";
              description
                "Virtual link ID(IP addr) associated with neighbor";
              leaf peer-id {
                type rt-types:ncs_template_router-id;
                description
                  "The Virtual Link ID associated with neighbor";
              }
              leaf vlink-dead-interval {
                type string;
                units "seconds";
                // NCS drop default statement
                description
                  "Vlink Dead interval (in seconds) for router detection time";
              }
              leaf vlink-hello-interval {
                type string;
                units "seconds";
                // NCS drop default statement
                description
                  "Vlink Hello interval (in seconds)";
              }
              leaf vlink-retransmit-interval {
                type string;
                units "seconds";
                // NCS drop default statement
                description
                  "Vlink LSA retransmit interval (in seconds)";
              }
              leaf vlink-transmit-delay {
                type string;
                units "seconds";
                // NCS drop default statement
                description
                  "Vlink LSA transmission delay (in seconds)";
              }
              container bfd {
                // NCS drop if-feature statement
                description
                  "Enable BFD for virtual link.";
                uses bfd-types:ncs_template_client-cfg-parms;
              }
            }
            uses ncs_template_area-common-config;
          }
        }
        container segment-routing {
          description
            "Attribute to enable MPLS-based segment routing for an ISIS or OSPF process";
          leaf enabled {
            type string;
            // NCS drop default statement
            description
              "Enable MPLS Segment Routing";
          }
          uses ncs_template_srgb-cfg;
        }
        container microloop-avoidance {
          description
            "OSPF microloop avoidance configuration.";
          leaf enable {
            type string;
            // NCS drop default statement
            description
              "Enable/disable microloop avoidance for protected prefixes.";
          }
          leaf rib-update-delay {
            type string;
            // NCS drop default statement
            units "milliseconds";
            description
              "Set route download delay for microloop avoidance on local interfaces.";
          }
        }
      }
    }
    // NCS drop config false container 'ospf-state'
  }

  identity normal-area {
    base area-type;
    description
      "OSPF normal area.";
  }

  identity area-type {
    description
      "Base identity for OSPF area type.";
  }

  feature router-id {
    description
      "Set Router-ID per instance explicitly.";
  }

  feature bfd {
    description
      "Support for BFD detection of OSPF neighbor reachability.";
    reference
      "RFC 5880: Bidirectional Forwarding Detection (BFD)
       RFC 5881: Bidirectional Forwarding Detection
       (BFD) for IPv4 and IPv6 (Single Hop)";
  }
}
