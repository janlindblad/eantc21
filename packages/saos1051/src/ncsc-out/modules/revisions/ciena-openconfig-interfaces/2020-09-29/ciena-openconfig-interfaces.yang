module ciena-openconfig-interfaces {
  // Generated by yanger -t ncs
  tailf:mount-id "saos1051-nc-1.0:saos1051-nc-1.0";
  tailf:ncs-device-type "netconf";

  yang-version 1.1;
  namespace "http://ciena.com/ns/yang/ciena-openconfig-interfaces";
  prefix cn-if;

  import openconfig-interfaces {
    prefix oc-if;
  }
  import ciena-mef-frame-to-cos-map {
    prefix ftc;
  }
  import ciena-vrf {
    prefix vrf;
  }
  import ciena-mef-cos-to-frame-map {
    prefix ctf;
  }
  import ietf-yang-types {
    prefix ietf-yt;
  }
  import ietf-inet-types {
    prefix inet;
    revision-date 2013-07-15;
  }
  import yuma-ncx {
    prefix ncx;
  }
  import ciena-mef-mac-management {
    prefix mef-mac-management;
  }
  import ciena-mef-access-flow {
    prefix acl;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076

              U.S.A.
     Phone:   +1 800-921-1144
     Fax:     +1 410-694-5750";
  description
    "This module contains the Ciena proprietary YANG deviations
     of the standard openconfig-interfaces YANG module.

     Copyright (c) 2016 Ciena Corporation.  All rights reserved.

     All information contained herein is, and remains
     the property of Ciena Corporation. Dissemination of this
     information or reproduction of this material is strictly
     forbidden unless prior written permission is obtained from
     Ciena Corporation.";

  revision 2020-09-29 {
    description
      "Added new reason-type ip-interface-delete.";
  }
  revision 2020-05-12 {
    description
      "Added new event-type ettp-capability-state and reason-type speed-compatibility.
       Added new leaf speed-compatibility in notification, which is pointing to a new state operational data.";
  }
  revision 2020-02-17 {
    description
      "Added L3 interface reference to access-profile.
       Added IP unnumbered feature.
       Added VTI Tunnel interface feature.";
  }
  revision 2019-08-28 {
    description
      "Upgrading to version 1.1";
  }
  revision 2017-07-12 {
    description
      "Initial version";
    reference "";
  }

  typedef ncs_template_ciena-openconfig-interface-ref {
    type string;
    description
      "This type is used by data models that need to reference
       configured openconfig-interfaces.";
  }

  typedef ncs_template_event-type {
    type string;
    description
      "A generic event type describing the type of events/notifications triggered by interface.";
  }

  typedef ncs_template_reason-type {
    type string;
    description
      "A generic event type describing the reason for an operational-state change.";
  }

  typedef ncs_rpc_notif_ciena-openconfig-interface-ref {
    type string;
    description
      "This type is used by data models that need to reference
       configured openconfig-interfaces.";
  }

  typedef ncs_rpc_notif_event-type {
    type enumeration {
      enum "operational-state" {
        description
          "Interface operational state change (link state, error state).";
      }
      enum "ettp-capability-state" {
        description
          "ETTP capability state change.";
      }
      enum "any" {
        description
          "An enum value used by notification registrants to specify any of the enumerated values in the enumeration list.";
      }
    }
    description
      "A generic event type describing the type of events/notifications triggered by interface.";
  }

  typedef ncs_rpc_notif_reason-type {
    type enumeration {
      enum "admin-state-change" {
        description
          "Operational State changed due to admin-state config change.";
      }
      enum "speed-compatibility" {
        description
          "Operational state changed due to underlying speed compatibility change.";
      }
      enum "other" {
        description
          "Operational State changed due to dependent component.";
      }
      enum "ip-interface-delete" {
        description
          "IP interface deleted.";
      }
    }
    description
      "A generic event type describing the reason for an operational-state change.";
  }

  typedef live_ncs_ciena-openconfig-interface-ref {
    type leafref {
      path "/ncs:devices/ncs:device/ncs:live-status/oc-if:interfaces/oc-if:interface/oc-if:name" {
        tailf:xpath-root 3;
      }
    }
    description
      "This type is used by data models that need to reference
       configured openconfig-interfaces.";
  }

  typedef live_ncs_event-type {
    type enumeration {
      enum "operational-state" {
        description
          "Interface operational state change (link state, error state).";
      }
      enum "ettp-capability-state" {
        description
          "ETTP capability state change.";
      }
      enum "any" {
        description
          "An enum value used by notification registrants to specify any of the enumerated values in the enumeration list.";
      }
    }
    description
      "A generic event type describing the type of events/notifications triggered by interface.";
  }

  typedef live_ncs_reason-type {
    type enumeration {
      enum "admin-state-change" {
        description
          "Operational State changed due to admin-state config change.";
      }
      enum "speed-compatibility" {
        description
          "Operational state changed due to underlying speed compatibility change.";
      }
      enum "other" {
        description
          "Operational State changed due to dependent component.";
      }
      enum "ip-interface-delete" {
        description
          "IP interface deleted.";
      }
    }
    description
      "A generic event type describing the reason for an operational-state change.";
  }

  typedef ciena-openconfig-interface-ref {
    type leafref {
      path "/ncs:devices/ncs:device/ncs:config/oc-if:interfaces/oc-if:interface/oc-if:name" {
        tailf:xpath-root 3;
      }
    }
    description
      "This type is used by data models that need to reference
       configured openconfig-interfaces.";
  }

  typedef event-type {
    type enumeration {
      enum "operational-state" {
        description
          "Interface operational state change (link state, error state).";
      }
      enum "ettp-capability-state" {
        description
          "ETTP capability state change.";
      }
      enum "any" {
        description
          "An enum value used by notification registrants to specify any of the enumerated values in the enumeration list.";
      }
    }
    description
      "A generic event type describing the type of events/notifications triggered by interface.";
  }

  typedef reason-type {
    type enumeration {
      enum "admin-state-change" {
        description
          "Operational State changed due to admin-state config change.";
      }
      enum "speed-compatibility" {
        description
          "Operational state changed due to underlying speed compatibility change.";
      }
      enum "other" {
        description
          "Operational State changed due to dependent component.";
      }
      enum "ip-interface-delete" {
        description
          "IP interface deleted.";
      }
    }
    description
      "A generic event type describing the reason for an operational-state change.";
  }

  grouping ncs_template_tunnel {
    description
      "Parameters relating to a tunnel interface.";
    leaf type {
      type string;
      description
        "Diffrent types of tunnel inetrface.";
    }
    leaf source {
      // NCS drop when statement
      type string;
      description
        "The source address that should be used for the
         tunnel.";
    }
    leaf destination {
      // NCS drop when statement
      type string;
      description
        "The destination address for the tunnel.";
    }
  }

  grouping ncs_rpc_notif_tunnel {
    description
      "Parameters relating to a tunnel interface.";
    leaf type {
      type enumeration {
        enum "vti" {
          description
            "Virtual tunnel interface type";
        }
      }
      description
        "Diffrent types of tunnel inetrface.";
    }
    leaf source {
      when "../cn-if:type='vti'" {
        tailf:xpath-root 3;
      }
      type inet:ipv4-address-no-zone;
      description
        "The source address that should be used for the
         tunnel.";
    }
    leaf destination {
      when "../cn-if:type='vti'" {
        tailf:xpath-root 3;
      }
      type inet:ipv4-address-no-zone;
      description
        "The destination address for the tunnel.";
    }
  }

  grouping live_ncs_tunnel {
    description
      "Parameters relating to a tunnel interface.";
    leaf type {
      type enumeration {
        enum "vti" {
          description
            "Virtual tunnel interface type";
        }
      }
      description
        "Diffrent types of tunnel inetrface.";
    }
    leaf source {
      // NCS drop when statement
      type inet:ipv4-address-no-zone;
      description
        "The source address that should be used for the
         tunnel.";
    }
    leaf destination {
      // NCS drop when statement
      type inet:ipv4-address-no-zone;
      description
        "The destination address for the tunnel.";
    }
  }

  grouping tunnel {
    description
      "Parameters relating to a tunnel interface.";
    leaf type {
      type enumeration {
        enum "vti" {
          description
            "Virtual tunnel interface type";
        }
      }
      description
        "Diffrent types of tunnel inetrface.";
    }
    leaf source {
      when "../cn-if:type='vti'" {
        tailf:xpath-root 3;
      }
      type inet:ipv4-address-no-zone;
      description
        "The source address that should be used for the
         tunnel.";
    }
    leaf destination {
      when "../cn-if:type='vti'" {
        tailf:xpath-root 3;
      }
      type inet:ipv4-address-no-zone;
      description
        "The destination address for the tunnel.";
    }
  }

  augment "/ncs:devices/ncs:device/ncs:rpc" {
    container rpc-interfaces-clear-statistics {
      tailf:ncs-device-type "netconf";
      tailf:display-when "not(../../ncs:module) or ../../ncs:module[ncs:name='ciena-openconfig-interfaces']";
      tailf:action interfaces-clear-statistics {
        tailf:actionpoint ncsproxy {
          tailf:internal;
        }
        description
          "An RPC operation to clear the statistics for one or all Interfaces.";
        input {
          choice clear-scope {
            case interface {
              leaf interface {
                type string;
              }
              description
                "Clear stats for this interface.";
            }
            case all {
              leaf all {
                type empty;
              }
              description
                "Clear stats for all interfaces.";
            }
          }
        }
        output {
          leaf status {
            type string;
            description
              "Status of the clear statistics operation.";
          }
        }
      }
    }
  }
  augment "/ncs:devices/ncs:device-group/ncs:ned-id/ncs:rpc" {
    container rpc-interfaces-clear-statistics {
      tailf:ncs-device-type "netconf";
      tailf:display-when "/ncs:devices/ncs:device[ncs:name=current()/../../../ncs:member]/ncs:module[ncs:name='ciena-openconfig-interfaces']";
      tailf:action interfaces-clear-statistics {
        tailf:actionpoint ncsproxy {
          tailf:internal;
        }
        description
          "An RPC operation to clear the statistics for one or all Interfaces.";
        input {
          choice clear-scope {
            case interface {
              leaf interface {
                type string;
              }
              description
                "Clear stats for this interface.";
            }
            case all {
              leaf all {
                type empty;
              }
              description
                "Clear stats for all interfaces.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:netconf-notifications/ncs:received-notifications/ncs:notification/ncs:data" {
    container interface-events {
      presence "";
      config false;
      list interface-event {
        description
          "Defines interface related events and associated data used to publish change in the state of the interface instance.";
        leaf interface-type {
          type string;
          description
            "The interface-type for the notification. 'any' means any interface-type";
        }
        list name-list {
          leaf name {
            type string;
            description
              "The interface-name for the notification. '*' means any interface-name";
          }
          list event-list {
            leaf event-type {
              type string;
              description
                "The event-type for the notification. 'any' means any event-type";
            }
          }
        }
        leaf operational-state {
          type string;
          description
            "interface operational state change (link state).";
        }
        leaf speed-compatibility {
          type string;
          description
            "speed compatibility state change.";
        }
        leaf reason {
          type ncs_rpc_notif_reason-type;
          description
            "Reason for operational state change";
        }
      }
    }
  }
  augment "/ncs:devices/ncs:device/ncs:config" {
    // NCS drop config false container 'interface-telemetry-state'
  }
  augment "/ncs:devices/ncs:device/ncs:live-status" {
    container interface-telemetry-state {
      tailf:ncs-device-type "netconf";
      tailf:display-when "not(../../ncs:module) or ../../ncs:module[ncs:name='ciena-openconfig-interfaces'] or (../../ncs:live-status-protocol[not(ncs:capability)]) or (../../ncs:live-status-protocol/ncs:capability/ncs:module[.='ciena-openconfig-interfaces'])";
      list interface-counters {
        description
          "Defines interface related events and associated data used to publish change in the state of the interface instance.";
        leaf interface-type {
          type leafref {
            path "/ncs:devices/ncs:device/ncs:live-status/oc-if:interfaces/oc-if:interface/oc-if:config/cn-if:type" {
              tailf:xpath-root 3;
            }
          }
          description
            "The interface-type for the state. 'any' means any interface-type";
        }
        list interfaces {
          leaf if-name {
            type leafref {
              path "/ncs:devices/ncs:device/ncs:live-status/oc-if:interfaces/oc-if:interface/oc-if:name" {
                tailf:xpath-root 3;
              }
            }
            description
              "The interface-name for the xpath definition. '*' means any interface-name";
          }
          uses oc-if:live_ncs_interface-common-state;
          uses oc-if:live_ncs_interface-counters-state;
        }
      }
    }
  }
  augment "/ncs:devices/ncs:template/ncs:ned-id/ncs:config" {
    // NCS drop config false container 'interface-telemetry-state'
  }
  augment "/ncs:devices/ncs:template/ncs:ned-id/ncs:config/oc-if:interfaces/oc-if:interface/oc-if:config" {
    leaf type {
      ncx:user-write "create";
      type string;
    }
    leaf admin-status {
      // NCS drop when statement
      type string;
      // NCS drop default statement
      description
        "[adapted from IETF interfaces model (RFC 7223)]

         This leaf contains the configured, desired state of the
         interface.

         Systems that implement the IF-MIB use the value of this
         leaf in the 'running' datastore to set
         IF-MIB.ifAdminStatus to 'up' or 'down' after an ifEntry
         has been initialized, as described in RFC 2863.

         Changes in this leaf in the 'running' datastore are
         reflected in ifAdminStatus, but if ifAdminStatus is
         changed over SNMP, this leaf is not affected.";
      reference "RFC 2863: The Interfaces Group MIB - ifAdminStatus";
    }
    leaf role {
      ncx:user-write "create delete";
      // NCS drop when statement
      type string;
      // NCS drop default statement
    }
    leaf vrfName {
      // NCS drop when statement
      type string;
      // NCS drop default statement
      description
        "Provides interface to parent VRF binding.";
    }
    leaf virtual-mac {
      // NCS drop when statement
      type string;
      description
        "Virtual mac-address on layer 3 interface.";
    }
    choice frame-to-cos {
      // NCS drop when statement
      // NCS drop default statement
      case map {
        leaf map-policy {
          type string;
        }
        leaf frame-to-cos-map {
          type ftc:ncs_template_frame-to-cos-ref;
          // NCS drop default statement
        }
      }
      case fixed {
        leaf cos {
          type string;
        }
        leaf color {
          type string;
        }
      }
    }
    leaf cos-to-frame-map {
      // NCS drop when statement
      type ctf:ncs_template_cos-to-frame-ref;
      // NCS drop default statement
    }
    leaf stats-collection {
      // NCS drop when statement
      type string;
      // NCS drop default statement
    }
    leaf access-profile {
      // NCS drop when statement
      type acl:ncs_template_access-profile-ref;
      // NCS drop must statement
      description
        "Specifies the Access-Profile for this IP interface";
    }
    container tunnel {
      // NCS drop when statement
      description
        "In the case that the interface is logical tunnel
         interface, the parameters for the tunnel are
         specified within this subtree. Tunnel interfaces
         have only a single logical subinterface associated
         with them.";
      container config {
        description
          "Configuration parameters associated with the
           tunnel interface";
        uses ncs_template_tunnel;
      }
    }
  }
  augment "/ncs:devices/ncs:device/ncs:live-status/oc-if:interfaces/oc-if:interface/oc-if:config" {
    leaf type {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      ncx:user-write "create";
      type enumeration {
        enum "ip" {
          value 1;
          description
            "Specifies an layer 3 interface.";
        }
        enum "ettp" {
          value 2;
          description
            "Specifies an underlay layer 2 interface.";
        }
        enum "lag" {
          value 3;
          description
            "Specifies an underlay layer 2 interface.";
        }
        enum "loopback" {
          value 4;
          description
            "A virtual interface designated as a loopback used for various tasks.";
        }
        enum "system" {
          value 5;
          description
            "A management interface provided by the system.";
        }
        enum "ip-unnumbered" {
          value 6;
          description
            "Specifies an layer 3 unnumbered interface.";
        }
        enum "ip-tunnel" {
          value 7;
          description
            "Specifies an IP tunnel interface";
        }
        enum "any" {
          value 999;
          // NCS drop if-feature statement
          description
            "Only used by notification registrants to specify any of the
             enumerated values in the enumeration list.";
        }
      }
    }
    leaf admin-status {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type boolean;
      // NCS drop default statement
      description
        "[adapted from IETF interfaces model (RFC 7223)]

         This leaf contains the configured, desired state of the
         interface.

         Systems that implement the IF-MIB use the value of this
         leaf in the 'running' datastore to set
         IF-MIB.ifAdminStatus to 'up' or 'down' after an ifEntry
         has been initialized, as described in RFC 2863.

         Changes in this leaf in the 'running' datastore are
         reflected in ifAdminStatus, but if ifAdminStatus is
         changed over SNMP, this leaf is not affected.";
      reference "RFC 2863: The Interfaces Group MIB - ifAdminStatus";
    }
    leaf role {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      ncx:user-write "create delete";
      // NCS drop when statement
      type identityref {
        base INTERFACE_ROLE;
      }
      // NCS drop default statement
    }
    leaf vrfName {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type leafref {
        path "/ncs:devices/ncs:device/ncs:live-status/vrf:vrf/vrf:vrfName" {
          tailf:xpath-root 3;
        }
      }
      // NCS drop default statement
      description
        "Provides interface to parent VRF binding.";
    }
    leaf virtual-mac {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type leafref {
        path "/ncs:devices/ncs:device/ncs:live-status/mef-mac-management:virtual-macs/mef-mac-management:mac-entry/mef-mac-management:mac-address" {
          tailf:xpath-root 3;
        }
      }
      description
        "Virtual mac-address on layer 3 interface.";
    }
    choice frame-to-cos {
      // NCS drop when statement
      // NCS drop default statement
      case map {
        leaf map-policy {
          type enumeration {
            enum "dscp" {
              description
                "Map to internal cos and color based on dscp field of IP of
                 L3-frame (if IP present). Any L3 frame which is non-IP is
                 considered non-conforming from frame-to-cos map perspective,
                 and the resolution to an internal cos and color is platform
                 specific for non-conforming frames.";
            }
          }
        }
        leaf frame-to-cos-map {
          type ftc:live_ncs_frame-to-cos-ref;
          // NCS drop default statement
        }
      }
      case fixed {
        leaf cos {
          type uint8 {
            range "0..63";
          }
        }
        leaf color {
          type enumeration {
            enum "green";
            enum "yellow";
            enum "red";
          }
        }
      }
    }
    leaf cos-to-frame-map {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type ctf:live_ncs_cos-to-frame-ref;
      // NCS drop default statement
    }
    leaf stats-collection {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type enumeration {
        enum "on" {
          value 1;
          description
            "Specifies counter status on interface is ON";
        }
        enum "off" {
          value 2;
          description
            "Specifies counter status on interface is OFF";
        }
      }
      // NCS drop default statement
    }
    leaf access-profile {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      type acl:live_ncs_access-profile-ref;
      // NCS drop must statement
      description
        "Specifies the Access-Profile for this IP interface";
    }
    container tunnel {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      // NCS drop when statement
      description
        "In the case that the interface is logical tunnel
         interface, the parameters for the tunnel are
         specified within this subtree. Tunnel interfaces
         have only a single logical subinterface associated
         with them.";
      container config {
        description
          "Configuration parameters associated with the
           tunnel interface";
        uses live_ncs_tunnel;
      }
    }
  }
  augment "/ncs:devices/ncs:device/ncs:config/oc-if:interfaces/oc-if:interface/oc-if:config" {
    leaf type {
      tailf:ncs-device-type "netconf";
      tailf:display-when "not(../../../../../ncs:module) or ../../../../../ncs:module[ncs:name='ciena-openconfig-interfaces']";
      ncx:user-write "create";
      type enumeration {
        enum "ip" {
          value 1;
          description
            "Specifies an layer 3 interface.";
        }
        enum "ettp" {
          value 2;
          description
            "Specifies an underlay layer 2 interface.";
        }
        enum "lag" {
          value 3;
          description
            "Specifies an underlay layer 2 interface.";
        }
        enum "loopback" {
          value 4;
          description
            "A virtual interface designated as a loopback used for various tasks.";
        }
        enum "system" {
          value 5;
          description
            "A management interface provided by the system.";
        }
        enum "ip-unnumbered" {
          value 6;
          description
            "Specifies an layer 3 unnumbered interface.";
        }
        enum "ip-tunnel" {
          value 7;
          description
            "Specifies an IP tunnel interface";
        }
        enum "any" {
          value 999;
          // NCS drop if-feature statement
          description
            "Only used by notification registrants to specify any of the
             enumerated values in the enumeration list.";
        }
      }
    }
    leaf admin-status {
      tailf:ncs-device-type "netconf";
      tailf:display-when "not(../../../../../ncs:module) or ../../../../../ncs:module[ncs:name='ciena-openconfig-interfaces']";
      when "../cn-if:type[.='ettp' or .='ip' or .='system' or .='loopback' or .='ip-unnumbered' or .='ip-tunnel']" {
        tailf:xpath-root 3;
      }
      type boolean;
      default "true";
      description
        "[adapted from IETF interfaces model (RFC 7223)]

         This leaf contains the configured, desired state of the
         interface.

         Systems that implement the IF-MIB use the value of this
         leaf in the 'running' datastore to set
         IF-MIB.ifAdminStatus to 'up' or 'down' after an ifEntry
         has been initialized, as described in RFC 2863.

         Changes in this leaf in the 'running' datastore are
         reflected in ifAdminStatus, but if ifAdminStatus is
         changed over SNMP, this leaf is not affected.";
      reference "RFC 2863: The Interfaces Group MIB - ifAdminStatus";
    }
    leaf role {
      tailf:ncs-device-type "netconf";
      tailf:display-when "not(../../../../../ncs:module) or ../../../../../ncs:module[ncs:name='ciena-openconfig-interfaces']";
      ncx:user-write "create delete";
      when "../cn-if:type[.='ip' or .='system' or .='loopback']" {
        tailf:xpath-root 3;
      }
      type identityref {
        base INTERFACE_ROLE;
      }
      default "data";
    }
    leaf vrfName {
      tailf:ncs-device-type "netconf";
      tailf:display-when "not(../../../../../ncs:module) or ../../../../../ncs:module[ncs:name='ciena-openconfig-interfaces']";
      when "../cn-if:type[.='loopback' or .='ip' or .='system' or .='ip-unnumbered']" {
        tailf:xpath-root 3;
      }
      type leafref {
        path "/ncs:devices/ncs:device/ncs:config/vrf:vrf/vrf:vrfName" {
          tailf:xpath-root 3;
        }
      }
      default "default";
      description
        "Provides interface to parent VRF binding.";
    }
    leaf virtual-mac {
      tailf:ncs-device-type "netconf";
      tailf:display-when "not(../../../../../ncs:module) or ../../../../../ncs:module[ncs:name='ciena-openconfig-interfaces']";
      when "../cn-if:type[.='ip' or .='ip-unnumbered']" {
        tailf:xpath-root 3;
      }
      type leafref {
        path "/ncs:devices/ncs:device/ncs:config/mef-mac-management:virtual-macs/mef-mac-management:mac-entry/mef-mac-management:mac-address" {
          tailf:xpath-root 3;
        }
      }
      description
        "Virtual mac-address on layer 3 interface.";
    }
    choice frame-to-cos {
      when "cn-if:type[.='ip' or .='ip-unnumbered']" {
        tailf:xpath-root 3;
      }
      default "map";
      case map {
        leaf map-policy {
          type enumeration {
            enum "dscp" {
              description
                "Map to internal cos and color based on dscp field of IP of
                 L3-frame (if IP present). Any L3 frame which is non-IP is
                 considered non-conforming from frame-to-cos map perspective,
                 and the resolution to an internal cos and color is platform
                 specific for non-conforming frames.";
            }
          }
        }
        leaf frame-to-cos-map {
          type ftc:frame-to-cos-ref;
          default "default-f2c";
        }
      }
      case fixed {
        leaf cos {
          type uint8 {
            range "0..63";
          }
        }
        leaf color {
          type enumeration {
            enum "green";
            enum "yellow";
            enum "red";
          }
        }
      }
    }
    leaf cos-to-frame-map {
      tailf:ncs-device-type "netconf";
      tailf:display-when "not(../../../../../ncs:module) or ../../../../../ncs:module[ncs:name='ciena-openconfig-interfaces']";
      when "../cn-if:type[.='ip' or .='ip-unnumbered']" {
        tailf:xpath-root 3;
      }
      type ctf:cos-to-frame-ref;
      default "default-c2f";
    }
    leaf stats-collection {
      tailf:ncs-device-type "netconf";
      tailf:display-when "not(../../../../../ncs:module) or ../../../../../ncs:module[ncs:name='ciena-openconfig-interfaces']";
      when "../cn-if:type[.='ip' or .='ip-unnumbered']" {
        tailf:xpath-root 3;
      }
      type enumeration {
        enum "on" {
          value 1;
          description
            "Specifies counter status on interface is ON";
        }
        enum "off" {
          value 2;
          description
            "Specifies counter status on interface is OFF";
        }
      }
      default "on";
    }
    leaf access-profile {
      tailf:ncs-device-type "netconf";
      tailf:display-when "not(../../../../../ncs:module) or ../../../../../ncs:module[ncs:name='ciena-openconfig-interfaces']";
      when "../cn-if:type[.='ip' or .='ip-unnumbered']" {
        tailf:xpath-root 3;
      }
      type acl:access-profile-ref;
      must "/acl:access-profiles/acl:access-profile[acl:name=current()]/acl:type = 'IP-interface'" {
        tailf:xpath-root 3;
        error-message "Referenced type is not supported.";
      }
      description
        "Specifies the Access-Profile for this IP interface";
    }
    container tunnel {
      tailf:ncs-device-type "netconf";
      tailf:display-when "not(../../../../../ncs:module) or ../../../../../ncs:module[ncs:name='ciena-openconfig-interfaces']";
      when "../cn-if:type='ip-tunnel'" {
        tailf:xpath-root 3;
      }
      description
        "In the case that the interface is logical tunnel
         interface, the parameters for the tunnel are
         specified within this subtree. Tunnel interfaces
         have only a single logical subinterface associated
         with them.";
      container config {
        description
          "Configuration parameters associated with the
           tunnel interface";
        uses tunnel;
      }
    }
  }
  augment "/ncs:devices/ncs:device/ncs:live-status/oc-if:interfaces/oc-if:interface/oc-if:state" {
    leaf type {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type enumeration {
        enum "ip" {
          value 1;
          description
            "Specifies an layer 3 interface.";
        }
        enum "ettp" {
          value 2;
          description
            "Specifies an underlay layer 2 interface.";
        }
        enum "lag" {
          value 3;
          description
            "Specifies an underlay layer 2 interface.";
        }
        enum "loopback" {
          value 4;
          description
            "A virtual interface designated as a loopback used for various tasks.";
        }
        enum "system" {
          value 5;
          description
            "A management interface provided by the system.";
        }
        enum "ip-unnumbered" {
          value 6;
          description
            "Specifies an layer 3 unnumbered interface.";
        }
        enum "ip-tunnel" {
          value 7;
          description
            "Specifies an IP tunnel interface";
        }
        enum "any" {
          value 999;
          // NCS drop if-feature statement
          description
            "Only used by notification registrants to specify any of the
             enumerated values in the enumeration list.";
        }
      }
    }
    leaf admin-status {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type boolean;
      // NCS drop default statement
      description
        "[adapted from IETF interfaces model (RFC 7223)]

         This leaf contains the configured, desired state of the
         interface.

         Systems that implement the IF-MIB use the value of this
         leaf in the 'running' datastore to set
         IF-MIB.ifAdminStatus to 'up' or 'down' after an ifEntry
         has been initialized, as described in RFC 2863.

         Changes in this leaf in the 'running' datastore are
         reflected in ifAdminStatus, but if ifAdminStatus is
         changed over SNMP, this leaf is not affected.";
      reference "RFC 2863: The Interfaces Group MIB - ifAdminStatus";
    }
    leaf role {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type identityref {
        base INTERFACE_ROLE;
      }
    }
    leaf vrfName {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type string;
      // NCS drop default statement
      description
        "Provides interface to parent VRF binding.";
    }
    leaf mac-address {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type ietf-yt:mac-address;
      description
        "The operational MAC address of this interface.";
    }
    leaf dhcp-v4-ip {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type inet:ipv4-address-no-zone;
      description
        "[adapted from IETF IP model RFC 7277]

         The DHCP acquired IPv4 address on the interface.";
    }
    leaf dhcp-v4-prefix-length {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type uint8 {
        range "0..32";
      }
      description
        "[adapted from IETF IP model RFC 7277]

         The DHCP acquired length of the subnet prefix.";
    }
    leaf dhcp-v4-client {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type boolean;
      // NCS drop default statement
      description
        "This leaf node specifies whether the ipv4 address was acquired via dhcp.";
    }
    leaf dhcp-v6-ip {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type inet:ipv6-address-no-zone;
      description
        "[adapted from IETF IP model RFC 7277]

         The DHCP acquired IPv6 address on the interface.";
    }
    leaf dhcp-v6-prefix-length {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type uint8 {
        range "0..128";
      }
      description
        "[adapted from IETF IP model RFC 7277]

         The DHCP acquired length of the subnet prefix.";
    }
    leaf dhcp-v6-client {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type boolean;
      // NCS drop default statement
      description
        "This leaf node specifies whether the ipv6 address was acquired via dhcpv6.";
    }
    leaf link-local-v6-ip {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type inet:ipv6-address-no-zone;
      description
        "[adapted from IETF IP model RFC 7277]

         The link local acquired IPv6 address on the interface.";
    }
    leaf link-local-v6-prefix-length {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type uint8 {
        range "0..128";
      }
      description
        "[adapted from IETF IP model RFC 7277]

         The link local acquired length of the subnet prefix.";
    }
    leaf access-profile {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type acl:live_ncs_access-profile-ref;
      description
        "Specifies the Access-Profile for this IP interface";
    }
    leaf speed-compatibility {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      type boolean;
      description
        "false means that ETTP configured speed is incompatible with underlying layer (e.g. XCVR).
         true means that ETTP configured speed is compatible with underlying layer (e.g. XCVR)";
    }
    container tunnel {
      tailf:ncs-device-type "netconf";
      tailf:display-when "not(../../../../../ncs:module) or ../../../../../ncs:module[ncs:name='ciena-openconfig-interfaces'] or (../../../../../ncs:live-status-protocol[not(ncs:capability)]) or (../../../../../ncs:live-status-protocol/ncs:capability/ncs:module[.='ciena-openconfig-interfaces'])";
      description
        "Operational state parameters associated with
         the tunnel interface.";
      uses live_ncs_tunnel;
    }
  }
  augment "/ncs:devices/ncs:device/ncs:live-status/oc-if:interfaces/oc-if:interface/oc-if:state/oc-if:counters" {
    leaf in-pkts {
      tailf:ncs-device-type "netconf";
      tailf:display-when "not(../../../../../../ncs:module) or ../../../../../../ncs:module[ncs:name='ciena-openconfig-interfaces'] or (../../../../../../ncs:live-status-protocol[not(ncs:capability)]) or (../../../../../../ncs:live-status-protocol/ncs:capability/ncs:module[.='ciena-openconfig-interfaces'])";
      type ietf-yt:counter64;
      description
        "The number of packets, delivered by this sub-layer to a
         higher (sub-)layer, that were addressed to an unicast,
         multicast and broadcast address at this sub-layer.";
    }
    leaf out-pkts {
      tailf:ncs-device-type "netconf";
      tailf:display-when "not(../../../../../../ncs:module) or ../../../../../../ncs:module[ncs:name='ciena-openconfig-interfaces'] or (../../../../../../ncs:live-status-protocol[not(ncs:capability)]) or (../../../../../../ncs:live-status-protocol/ncs:capability/ncs:module[.='ciena-openconfig-interfaces'])";
      type ietf-yt:counter64;
      description
        "The total number of packets that higher-level protocols
          requested be transmitted, and that were addressed
          to a unicast, multicast and a broadcast address at this sub-layer.";
    }
    leaf in-dropped-octets {
      tailf:ncs-device-type "netconf";
      tailf:display-when "not(../../../../../../ncs:module) or ../../../../../../ncs:module[ncs:name='ciena-openconfig-interfaces'] or (../../../../../../ncs:live-status-protocol[not(ncs:capability)]) or (../../../../../../ncs:live-status-protocol/ncs:capability/ncs:module[.='ciena-openconfig-interfaces'])";
      type ietf-yt:counter64;
      description
        "The number of inbound octets that were chosen to be
         dropped even though no errors had been detected to
         prevent their being deliverable to a higher-layer
         protocol.";
    }
    leaf in-dropped-pkts {
      tailf:ncs-device-type "netconf";
      tailf:display-when "not(../../../../../../ncs:module) or ../../../../../../ncs:module[ncs:name='ciena-openconfig-interfaces'] or (../../../../../../ncs:live-status-protocol[not(ncs:capability)]) or (../../../../../../ncs:live-status-protocol/ncs:capability/ncs:module[.='ciena-openconfig-interfaces'])";
      type ietf-yt:counter64;
      description
        "The number of inbound packets that were chosen to be
         dropped even though no errors had been detected to
         prevent their being deliverable to a higher-layer
         protocol.";
    }
  }
  augment "/ncs:devices/ncs:template/ncs:ned-id/ncs:config/oc-if:interfaces/oc-if:interface" {
    // NCS drop config false leaf 'if-event-type'
  }
  augment "/ncs:devices/ncs:device/ncs:live-status/oc-if:interfaces/oc-if:interface" {
    leaf if-event-type {
      tailf:ncs-device-type "netconf";
      tailf:display-when "not(../../../../ncs:module) or ../../../../ncs:module[ncs:name='ciena-openconfig-interfaces'] or (../../../../ncs:live-status-protocol[not(ncs:capability)]) or (../../../../ncs:live-status-protocol/ncs:capability/ncs:module[.='ciena-openconfig-interfaces'])";
      type live_ncs_event-type;
      description
        "Defines the set of event types corresponding to the interface state changes.";
    }
  }
  augment "/ncs:devices/ncs:device/ncs:config/oc-if:interfaces/oc-if:interface" {
    // NCS drop config false leaf 'if-event-type'
  }

  identity data {
    base INTERFACE_ROLE;
    description
      "Specifies that the interface is of type data.";
  }

  identity management {
    base INTERFACE_ROLE;
    description
      "Specifies that the interface is of type management.";
  }

  identity connectivity {
    base INTERFACE_ROLE;
    description
      "Specifies that the interface is used for connectivity validation.";
  }

  identity INTERFACE_ROLE {
    description
      "Base identity for the layer 3 roles.";
  }

  feature cn-notification {
    description
      "This feature indicates that notification is supported.";
  }
}
