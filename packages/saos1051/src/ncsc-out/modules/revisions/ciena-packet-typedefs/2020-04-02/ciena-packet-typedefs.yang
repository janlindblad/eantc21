module ciena-packet-typedefs {
  // Generated by yanger -t ncs
  tailf:mount-id "saos1051-nc-1.0:saos1051-nc-1.0";
  tailf:ncs-device-type "netconf";

  namespace "http://www.ciena.com/ns/yang/ciena-packet-typedefs";
  prefix cntypes;

  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's commonly used typedefs";

  revision 2020-04-02 {
    description
      "Added new XCVR modes for TDM native ports.
       Added new XCVR types QSFP56 and QSFPDD.
       Added new XCVR mode 200GE.
       Updated lanes-number range from 0..4 to 0..8
       Added new XCVR type SFP28.";
  }
  revision 2020-01-10 {
    description
      "Added fingerprint types";
  }
  revision 2019-10-10 {
    description
      "Added new values to xcvr-mode and xcvr-type enums.";
  }
  revision 2019-03-20 {
    description
      "Added Xcvr types and mode";
  }
  revision 2018-05-17 {
    description
      "Based off of ciena-waveserver-typedefs.yang";
  }

  typedef ncs_template_fingerprint {
    type string;
    description
      "SHA-1 or SHA-256 fingerprint";
  }

  typedef ncs_template_mac-string {
    type string;
    description
      "MAC address string.";
  }

  typedef ncs_template_name-string {
    type string;
    description
      "String type for object names used in Ciena defined modules. It must be a
       non empty string that is at most 32 characters long.";
  }

  typedef ncs_template_description-string {
    type string;
    description
      "String type for description used in Ciena defined modules. Max length of
       128 characters, plus null.";
  }

  typedef ncs_template_on-off-enum {
    type string;
    description
      "Off and On enum toggle used in Ciena defined modules.";
  }

  typedef ncs_template_power-state {
    type string;
    description
      "Power state automatic (on/normal) or shutdown (off/low-power-mode).";
  }

  typedef ncs_template_yes-no-enum {
    type string;
    description
      "No and Yes enum toggle used in Ciena defined modules.";
  }

  typedef ncs_template_up-down-enum {
    type string;
    description
      "Down and Up enum toggle used in Ciena defined modules.";
  }

  typedef ncs_template_enabled-disabled-enum {
    type string;
    description
      "Enabled and Disabled enum toggle used in Ciena defined modules.";
  }

  typedef ncs_template_ettp-fec-enum {
    type string;
    description
      "Different state for Ettp forward-error-correction";
  }

  typedef ncs_template_yes-no-na-enum {
    type string;
    description
      "No and Yes enum toggle used in Ciena defined modules.";
  }

  typedef ncs_template_enabled-disabled-na-enum {
    type string;
    description
      "Enabled, Disabled, and not-applicable enum used in Ciena defined modules.";
  }

  typedef ncs_template_wl-spacing {
    type string;
    description
      "Wavelength spacing, 50GHz, 100GHz, 200GHz, or flex-grid. Only 'flex-grid'
       supported in Waveserver Ai R1.0.";
  }

  typedef ncs_template_decimal-3-dig {
    type string;
    description
      "Decimal value up to 3 digits.";
  }

  typedef ncs_template_decimal-2-dig-small {
    type string;
    description
      "Decimal value up to 2 digits.";
  }

  typedef ncs_template_decimal-2-dig {
    type string;
    description
      "Decimal value up to 2 digits.";
  }

  typedef ncs_template_decimal-1-dig {
    type string;
    description
      "Decimal value up to 1 digits.";
  }

  typedef ncs_template_string-sci {
    type string;
    description
      "String in Scientific Notation format with a max length of 32 characters.";
  }

  typedef ncs_template_string-maxl-15 {
    type string;
    description
      "Standard string that has a max length of 15 characters. Can be used for
       various nodes that may require string of this length.";
  }

  typedef ncs_template_string-maxl-16 {
    type string;
    description
      "Standard string that has a max length of 16 characters. Can be used for
       various nodes that may require string of this length.";
  }

  typedef ncs_template_string-maxl-32 {
    type string;
    description
      "Standard string that has a max length of 32 characters. Can be used for
       various nodes that may require string of this length.";
  }

  typedef ncs_template_string-maxl-44 {
    type string;
    description
      "Standard string that has a max length of 44 characters. Can be used for
       various nodes that may require string of this length.";
  }

  typedef ncs_template_string-maxl-50 {
    type string;
    description
      "Standard string that has a max length of 50 characters. Can be used for
       various nodes that may require string of this length.";
  }

  typedef ncs_template_string-maxl-64 {
    type string;
    description
      "Standard string that has a max length of 64 characters. Can be used for
       various nodes that may require string of this length.";
  }

  typedef ncs_template_string-maxl-128 {
    type string;
    description
      "Standard string that has a max length of 128 characters. Can be used for
       various nodes that may require string of this length.";
  }

  typedef ncs_template_string-maxl-254 {
    type string;
    description
      "Standard string that has a max length of 254 characters. Can be used for
       various nodes that may require string of this length.";
  }

  typedef ncs_template_string-maxl-256 {
    type string;
    description
      "Standard string that has a max length of 256 characters. Can be used for
       various nodes that may require string of this length.";
  }

  typedef ncs_template_ipaddr-or-hostname {
    type string;
    description
      "IP address or hostname string.";
  }

  typedef ncs_template_ipv4-address {
    type string;
    description
      "An IPv4 address represented in dotted decimal notation.";
  }

  typedef ncs_template_ipv4-prefix {
    type string;
    description
      "An IPv4 address and prefix represented in dotted decimal notation
       followed by a slash and a prefix length, e.g. '192.168.1.2/24'.";
  }

  typedef ncs_template_ipv4-opt-prefix {
    type string;
    description
      "A string type matching either the ipv4-address format or the
       ipv4-prefix format. That is, an IPv4 address in dotted decimal
       notation with an optional slash and prefix length.";
  }

  typedef ncs_template_port-name {
    type string;
    description
      "A string representing a port interface name. Format is: '<slot>-<port>'
       or '<slot>-<majorport>.<minorport>'.";
  }

  typedef ncs_template_service-idx {
    type string;
    description
      "Service Index";
  }

  typedef ncs_template_service-domain-idx {
    type string;
    description
      "Service Domain Index";
  }

  typedef ncs_template_xcvr-type {
    type string;
    description
      "Transceiver type.";
  }

  typedef ncs_template_xcvr-mode {
    type string;
    description
      "Transceiver mode.";
  }

  typedef ncs_template_xcvr-fec-type {
    type string;
    description
      "Transceiver FEC type.";
  }

  typedef ncs_template_line-sys-enum {
    type string;
    description
      "Line system type.";
  }

  typedef ncs_template_lanes-number {
    type string;
    description
      "Lane number common type, lane range is defined from 0 to 8.";
  }

  typedef ncs_template_connector-type-desc-enum {
    type string;
    description
      "Human readable description of Vendor's connector type byte value.";
    reference "SFF-8024, table 4-3";
  }

  typedef ncs_template_modem-frequency {
    type string;
    units "GHz";
    description
      "Modem frequency, in GHz. 0.0 indicates unprovisioned (default) value. L-Band
       range is 186087.5 - 190956.2 GHz, and C-Band range is 191100.0 - 196150.0 GHz.";
  }

  typedef ncs_template_modem-class {
    type string;
    description
      "The modem class type, terrestrial or submarine.";
  }

  typedef ncs_template_link-optimization-mode {
    type string;
    description
      "Link Optimization Modes for the WaveLogic modems.";
  }

  typedef ncs_template_supported-link-optimization-modes {
    type string;
    description
      "Type definition for supported link-optimization-mode values for PTPs
       associated with modem XCVR objects.";
  }

  typedef ncs_template_tx-power-lvl {
    type string;
    units "dBm";
    description
      "Modem Tx Power Level.";
  }

  typedef ncs_template_module-type-enum {
    type string;
    description
      "Module type enum.";
  }

  typedef ncs_template_module-type-bits {
    type string;
    description
      "Module type bits.";
  }

  typedef ncs_template_restart-reason {
    type string;
    description
      "Chassis/Module last restart reason.";
  }

  typedef ncs_template_conditioning-type {
    type string;
    description
      "Egress UNI port consequent action for an EPL service to be applied on a
       far-end ingress UNI failure or network failure.";
  }

  typedef ncs_template_conditioning-holdoff {
    type string;
    units "ms";
    description
      "Number of milliseconds to delay Egress UNI port consequent action for an
       EPL service.";
  }

  typedef ncs_template_trace-mismatch-mode {
    type string;
    description
      "The trail trace identifier (TTI) mismatch mode, indicating which fields of
       the TTI overhead are used for trace mismatch detection.";
  }

  typedef ncs_template_trace-mismatch-fail-mode {
    type string;
    description
      "The trail trace identifier (TTI) mismatch failure mode. When TTI mismatch
       condition occurs, this indicates the consequent action taken, e.g. whether
       or not to raise an alarm.";
  }

  typedef ncs_rpc_notif_fingerprint {
    type string {
      pattern '(sha-256:([A-F0-9]{2}:){31}[A-F0-9]{2})|(sha-1:([A-F0-9]{2}:){19}[A-F0-9]{2})';
    }
    description
      "SHA-1 or SHA-256 fingerprint";
  }

  typedef ncs_rpc_notif_mac-string {
    type string {
      length "1..20";
    }
    description
      "MAC address string.";
  }

  typedef ncs_rpc_notif_name-string {
    type string {
      length "1..32";
    }
    description
      "String type for object names used in Ciena defined modules. It must be a
       non empty string that is at most 32 characters long.";
  }

  typedef ncs_rpc_notif_description-string {
    type string {
      length "0..128";
    }
    description
      "String type for description used in Ciena defined modules. Max length of
       128 characters, plus null.";
  }

  typedef ncs_rpc_notif_on-off-enum {
    type enumeration {
      enum "off" {
        description
          "Off";
      }
      enum "on" {
        description
          "On";
      }
    }
    description
      "Off and On enum toggle used in Ciena defined modules.";
  }

  typedef ncs_rpc_notif_power-state {
    type enumeration {
      enum "automatic" {
        description
          "Power state is automatic (on/normal).";
      }
      enum "shutdown" {
        description
          "Power state is shutdown (off/low-power-mode).";
      }
    }
    description
      "Power state automatic (on/normal) or shutdown (off/low-power-mode).";
  }

  typedef ncs_rpc_notif_yes-no-enum {
    type enumeration {
      enum "no" {
        description
          "No";
      }
      enum "yes" {
        description
          "Yes";
      }
    }
    description
      "No and Yes enum toggle used in Ciena defined modules.";
  }

  typedef ncs_rpc_notif_up-down-enum {
    type enumeration {
      enum "down" {
        description
          "Object is down/disabled/failed.";
      }
      enum "up" {
        description
          "Object is up/operational.";
      }
    }
    description
      "Down and Up enum toggle used in Ciena defined modules.";
  }

  typedef ncs_rpc_notif_enabled-disabled-enum {
    type enumeration {
      enum "disabled" {
        description
          "Object or attribute is disabled.";
      }
      enum "enabled" {
        description
          "Object or attribute is enabled.";
      }
    }
    description
      "Enabled and Disabled enum toggle used in Ciena defined modules.";
  }

  typedef ncs_rpc_notif_ettp-fec-enum {
    type enumeration {
      enum "auto" {
        description
          "Object or attribute value is automatic";
      }
      enum "disabled" {
        description
          "Object or attribute is disabled.";
      }
      enum "enabled" {
        description
          "Object or attribute is enabled.";
      }
    }
    description
      "Different state for Ettp forward-error-correction";
  }

  typedef ncs_rpc_notif_yes-no-na-enum {
    type enumeration {
      enum "no" {
        description
          "No";
      }
      enum "yes" {
        description
          "Yes";
      }
      enum "not-applicable" {
        description
          "Not applicable";
      }
    }
    description
      "No and Yes enum toggle used in Ciena defined modules.";
  }

  typedef ncs_rpc_notif_enabled-disabled-na-enum {
    type enumeration {
      enum "disabled" {
        description
          "Disabled";
      }
      enum "enabled" {
        description
          "Enabled";
      }
      enum "not-applicable" {
        description
          "Not applicable";
      }
    }
    description
      "Enabled, Disabled, and not-applicable enum used in Ciena defined modules.";
  }

  typedef ncs_rpc_notif_wl-spacing {
    type enumeration {
      enum "50GHz" {
        description
          "50GHz wavelength spacing.";
      }
      enum "100GHz" {
        description
          "100GHz wavelength spacing.";
      }
      enum "200GHz" {
        description
          "200GHz wavelength spacing.";
      }
      enum "flex-grid" {
        description
          "Flex-grid wavelength spacing.";
      }
    }
    description
      "Wavelength spacing, 50GHz, 100GHz, 200GHz, or flex-grid. Only 'flex-grid'
       supported in Waveserver Ai R1.0.";
  }

  typedef ncs_rpc_notif_decimal-3-dig {
    type decimal64 {
      fraction-digits 3;
      range "-2147483.0 .. 2147483.0";
    }
    description
      "Decimal value up to 3 digits.";
  }

  typedef ncs_rpc_notif_decimal-2-dig-small {
    type decimal64 {
      fraction-digits 2;
      range "-30000.0 .. 30000.0";
    }
    description
      "Decimal value up to 2 digits.";
  }

  typedef ncs_rpc_notif_decimal-2-dig {
    type decimal64 {
      fraction-digits 2;
      range "-21474836.0 .. 21474836.0";
    }
    description
      "Decimal value up to 2 digits.";
  }

  typedef ncs_rpc_notif_decimal-1-dig {
    type decimal64 {
      fraction-digits 1;
      range "-214748364.0 .. 214748364.0";
    }
    description
      "Decimal value up to 1 digits.";
  }

  typedef ncs_rpc_notif_string-sci {
    type string {
      length "0..32";
      pattern '[-+]?[0-9](\.[0-9]+)?([eE][-+]?[0-9]+)?';
    }
    description
      "String in Scientific Notation format with a max length of 32 characters.";
  }

  typedef ncs_rpc_notif_string-maxl-15 {
    type string {
      length "0..15";
    }
    description
      "Standard string that has a max length of 15 characters. Can be used for
       various nodes that may require string of this length.";
  }

  typedef ncs_rpc_notif_string-maxl-16 {
    type string {
      length "0..16";
    }
    description
      "Standard string that has a max length of 16 characters. Can be used for
       various nodes that may require string of this length.";
  }

  typedef ncs_rpc_notif_string-maxl-32 {
    type string {
      length "0..32";
    }
    description
      "Standard string that has a max length of 32 characters. Can be used for
       various nodes that may require string of this length.";
  }

  typedef ncs_rpc_notif_string-maxl-44 {
    type string {
      length "0..44";
    }
    description
      "Standard string that has a max length of 44 characters. Can be used for
       various nodes that may require string of this length.";
  }

  typedef ncs_rpc_notif_string-maxl-50 {
    type string {
      length "0..50";
    }
    description
      "Standard string that has a max length of 50 characters. Can be used for
       various nodes that may require string of this length.";
  }

  typedef ncs_rpc_notif_string-maxl-64 {
    type string {
      length "0..64";
    }
    description
      "Standard string that has a max length of 64 characters. Can be used for
       various nodes that may require string of this length.";
  }

  typedef ncs_rpc_notif_string-maxl-128 {
    type string {
      length "0..128";
    }
    description
      "Standard string that has a max length of 128 characters. Can be used for
       various nodes that may require string of this length.";
  }

  typedef ncs_rpc_notif_string-maxl-254 {
    type string {
      length "0..254";
    }
    description
      "Standard string that has a max length of 254 characters. Can be used for
       various nodes that may require string of this length.";
  }

  typedef ncs_rpc_notif_string-maxl-256 {
    type string {
      length "0..256";
    }
    description
      "Standard string that has a max length of 256 characters. Can be used for
       various nodes that may require string of this length.";
  }

  typedef ncs_rpc_notif_ipaddr-or-hostname {
    type string {
      length "1..63";
    }
    description
      "IP address or hostname string.";
  }

  typedef ncs_rpc_notif_ipv4-address {
    type string {
      length "0..16";
      pattern '(([0-9]|[1-9][0-9]|1[0-9][0-9]|2[0-4][0-9]|25[0-5])\.){3}([0-9]|[1-9][0-9]|1[0-9][0-9]|2[0-4][0-9]|25[0-5])';
    }
    description
      "An IPv4 address represented in dotted decimal notation.";
  }

  typedef ncs_rpc_notif_ipv4-prefix {
    type string {
      length "0..20";
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
    description
      "An IPv4 address and prefix represented in dotted decimal notation
       followed by a slash and a prefix length, e.g. '192.168.1.2/24'.";
  }

  typedef ncs_rpc_notif_ipv4-opt-prefix {
    type string {
      length "0..20";
      pattern '(([0-9]|[1-9][0-9]|1[0-9][0-9]|2[0-4][0-9]|25[0-5])\.){3}([0-9]|[1-9][0-9]|1[0-9][0-9]|2[0-4][0-9]|25[0-5])(/(([0-9])|([1-2][0-9])|(3[0-2])))?';
    }
    description
      "A string type matching either the ipv4-address format or the
       ipv4-prefix format. That is, an IPv4 address in dotted decimal
       notation with an optional slash and prefix length.";
  }

  typedef ncs_rpc_notif_port-name {
    type string {
      length "1..32";
    }
    description
      "A string representing a port interface name. Format is: '<slot>-<port>'
       or '<slot>-<majorport>.<minorport>'.";
  }

  typedef ncs_rpc_notif_service-idx {
    type uint32 {
      range "0 .. 1000";
    }
    description
      "Service Index";
  }

  typedef ncs_rpc_notif_service-domain-idx {
    type uint32 {
      range "0 .. 20";
    }
    description
      "Service Domain Index";
  }

  typedef ncs_rpc_notif_xcvr-type {
    type enumeration {
      enum "not-available" {
        value 0;
        description
          "XCVR type not available.";
      }
      enum "unsupported" {
        value 1;
        description
          "XCVR type unsupported.";
      }
      enum "QSFPplus" {
        value 2;
        description
          "XCVR type QSFP+.";
      }
      enum "QSFP28" {
        value 3;
        description
          "XCVR type QSFP28.";
      }
      enum "WaveLogic 3 Extreme" {
        value 4;
        description
          "XCVR type WL3e.";
      }
      enum "WaveLogic Ai" {
        value 5;
        description
          "XCVR type WLAi.";
      }
      enum "Sgmii" {
        value 6;
        description
          "XCVR type Sgmii.";
      }
      enum "CFP" {
        value 7;
        description
          "XCVR type CFP.";
      }
      enum "SFP" {
        value 8;
        description
          "XCVR type SFP.";
      }
      enum "SFPplus" {
        value 9;
        description
          "XCVR type SFP Plus.";
      }
      enum "XFP" {
        value 10;
        description
          "XCVR type XFP.";
      }
      enum "SFPplus tdwdm" {
        value 11;
        description
          "XCVR type SFPplus tdwdm.";
      }
      enum "CFP2" {
        value 12;
        description
          "XCVR type CFP2.";
      }
      enum "CFP2-DCO" {
        value 13;
        description
          "XCVR type CFP2-DCO.";
      }
      enum "CFP2-ACO" {
        value 14;
        description
          "XCVR type CFP2-ACO.";
      }
      enum "CEP001-OC3" {
        value 15;
        description
          "XCVR type CEP001-OC3.";
      }
      enum "CEP002-OC3-OC12" {
        value 16;
        description
          "XCVR type CEP002-OC3-OC12.";
      }
      enum "CEP003-DS3-E3" {
        value 17;
        description
          "XCVR type CEP003-DS3-E3.";
      }
      enum "GES101-OC3-STM1" {
        value 18;
        description
          "XCVR type GES101-OC3-STM1.";
      }
      enum "TDM2GE-E1" {
        value 19;
        description
          "XCVR type TDM2GE-E1.";
      }
      enum "TDM4GE-DS1" {
        value 20;
        description
          "XCVR type TDM4GE-DS1.";
      }
      enum "TSOP01-OC3-STM1" {
        value 21;
        description
          "XCVR type TSOP01-OC3-STM1.";
      }
      enum "TSOP02-OC12-STM4" {
        value 22;
        description
          "XCVR type TSOP02-OC12-STM4.";
      }
      enum "TSOP03-OC48-STM16" {
        value 23;
        description
          "XCVR type TSOP03-OC48-STM16.";
      }
      enum "NTTP04CDE6-OC3-OC12" {
        value 24;
        description
          "XCVR type NTTP04CDE6-OC3-OC12.";
      }
      enum "NTTP03CFE6-OC48" {
        value 25;
        description
          "XCVR type NTTP03CFE6-OC48.";
      }
      enum "QSFP56" {
        value 26;
        description
          "XCVR type QSFP56.";
      }
      enum "QSFPDD" {
        value 27;
        description
          "XCVR type QSFPDD.";
      }
      enum "SFP28" {
        value 28;
        description
          "XCVR type SFP28.";
      }
    }
    description
      "Transceiver type.";
  }

  typedef ncs_rpc_notif_xcvr-mode {
    type enumeration {
      enum "blank" {
        description
          "XCVR/slot is blank.";
      }
      enum "auto" {
        description
          "Various speed XCVRs can be inserted (e.g. 40GbE versus 100GbE)
           as long as the hardware supports them, and the system will
           automatically adjust the port speed based on the XCVRs
           capabilities. For multi rate XCVRs, the highest speed
           supported will be selected.";
      }
      enum "100M" {
        description
          "XCVR mode FastEthernet.";
      }
      enum "1GE" {
        description
          "XCVR mode 1 Gigabit Ethernet.";
      }
      enum "10GE" {
        description
          "XCVR mode 10 Gigabit Ethernet.";
      }
      enum "25GE" {
        description
          "XCVR mode 25 Gigabit Ethernet.";
      }
      enum "40GE" {
        description
          "XCVR mode 40 Gigabit Ethernet.";
      }
      enum "100GE" {
        description
          "XCVR mode 100 Gigabit Ethernet.";
      }
      enum "400GE" {
        description
          "XCVR mode 400 Gigabit Ethernet.";
      }
      enum "35-100" {
        description
          "XCVR mode 35Gbaud, 100Gbps.";
      }
      enum "35-200" {
        description
          "XCVR mode 35Gbaud, 200Gbps.";
      }
      enum "56-100" {
        description
          "XCVR mode 56Gbaud, 100Gbps.";
      }
      enum "56-200" {
        description
          "XCVR mode 56Gbaud, 200Gbps.";
      }
      enum "56-300" {
        description
          "XCVR mode 56Gbaud, 300Gbps.";
      }
      enum "56-400" {
        description
          "XCVR mode 56Gbaud, 400Gbps.";
      }
      enum "28-100" {
        description
          "XCVR mode 28Gbaud, 100Gbps.";
      }
      enum "32-100" {
        description
          "XCVR mode 32Gbaud, 100Gbps.";
      }
      enum "32-200" {
        description
          "XCVR mode 32Gbaud, 200Gbps.";
      }
      enum "DS1-E1" {
        description
          "XCVR mode DS1-E1.";
      }
      enum "DS3-E3" {
        description
          "XCVR mode DS3-E3.";
      }
      enum "OC3-STM1" {
        description
          "XCVR mode OC3-STM1.";
      }
      enum "OC12-STM4" {
        description
          "XCVR mode OC12-STM4.";
      }
      enum "OC48-STM16" {
        description
          "XCVR mode OC48-STM16.";
      }
      enum "NATIVE-OC3-STM1" {
        description
          "XCVR mode NATIVE-OC3-STM1.";
      }
      enum "NATIVE-OC12-STM4" {
        description
          "XCVR mode NATIVE-OC12-STM4.";
      }
      enum "NATIVE-OC48-STM16" {
        description
          "XCVR mode NATIVE-OC48-STM16.";
      }
      enum "200GE" {
        description
          "XCVR mode 200 Gigabit Ethernet.";
      }
    }
    description
      "Transceiver mode.";
  }

  typedef ncs_rpc_notif_xcvr-fec-type {
    type enumeration {
      enum "GFEC" {
        description
          "XCVR GFEC type.";
      }
      enum "EFEC" {
        description
          "XCVR EFEC type.";
      }
    }
    description
      "Transceiver FEC type.";
  }

  typedef ncs_rpc_notif_line-sys-enum {
    type enumeration {
      enum "coloured" {
        description
          "Line system coloured.";
      }
      enum "colourless" {
        description
          "Line system colourless.";
      }
      enum "contentionless" {
        description
          "Line system contentionless.";
      }
      enum "cs-coloured" {
        description
          "Line system cs-coloured.";
      }
      enum "cs-colourless" {
        description
          "Line system cs-colourless.";
      }
    }
    description
      "Line system type.";
  }

  typedef ncs_rpc_notif_lanes-number {
    type uint16 {
      range "0 .. 8";
    }
    description
      "Lane number common type, lane range is defined from 0 to 8.";
  }

  typedef ncs_rpc_notif_connector-type-desc-enum {
    type enumeration {
      enum "Unknown or unspecified" {
        value 0;
        description
          "Unknown or unspecified.";
      }
      enum "SC - Subscriber Connector" {
        value 1;
        description
          "SC - Subscriber Connector.";
      }
      enum "Fibre Channel Style 1 copper connector" {
        value 2;
        description
          "Fibre Channel Style 1 copper connector.";
      }
      enum "Fibre Channel Style 2 copper connector" {
        value 3;
        description
          "Fibre Channel Style 2 copper connector.";
      }
      enum "BNC/TNC - Bayonet/Threaded Neill-Concelman" {
        value 4;
        description
          "BNC/TNC - Bayonet/Threaded Neill-Concelman.";
      }
      enum "Fibre Channel coax headers" {
        value 5;
        description
          "Fibre Channel coax headers.";
      }
      enum "Fiber Jack" {
        value 6;
        description
          "Fiber Jack.";
      }
      enum "LC - Lucent Connector" {
        value 7;
        description
          "LC - Lucent Connector.";
      }
      enum "MT-RJ - Mechanical Transfer - Registered Jack" {
        value 8;
        description
          "MT-RJ - Mechanical Transfer - Registered Jack.";
      }
      enum "MU - Multiple Optical" {
        value 9;
        description
          "MU - Multiple Optical.";
      }
      enum "SG" {
        value 10;
        description
          "SG.";
      }
      enum "Optical Pigtail" {
        value 11;
        description
          "Optical Pigtail.";
      }
      enum "MPO 1x12 - Multifiber Parallel Optic" {
        value 12;
        description
          "MPO 1x12 - Multifiber Parallel Optic.";
      }
      enum "MPO 2x16" {
        value 13;
        description
          "MPO 2x16.";
      }
      enum "HSSDC II - High Speed Serial Data Connector" {
        value 32;
        description
          "HSSDC II - High Speed Serial Data Connector.";
      }
      enum "Copper pigtail" {
        value 33;
        description
          "Copper pigtail.";
      }
      enum "RJ45 - Registered Jack" {
        value 34;
        description
          "RJ45 - Registered Jack.";
      }
      enum "No separable connector" {
        value 35;
        description
          "No separable connector.";
      }
      enum "MXC 2x16" {
        value 36;
        description
          "MXC 2x16.";
      }
    }
    description
      "Human readable description of Vendor's connector type byte value.";
    reference "SFF-8024, table 4-3";
  }

  typedef ncs_rpc_notif_modem-frequency {
    type decimal64 {
      fraction-digits 1;
    }
    units "GHz";
    description
      "Modem frequency, in GHz. 0.0 indicates unprovisioned (default) value. L-Band
       range is 186087.5 - 190956.2 GHz, and C-Band range is 191100.0 - 196150.0 GHz.";
  }

  typedef ncs_rpc_notif_modem-class {
    type enumeration {
      enum "terrestrial" {
        description
          "Terrestrial modem class.";
      }
      enum "submarine" {
        description
          "Submarine modem class.";
      }
      enum "unavailable" {
        description
          "Modem class is unavailable.";
      }
    }
    description
      "The modem class type, terrestrial or submarine.";
  }

  typedef ncs_rpc_notif_link-optimization-mode {
    type enumeration {
      enum "standard" {
        description
          "Standard Mode - Default setting which provides best SNR performance.";
      }
      enum "snr-tolerant" {
        description
          "SNR Tolerant Mode - Recommended for applications that want to
           achieve maximum SNR tolerance while still providing reasonable
           polarization tracking speed and PDL tolerance.";
      }
      enum "fast-tracking" {
        description
          "Fast Tracking Mode - Recommended for applications that want to
           maximize SOP tracking.";
      }
      enum "spectral-efficiency" {
        description
          "Spectral Efficiency Mode - Recommended for applications that want
           to maximize spectral efficiency by minimizing spectral signal width.";
      }
      enum "latency" {
        description
          "Low Latency Mode - Recommended for applications that want to
           minimize transmission latency.";
      }
      enum "foreign" {
        description
          "Foreign Line Mode - Recommended for applications that require the
           transmitted signal to be be recognized/controlled by a foreign line
           system.";
      }
      enum "narrow" {
        description
          "Narrow Channel Mode - Recommended for applications that want to
           achieve maximum SNR tolerance over heavily filtered optical link.";
      }
      enum "non-linear" {
        description
          "Non-Linear Channel Mode - Recommended for applications that want
           to achieve maximum SNR tolerance on a non-linear fiber link.";
      }
      enum "reserved-1" {
        description
          "Reserved Mode 1.";
      }
      enum "reserved-2" {
        description
          "Reserved Mode 2.";
      }
      enum "reserved-3" {
        description
          "Reserved Mode 3.";
      }
      enum "custom" {
        description
          "Custom Link Optimization Mode.";
      }
    }
    description
      "Link Optimization Modes for the WaveLogic modems.";
  }

  typedef ncs_rpc_notif_supported-link-optimization-modes {
    type bits {
      bit standard {
        description
          "Supports standard link-optimization-mode.";
      }
      bit snr-tolerant {
        description
          "Supports snr-tolerant link-optimization-mode.";
      }
      bit fast-tracking {
        description
          "Supports fast-tracking link-optimization-mode.";
      }
      bit spectral-efficiency {
        description
          "Supports spectral-efficiency link-optimization-mode.";
      }
      bit latency {
        description
          "Supports latency link-optimization-mode.";
      }
      bit foreign {
        description
          "Supports foreign link-optimization-mode.";
      }
      bit narrow {
        description
          "Supports narrow link-optimization-mode.";
      }
      bit non-linear {
        description
          "Supports non-linear link-optimization-mode.";
      }
      bit reserved-1 {
        description
          "Supports reserved-1 link-optimization-mode.";
      }
      bit reserved-2 {
        description
          "Supports reserved-2 link-optimization-mode.";
      }
      bit reserved-3 {
        description
          "Supports reserved-3 link-optimization-mode.";
      }
      bit custom {
        description
          "Supports custom link-optimization-mode.";
      }
    }
    description
      "Type definition for supported link-optimization-mode values for PTPs
       associated with modem XCVR objects.";
  }

  typedef ncs_rpc_notif_tx-power-lvl {
    type decimal64 {
      fraction-digits 1;
      range "-9.0 .. 4.0";
    }
    units "dBm";
    description
      "Modem Tx Power Level.";
  }

  typedef ncs_rpc_notif_module-type-enum {
    type enumeration {
      enum "unknown" {
        description
          "Module type unknown.";
      }
      enum "integrated" {
        description
          "Module type integrated.";
      }
      enum "field-replaceable" {
        description
          "Module type field-replaceable.";
      }
    }
    description
      "Module type enum.";
  }

  typedef ncs_rpc_notif_module-type-bits {
    type bits {
      bit integrated {
        position 0;
        description
          "Module type integrated.";
      }
      bit field-replaceable {
        position 1;
        description
          "Module type field-replaceable.";
      }
    }
    description
      "Module type bits.";
  }

  typedef ncs_rpc_notif_restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef ncs_rpc_notif_conditioning-type {
    type enumeration {
      enum "none" {
        value 0;
        description
          "No consequent action.";
      }
      enum "laser-off" {
        value 1;
        description
          "Disable the transmitter consequent action.";
      }
      enum "ethernet" {
        value 2;
        description
          "Ethernet Local Fault consequent action.";
      }
      enum "otn" {
        value 3;
        description
          "OTN consequent action as defined in ITU-T G.798.";
      }
    }
    description
      "Egress UNI port consequent action for an EPL service to be applied on a
       far-end ingress UNI failure or network failure.";
  }

  typedef ncs_rpc_notif_conditioning-holdoff {
    type int16 {
      range "0|10|20|30|40|50|60|70|80|90|100|200|300|400|500|600|700|800|900|1000";
    }
    units "ms";
    description
      "Number of milliseconds to delay Egress UNI port consequent action for an
       EPL service.";
  }

  typedef ncs_rpc_notif_trace-mismatch-mode {
    type enumeration {
      enum "operator-only" {
        value 1;
        description
          "Trace mismatch detection criteria includes operator-specific trace
           string only. Other fields are ignored.";
      }
      enum "sapi" {
        value 2;
        description
          "Trace mismatch detection criteria includes source access point
           identifier (SAPI) trace string only. Other fields are ignored.";
      }
      enum "dapi" {
        value 3;
        description
          "Trace mismatch detection criteria includes destination access point
           identifier (DAPI) trace string only. Other fields are ignored.";
      }
      enum "sapi-and-dapi" {
        value 4;
        description
          "Trace mismatch detection criteria includes SAPI and DAPI strings. A
           mismatch of either of these fields will result in TTI mismatch. The
           operator specific field is ignored.";
      }
    }
    description
      "The trail trace identifier (TTI) mismatch mode, indicating which fields of
       the TTI overhead are used for trace mismatch detection.";
  }

  typedef ncs_rpc_notif_trace-mismatch-fail-mode {
    type enumeration {
      enum "none" {
        description
          "TTI mismatch detection is disable or ignored. Do not raise an alarm on
           TTI mismatch condition.";
      }
      enum "alarm-only" {
        description
          "Raise an alarm when TTI mismatch occurs, but do not squelch traffic.";
      }
      enum "squelch-traffic" {
        description
          "Squelch the traffic via signal conditioning when TTI mismatch occurs.";
      }
    }
    description
      "The trail trace identifier (TTI) mismatch failure mode. When TTI mismatch
       condition occurs, this indicates the consequent action taken, e.g. whether
       or not to raise an alarm.";
  }

  typedef live_ncs_fingerprint {
    type string {
      pattern '(sha-256:([A-F0-9]{2}:){31}[A-F0-9]{2})|(sha-1:([A-F0-9]{2}:){19}[A-F0-9]{2})';
    }
    description
      "SHA-1 or SHA-256 fingerprint";
  }

  typedef live_ncs_mac-string {
    type string {
      length "1..20";
    }
    description
      "MAC address string.";
  }

  typedef live_ncs_name-string {
    type string {
      length "1..32";
    }
    description
      "String type for object names used in Ciena defined modules. It must be a
       non empty string that is at most 32 characters long.";
  }

  typedef live_ncs_description-string {
    type string {
      length "0..128";
    }
    description
      "String type for description used in Ciena defined modules. Max length of
       128 characters, plus null.";
  }

  typedef live_ncs_on-off-enum {
    type enumeration {
      enum "off" {
        description
          "Off";
      }
      enum "on" {
        description
          "On";
      }
    }
    description
      "Off and On enum toggle used in Ciena defined modules.";
  }

  typedef live_ncs_power-state {
    type enumeration {
      enum "automatic" {
        description
          "Power state is automatic (on/normal).";
      }
      enum "shutdown" {
        description
          "Power state is shutdown (off/low-power-mode).";
      }
    }
    description
      "Power state automatic (on/normal) or shutdown (off/low-power-mode).";
  }

  typedef live_ncs_yes-no-enum {
    type enumeration {
      enum "no" {
        description
          "No";
      }
      enum "yes" {
        description
          "Yes";
      }
    }
    description
      "No and Yes enum toggle used in Ciena defined modules.";
  }

  typedef live_ncs_up-down-enum {
    type enumeration {
      enum "down" {
        description
          "Object is down/disabled/failed.";
      }
      enum "up" {
        description
          "Object is up/operational.";
      }
    }
    description
      "Down and Up enum toggle used in Ciena defined modules.";
  }

  typedef live_ncs_enabled-disabled-enum {
    type enumeration {
      enum "disabled" {
        description
          "Object or attribute is disabled.";
      }
      enum "enabled" {
        description
          "Object or attribute is enabled.";
      }
    }
    description
      "Enabled and Disabled enum toggle used in Ciena defined modules.";
  }

  typedef live_ncs_ettp-fec-enum {
    type enumeration {
      enum "auto" {
        description
          "Object or attribute value is automatic";
      }
      enum "disabled" {
        description
          "Object or attribute is disabled.";
      }
      enum "enabled" {
        description
          "Object or attribute is enabled.";
      }
    }
    description
      "Different state for Ettp forward-error-correction";
  }

  typedef live_ncs_yes-no-na-enum {
    type enumeration {
      enum "no" {
        description
          "No";
      }
      enum "yes" {
        description
          "Yes";
      }
      enum "not-applicable" {
        description
          "Not applicable";
      }
    }
    description
      "No and Yes enum toggle used in Ciena defined modules.";
  }

  typedef live_ncs_enabled-disabled-na-enum {
    type enumeration {
      enum "disabled" {
        description
          "Disabled";
      }
      enum "enabled" {
        description
          "Enabled";
      }
      enum "not-applicable" {
        description
          "Not applicable";
      }
    }
    description
      "Enabled, Disabled, and not-applicable enum used in Ciena defined modules.";
  }

  typedef live_ncs_wl-spacing {
    type enumeration {
      enum "50GHz" {
        description
          "50GHz wavelength spacing.";
      }
      enum "100GHz" {
        description
          "100GHz wavelength spacing.";
      }
      enum "200GHz" {
        description
          "200GHz wavelength spacing.";
      }
      enum "flex-grid" {
        description
          "Flex-grid wavelength spacing.";
      }
    }
    description
      "Wavelength spacing, 50GHz, 100GHz, 200GHz, or flex-grid. Only 'flex-grid'
       supported in Waveserver Ai R1.0.";
  }

  typedef live_ncs_decimal-3-dig {
    type decimal64 {
      fraction-digits 3;
      range "-2147483.0 .. 2147483.0";
    }
    description
      "Decimal value up to 3 digits.";
  }

  typedef live_ncs_decimal-2-dig-small {
    type decimal64 {
      fraction-digits 2;
      range "-30000.0 .. 30000.0";
    }
    description
      "Decimal value up to 2 digits.";
  }

  typedef live_ncs_decimal-2-dig {
    type decimal64 {
      fraction-digits 2;
      range "-21474836.0 .. 21474836.0";
    }
    description
      "Decimal value up to 2 digits.";
  }

  typedef live_ncs_decimal-1-dig {
    type decimal64 {
      fraction-digits 1;
      range "-214748364.0 .. 214748364.0";
    }
    description
      "Decimal value up to 1 digits.";
  }

  typedef live_ncs_string-sci {
    type string {
      length "0..32";
      pattern '[-+]?[0-9](\.[0-9]+)?([eE][-+]?[0-9]+)?';
    }
    description
      "String in Scientific Notation format with a max length of 32 characters.";
  }

  typedef live_ncs_string-maxl-15 {
    type string {
      length "0..15";
    }
    description
      "Standard string that has a max length of 15 characters. Can be used for
       various nodes that may require string of this length.";
  }

  typedef live_ncs_string-maxl-16 {
    type string {
      length "0..16";
    }
    description
      "Standard string that has a max length of 16 characters. Can be used for
       various nodes that may require string of this length.";
  }

  typedef live_ncs_string-maxl-32 {
    type string {
      length "0..32";
    }
    description
      "Standard string that has a max length of 32 characters. Can be used for
       various nodes that may require string of this length.";
  }

  typedef live_ncs_string-maxl-44 {
    type string {
      length "0..44";
    }
    description
      "Standard string that has a max length of 44 characters. Can be used for
       various nodes that may require string of this length.";
  }

  typedef live_ncs_string-maxl-50 {
    type string {
      length "0..50";
    }
    description
      "Standard string that has a max length of 50 characters. Can be used for
       various nodes that may require string of this length.";
  }

  typedef live_ncs_string-maxl-64 {
    type string {
      length "0..64";
    }
    description
      "Standard string that has a max length of 64 characters. Can be used for
       various nodes that may require string of this length.";
  }

  typedef live_ncs_string-maxl-128 {
    type string {
      length "0..128";
    }
    description
      "Standard string that has a max length of 128 characters. Can be used for
       various nodes that may require string of this length.";
  }

  typedef live_ncs_string-maxl-254 {
    type string {
      length "0..254";
    }
    description
      "Standard string that has a max length of 254 characters. Can be used for
       various nodes that may require string of this length.";
  }

  typedef live_ncs_string-maxl-256 {
    type string {
      length "0..256";
    }
    description
      "Standard string that has a max length of 256 characters. Can be used for
       various nodes that may require string of this length.";
  }

  typedef live_ncs_ipaddr-or-hostname {
    type string {
      length "1..63";
    }
    description
      "IP address or hostname string.";
  }

  typedef live_ncs_ipv4-address {
    type string {
      length "0..16";
      pattern '(([0-9]|[1-9][0-9]|1[0-9][0-9]|2[0-4][0-9]|25[0-5])\.){3}([0-9]|[1-9][0-9]|1[0-9][0-9]|2[0-4][0-9]|25[0-5])';
    }
    description
      "An IPv4 address represented in dotted decimal notation.";
  }

  typedef live_ncs_ipv4-prefix {
    type string {
      length "0..20";
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
    description
      "An IPv4 address and prefix represented in dotted decimal notation
       followed by a slash and a prefix length, e.g. '192.168.1.2/24'.";
  }

  typedef live_ncs_ipv4-opt-prefix {
    type string {
      length "0..20";
      pattern '(([0-9]|[1-9][0-9]|1[0-9][0-9]|2[0-4][0-9]|25[0-5])\.){3}([0-9]|[1-9][0-9]|1[0-9][0-9]|2[0-4][0-9]|25[0-5])(/(([0-9])|([1-2][0-9])|(3[0-2])))?';
    }
    description
      "A string type matching either the ipv4-address format or the
       ipv4-prefix format. That is, an IPv4 address in dotted decimal
       notation with an optional slash and prefix length.";
  }

  typedef live_ncs_port-name {
    type string {
      length "1..32";
    }
    description
      "A string representing a port interface name. Format is: '<slot>-<port>'
       or '<slot>-<majorport>.<minorport>'.";
  }

  typedef live_ncs_service-idx {
    type uint32 {
      range "0 .. 1000";
    }
    description
      "Service Index";
  }

  typedef live_ncs_service-domain-idx {
    type uint32 {
      range "0 .. 20";
    }
    description
      "Service Domain Index";
  }

  typedef live_ncs_xcvr-type {
    type enumeration {
      enum "not-available" {
        value 0;
        description
          "XCVR type not available.";
      }
      enum "unsupported" {
        value 1;
        description
          "XCVR type unsupported.";
      }
      enum "QSFPplus" {
        value 2;
        description
          "XCVR type QSFP+.";
      }
      enum "QSFP28" {
        value 3;
        description
          "XCVR type QSFP28.";
      }
      enum "WaveLogic 3 Extreme" {
        value 4;
        description
          "XCVR type WL3e.";
      }
      enum "WaveLogic Ai" {
        value 5;
        description
          "XCVR type WLAi.";
      }
      enum "Sgmii" {
        value 6;
        description
          "XCVR type Sgmii.";
      }
      enum "CFP" {
        value 7;
        description
          "XCVR type CFP.";
      }
      enum "SFP" {
        value 8;
        description
          "XCVR type SFP.";
      }
      enum "SFPplus" {
        value 9;
        description
          "XCVR type SFP Plus.";
      }
      enum "XFP" {
        value 10;
        description
          "XCVR type XFP.";
      }
      enum "SFPplus tdwdm" {
        value 11;
        description
          "XCVR type SFPplus tdwdm.";
      }
      enum "CFP2" {
        value 12;
        description
          "XCVR type CFP2.";
      }
      enum "CFP2-DCO" {
        value 13;
        description
          "XCVR type CFP2-DCO.";
      }
      enum "CFP2-ACO" {
        value 14;
        description
          "XCVR type CFP2-ACO.";
      }
      enum "CEP001-OC3" {
        value 15;
        description
          "XCVR type CEP001-OC3.";
      }
      enum "CEP002-OC3-OC12" {
        value 16;
        description
          "XCVR type CEP002-OC3-OC12.";
      }
      enum "CEP003-DS3-E3" {
        value 17;
        description
          "XCVR type CEP003-DS3-E3.";
      }
      enum "GES101-OC3-STM1" {
        value 18;
        description
          "XCVR type GES101-OC3-STM1.";
      }
      enum "TDM2GE-E1" {
        value 19;
        description
          "XCVR type TDM2GE-E1.";
      }
      enum "TDM4GE-DS1" {
        value 20;
        description
          "XCVR type TDM4GE-DS1.";
      }
      enum "TSOP01-OC3-STM1" {
        value 21;
        description
          "XCVR type TSOP01-OC3-STM1.";
      }
      enum "TSOP02-OC12-STM4" {
        value 22;
        description
          "XCVR type TSOP02-OC12-STM4.";
      }
      enum "TSOP03-OC48-STM16" {
        value 23;
        description
          "XCVR type TSOP03-OC48-STM16.";
      }
      enum "NTTP04CDE6-OC3-OC12" {
        value 24;
        description
          "XCVR type NTTP04CDE6-OC3-OC12.";
      }
      enum "NTTP03CFE6-OC48" {
        value 25;
        description
          "XCVR type NTTP03CFE6-OC48.";
      }
      enum "QSFP56" {
        value 26;
        description
          "XCVR type QSFP56.";
      }
      enum "QSFPDD" {
        value 27;
        description
          "XCVR type QSFPDD.";
      }
      enum "SFP28" {
        value 28;
        description
          "XCVR type SFP28.";
      }
    }
    description
      "Transceiver type.";
  }

  typedef live_ncs_xcvr-mode {
    type enumeration {
      enum "blank" {
        description
          "XCVR/slot is blank.";
      }
      enum "auto" {
        description
          "Various speed XCVRs can be inserted (e.g. 40GbE versus 100GbE)
           as long as the hardware supports them, and the system will
           automatically adjust the port speed based on the XCVRs
           capabilities. For multi rate XCVRs, the highest speed
           supported will be selected.";
      }
      enum "100M" {
        description
          "XCVR mode FastEthernet.";
      }
      enum "1GE" {
        description
          "XCVR mode 1 Gigabit Ethernet.";
      }
      enum "10GE" {
        description
          "XCVR mode 10 Gigabit Ethernet.";
      }
      enum "25GE" {
        description
          "XCVR mode 25 Gigabit Ethernet.";
      }
      enum "40GE" {
        description
          "XCVR mode 40 Gigabit Ethernet.";
      }
      enum "100GE" {
        description
          "XCVR mode 100 Gigabit Ethernet.";
      }
      enum "400GE" {
        description
          "XCVR mode 400 Gigabit Ethernet.";
      }
      enum "35-100" {
        description
          "XCVR mode 35Gbaud, 100Gbps.";
      }
      enum "35-200" {
        description
          "XCVR mode 35Gbaud, 200Gbps.";
      }
      enum "56-100" {
        description
          "XCVR mode 56Gbaud, 100Gbps.";
      }
      enum "56-200" {
        description
          "XCVR mode 56Gbaud, 200Gbps.";
      }
      enum "56-300" {
        description
          "XCVR mode 56Gbaud, 300Gbps.";
      }
      enum "56-400" {
        description
          "XCVR mode 56Gbaud, 400Gbps.";
      }
      enum "28-100" {
        description
          "XCVR mode 28Gbaud, 100Gbps.";
      }
      enum "32-100" {
        description
          "XCVR mode 32Gbaud, 100Gbps.";
      }
      enum "32-200" {
        description
          "XCVR mode 32Gbaud, 200Gbps.";
      }
      enum "DS1-E1" {
        description
          "XCVR mode DS1-E1.";
      }
      enum "DS3-E3" {
        description
          "XCVR mode DS3-E3.";
      }
      enum "OC3-STM1" {
        description
          "XCVR mode OC3-STM1.";
      }
      enum "OC12-STM4" {
        description
          "XCVR mode OC12-STM4.";
      }
      enum "OC48-STM16" {
        description
          "XCVR mode OC48-STM16.";
      }
      enum "NATIVE-OC3-STM1" {
        description
          "XCVR mode NATIVE-OC3-STM1.";
      }
      enum "NATIVE-OC12-STM4" {
        description
          "XCVR mode NATIVE-OC12-STM4.";
      }
      enum "NATIVE-OC48-STM16" {
        description
          "XCVR mode NATIVE-OC48-STM16.";
      }
      enum "200GE" {
        description
          "XCVR mode 200 Gigabit Ethernet.";
      }
    }
    description
      "Transceiver mode.";
  }

  typedef live_ncs_xcvr-fec-type {
    type enumeration {
      enum "GFEC" {
        description
          "XCVR GFEC type.";
      }
      enum "EFEC" {
        description
          "XCVR EFEC type.";
      }
    }
    description
      "Transceiver FEC type.";
  }

  typedef live_ncs_line-sys-enum {
    type enumeration {
      enum "coloured" {
        description
          "Line system coloured.";
      }
      enum "colourless" {
        description
          "Line system colourless.";
      }
      enum "contentionless" {
        description
          "Line system contentionless.";
      }
      enum "cs-coloured" {
        description
          "Line system cs-coloured.";
      }
      enum "cs-colourless" {
        description
          "Line system cs-colourless.";
      }
    }
    description
      "Line system type.";
  }

  typedef live_ncs_lanes-number {
    type uint16 {
      range "0 .. 8";
    }
    description
      "Lane number common type, lane range is defined from 0 to 8.";
  }

  typedef live_ncs_connector-type-desc-enum {
    type enumeration {
      enum "Unknown or unspecified" {
        value 0;
        description
          "Unknown or unspecified.";
      }
      enum "SC - Subscriber Connector" {
        value 1;
        description
          "SC - Subscriber Connector.";
      }
      enum "Fibre Channel Style 1 copper connector" {
        value 2;
        description
          "Fibre Channel Style 1 copper connector.";
      }
      enum "Fibre Channel Style 2 copper connector" {
        value 3;
        description
          "Fibre Channel Style 2 copper connector.";
      }
      enum "BNC/TNC - Bayonet/Threaded Neill-Concelman" {
        value 4;
        description
          "BNC/TNC - Bayonet/Threaded Neill-Concelman.";
      }
      enum "Fibre Channel coax headers" {
        value 5;
        description
          "Fibre Channel coax headers.";
      }
      enum "Fiber Jack" {
        value 6;
        description
          "Fiber Jack.";
      }
      enum "LC - Lucent Connector" {
        value 7;
        description
          "LC - Lucent Connector.";
      }
      enum "MT-RJ - Mechanical Transfer - Registered Jack" {
        value 8;
        description
          "MT-RJ - Mechanical Transfer - Registered Jack.";
      }
      enum "MU - Multiple Optical" {
        value 9;
        description
          "MU - Multiple Optical.";
      }
      enum "SG" {
        value 10;
        description
          "SG.";
      }
      enum "Optical Pigtail" {
        value 11;
        description
          "Optical Pigtail.";
      }
      enum "MPO 1x12 - Multifiber Parallel Optic" {
        value 12;
        description
          "MPO 1x12 - Multifiber Parallel Optic.";
      }
      enum "MPO 2x16" {
        value 13;
        description
          "MPO 2x16.";
      }
      enum "HSSDC II - High Speed Serial Data Connector" {
        value 32;
        description
          "HSSDC II - High Speed Serial Data Connector.";
      }
      enum "Copper pigtail" {
        value 33;
        description
          "Copper pigtail.";
      }
      enum "RJ45 - Registered Jack" {
        value 34;
        description
          "RJ45 - Registered Jack.";
      }
      enum "No separable connector" {
        value 35;
        description
          "No separable connector.";
      }
      enum "MXC 2x16" {
        value 36;
        description
          "MXC 2x16.";
      }
    }
    description
      "Human readable description of Vendor's connector type byte value.";
    reference "SFF-8024, table 4-3";
  }

  typedef live_ncs_modem-frequency {
    type decimal64 {
      fraction-digits 1;
    }
    units "GHz";
    description
      "Modem frequency, in GHz. 0.0 indicates unprovisioned (default) value. L-Band
       range is 186087.5 - 190956.2 GHz, and C-Band range is 191100.0 - 196150.0 GHz.";
  }

  typedef live_ncs_modem-class {
    type enumeration {
      enum "terrestrial" {
        description
          "Terrestrial modem class.";
      }
      enum "submarine" {
        description
          "Submarine modem class.";
      }
      enum "unavailable" {
        description
          "Modem class is unavailable.";
      }
    }
    description
      "The modem class type, terrestrial or submarine.";
  }

  typedef live_ncs_link-optimization-mode {
    type enumeration {
      enum "standard" {
        description
          "Standard Mode - Default setting which provides best SNR performance.";
      }
      enum "snr-tolerant" {
        description
          "SNR Tolerant Mode - Recommended for applications that want to
           achieve maximum SNR tolerance while still providing reasonable
           polarization tracking speed and PDL tolerance.";
      }
      enum "fast-tracking" {
        description
          "Fast Tracking Mode - Recommended for applications that want to
           maximize SOP tracking.";
      }
      enum "spectral-efficiency" {
        description
          "Spectral Efficiency Mode - Recommended for applications that want
           to maximize spectral efficiency by minimizing spectral signal width.";
      }
      enum "latency" {
        description
          "Low Latency Mode - Recommended for applications that want to
           minimize transmission latency.";
      }
      enum "foreign" {
        description
          "Foreign Line Mode - Recommended for applications that require the
           transmitted signal to be be recognized/controlled by a foreign line
           system.";
      }
      enum "narrow" {
        description
          "Narrow Channel Mode - Recommended for applications that want to
           achieve maximum SNR tolerance over heavily filtered optical link.";
      }
      enum "non-linear" {
        description
          "Non-Linear Channel Mode - Recommended for applications that want
           to achieve maximum SNR tolerance on a non-linear fiber link.";
      }
      enum "reserved-1" {
        description
          "Reserved Mode 1.";
      }
      enum "reserved-2" {
        description
          "Reserved Mode 2.";
      }
      enum "reserved-3" {
        description
          "Reserved Mode 3.";
      }
      enum "custom" {
        description
          "Custom Link Optimization Mode.";
      }
    }
    description
      "Link Optimization Modes for the WaveLogic modems.";
  }

  typedef live_ncs_supported-link-optimization-modes {
    type bits {
      bit standard {
        description
          "Supports standard link-optimization-mode.";
      }
      bit snr-tolerant {
        description
          "Supports snr-tolerant link-optimization-mode.";
      }
      bit fast-tracking {
        description
          "Supports fast-tracking link-optimization-mode.";
      }
      bit spectral-efficiency {
        description
          "Supports spectral-efficiency link-optimization-mode.";
      }
      bit latency {
        description
          "Supports latency link-optimization-mode.";
      }
      bit foreign {
        description
          "Supports foreign link-optimization-mode.";
      }
      bit narrow {
        description
          "Supports narrow link-optimization-mode.";
      }
      bit non-linear {
        description
          "Supports non-linear link-optimization-mode.";
      }
      bit reserved-1 {
        description
          "Supports reserved-1 link-optimization-mode.";
      }
      bit reserved-2 {
        description
          "Supports reserved-2 link-optimization-mode.";
      }
      bit reserved-3 {
        description
          "Supports reserved-3 link-optimization-mode.";
      }
      bit custom {
        description
          "Supports custom link-optimization-mode.";
      }
    }
    description
      "Type definition for supported link-optimization-mode values for PTPs
       associated with modem XCVR objects.";
  }

  typedef live_ncs_tx-power-lvl {
    type decimal64 {
      fraction-digits 1;
      range "-9.0 .. 4.0";
    }
    units "dBm";
    description
      "Modem Tx Power Level.";
  }

  typedef live_ncs_module-type-enum {
    type enumeration {
      enum "unknown" {
        description
          "Module type unknown.";
      }
      enum "integrated" {
        description
          "Module type integrated.";
      }
      enum "field-replaceable" {
        description
          "Module type field-replaceable.";
      }
    }
    description
      "Module type enum.";
  }

  typedef live_ncs_module-type-bits {
    type bits {
      bit integrated {
        position 0;
        description
          "Module type integrated.";
      }
      bit field-replaceable {
        position 1;
        description
          "Module type field-replaceable.";
      }
    }
    description
      "Module type bits.";
  }

  typedef live_ncs_restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef live_ncs_conditioning-type {
    type enumeration {
      enum "none" {
        value 0;
        description
          "No consequent action.";
      }
      enum "laser-off" {
        value 1;
        description
          "Disable the transmitter consequent action.";
      }
      enum "ethernet" {
        value 2;
        description
          "Ethernet Local Fault consequent action.";
      }
      enum "otn" {
        value 3;
        description
          "OTN consequent action as defined in ITU-T G.798.";
      }
    }
    description
      "Egress UNI port consequent action for an EPL service to be applied on a
       far-end ingress UNI failure or network failure.";
  }

  typedef live_ncs_conditioning-holdoff {
    type int16 {
      range "0|10|20|30|40|50|60|70|80|90|100|200|300|400|500|600|700|800|900|1000";
    }
    units "ms";
    description
      "Number of milliseconds to delay Egress UNI port consequent action for an
       EPL service.";
  }

  typedef live_ncs_trace-mismatch-mode {
    type enumeration {
      enum "operator-only" {
        value 1;
        description
          "Trace mismatch detection criteria includes operator-specific trace
           string only. Other fields are ignored.";
      }
      enum "sapi" {
        value 2;
        description
          "Trace mismatch detection criteria includes source access point
           identifier (SAPI) trace string only. Other fields are ignored.";
      }
      enum "dapi" {
        value 3;
        description
          "Trace mismatch detection criteria includes destination access point
           identifier (DAPI) trace string only. Other fields are ignored.";
      }
      enum "sapi-and-dapi" {
        value 4;
        description
          "Trace mismatch detection criteria includes SAPI and DAPI strings. A
           mismatch of either of these fields will result in TTI mismatch. The
           operator specific field is ignored.";
      }
    }
    description
      "The trail trace identifier (TTI) mismatch mode, indicating which fields of
       the TTI overhead are used for trace mismatch detection.";
  }

  typedef live_ncs_trace-mismatch-fail-mode {
    type enumeration {
      enum "none" {
        description
          "TTI mismatch detection is disable or ignored. Do not raise an alarm on
           TTI mismatch condition.";
      }
      enum "alarm-only" {
        description
          "Raise an alarm when TTI mismatch occurs, but do not squelch traffic.";
      }
      enum "squelch-traffic" {
        description
          "Squelch the traffic via signal conditioning when TTI mismatch occurs.";
      }
    }
    description
      "The trail trace identifier (TTI) mismatch failure mode. When TTI mismatch
       condition occurs, this indicates the consequent action taken, e.g. whether
       or not to raise an alarm.";
  }

  typedef fingerprint {
    type string {
      pattern '(sha-256:([A-F0-9]{2}:){31}[A-F0-9]{2})|(sha-1:([A-F0-9]{2}:){19}[A-F0-9]{2})';
    }
    description
      "SHA-1 or SHA-256 fingerprint";
  }

  typedef mac-string {
    type string {
      length "1..20";
    }
    description
      "MAC address string.";
  }

  typedef name-string {
    type string {
      length "1..32";
    }
    description
      "String type for object names used in Ciena defined modules. It must be a
       non empty string that is at most 32 characters long.";
  }

  typedef description-string {
    type string {
      length "0..128";
    }
    description
      "String type for description used in Ciena defined modules. Max length of
       128 characters, plus null.";
  }

  typedef on-off-enum {
    type enumeration {
      enum "off" {
        description
          "Off";
      }
      enum "on" {
        description
          "On";
      }
    }
    description
      "Off and On enum toggle used in Ciena defined modules.";
  }

  typedef power-state {
    type enumeration {
      enum "automatic" {
        description
          "Power state is automatic (on/normal).";
      }
      enum "shutdown" {
        description
          "Power state is shutdown (off/low-power-mode).";
      }
    }
    description
      "Power state automatic (on/normal) or shutdown (off/low-power-mode).";
  }

  typedef yes-no-enum {
    type enumeration {
      enum "no" {
        description
          "No";
      }
      enum "yes" {
        description
          "Yes";
      }
    }
    description
      "No and Yes enum toggle used in Ciena defined modules.";
  }

  typedef up-down-enum {
    type enumeration {
      enum "down" {
        description
          "Object is down/disabled/failed.";
      }
      enum "up" {
        description
          "Object is up/operational.";
      }
    }
    description
      "Down and Up enum toggle used in Ciena defined modules.";
  }

  typedef enabled-disabled-enum {
    type enumeration {
      enum "disabled" {
        description
          "Object or attribute is disabled.";
      }
      enum "enabled" {
        description
          "Object or attribute is enabled.";
      }
    }
    description
      "Enabled and Disabled enum toggle used in Ciena defined modules.";
  }

  typedef ettp-fec-enum {
    type enumeration {
      enum "auto" {
        description
          "Object or attribute value is automatic";
      }
      enum "disabled" {
        description
          "Object or attribute is disabled.";
      }
      enum "enabled" {
        description
          "Object or attribute is enabled.";
      }
    }
    description
      "Different state for Ettp forward-error-correction";
  }

  typedef yes-no-na-enum {
    type enumeration {
      enum "no" {
        description
          "No";
      }
      enum "yes" {
        description
          "Yes";
      }
      enum "not-applicable" {
        description
          "Not applicable";
      }
    }
    description
      "No and Yes enum toggle used in Ciena defined modules.";
  }

  typedef enabled-disabled-na-enum {
    type enumeration {
      enum "disabled" {
        description
          "Disabled";
      }
      enum "enabled" {
        description
          "Enabled";
      }
      enum "not-applicable" {
        description
          "Not applicable";
      }
    }
    description
      "Enabled, Disabled, and not-applicable enum used in Ciena defined modules.";
  }

  typedef wl-spacing {
    type enumeration {
      enum "50GHz" {
        description
          "50GHz wavelength spacing.";
      }
      enum "100GHz" {
        description
          "100GHz wavelength spacing.";
      }
      enum "200GHz" {
        description
          "200GHz wavelength spacing.";
      }
      enum "flex-grid" {
        description
          "Flex-grid wavelength spacing.";
      }
    }
    description
      "Wavelength spacing, 50GHz, 100GHz, 200GHz, or flex-grid. Only 'flex-grid'
       supported in Waveserver Ai R1.0.";
  }

  typedef decimal-3-dig {
    type decimal64 {
      fraction-digits 3;
      range "-2147483.0 .. 2147483.0";
    }
    description
      "Decimal value up to 3 digits.";
  }

  typedef decimal-2-dig-small {
    type decimal64 {
      fraction-digits 2;
      range "-30000.0 .. 30000.0";
    }
    description
      "Decimal value up to 2 digits.";
  }

  typedef decimal-2-dig {
    type decimal64 {
      fraction-digits 2;
      range "-21474836.0 .. 21474836.0";
    }
    description
      "Decimal value up to 2 digits.";
  }

  typedef decimal-1-dig {
    type decimal64 {
      fraction-digits 1;
      range "-214748364.0 .. 214748364.0";
    }
    description
      "Decimal value up to 1 digits.";
  }

  typedef string-sci {
    type string {
      length "0..32";
      pattern '[-+]?[0-9](\.[0-9]+)?([eE][-+]?[0-9]+)?';
    }
    description
      "String in Scientific Notation format with a max length of 32 characters.";
  }

  typedef string-maxl-15 {
    type string {
      length "0..15";
    }
    description
      "Standard string that has a max length of 15 characters. Can be used for
       various nodes that may require string of this length.";
  }

  typedef string-maxl-16 {
    type string {
      length "0..16";
    }
    description
      "Standard string that has a max length of 16 characters. Can be used for
       various nodes that may require string of this length.";
  }

  typedef string-maxl-32 {
    type string {
      length "0..32";
    }
    description
      "Standard string that has a max length of 32 characters. Can be used for
       various nodes that may require string of this length.";
  }

  typedef string-maxl-44 {
    type string {
      length "0..44";
    }
    description
      "Standard string that has a max length of 44 characters. Can be used for
       various nodes that may require string of this length.";
  }

  typedef string-maxl-50 {
    type string {
      length "0..50";
    }
    description
      "Standard string that has a max length of 50 characters. Can be used for
       various nodes that may require string of this length.";
  }

  typedef string-maxl-64 {
    type string {
      length "0..64";
    }
    description
      "Standard string that has a max length of 64 characters. Can be used for
       various nodes that may require string of this length.";
  }

  typedef string-maxl-128 {
    type string {
      length "0..128";
    }
    description
      "Standard string that has a max length of 128 characters. Can be used for
       various nodes that may require string of this length.";
  }

  typedef string-maxl-254 {
    type string {
      length "0..254";
    }
    description
      "Standard string that has a max length of 254 characters. Can be used for
       various nodes that may require string of this length.";
  }

  typedef string-maxl-256 {
    type string {
      length "0..256";
    }
    description
      "Standard string that has a max length of 256 characters. Can be used for
       various nodes that may require string of this length.";
  }

  typedef ipaddr-or-hostname {
    type string {
      length "1..63";
    }
    description
      "IP address or hostname string.";
  }

  typedef ipv4-address {
    type string {
      length "0..16";
      pattern '(([0-9]|[1-9][0-9]|1[0-9][0-9]|2[0-4][0-9]|25[0-5])\.){3}([0-9]|[1-9][0-9]|1[0-9][0-9]|2[0-4][0-9]|25[0-5])';
    }
    description
      "An IPv4 address represented in dotted decimal notation.";
  }

  typedef ipv4-prefix {
    type string {
      length "0..20";
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
    description
      "An IPv4 address and prefix represented in dotted decimal notation
       followed by a slash and a prefix length, e.g. '192.168.1.2/24'.";
  }

  typedef ipv4-opt-prefix {
    type string {
      length "0..20";
      pattern '(([0-9]|[1-9][0-9]|1[0-9][0-9]|2[0-4][0-9]|25[0-5])\.){3}([0-9]|[1-9][0-9]|1[0-9][0-9]|2[0-4][0-9]|25[0-5])(/(([0-9])|([1-2][0-9])|(3[0-2])))?';
    }
    description
      "A string type matching either the ipv4-address format or the
       ipv4-prefix format. That is, an IPv4 address in dotted decimal
       notation with an optional slash and prefix length.";
  }

  typedef port-name {
    type string {
      length "1..32";
    }
    description
      "A string representing a port interface name. Format is: '<slot>-<port>'
       or '<slot>-<majorport>.<minorport>'.";
  }

  typedef service-idx {
    type uint32 {
      range "0 .. 1000";
    }
    description
      "Service Index";
  }

  typedef service-domain-idx {
    type uint32 {
      range "0 .. 20";
    }
    description
      "Service Domain Index";
  }

  typedef xcvr-type {
    type enumeration {
      enum "not-available" {
        value 0;
        description
          "XCVR type not available.";
      }
      enum "unsupported" {
        value 1;
        description
          "XCVR type unsupported.";
      }
      enum "QSFPplus" {
        value 2;
        description
          "XCVR type QSFP+.";
      }
      enum "QSFP28" {
        value 3;
        description
          "XCVR type QSFP28.";
      }
      enum "WaveLogic 3 Extreme" {
        value 4;
        description
          "XCVR type WL3e.";
      }
      enum "WaveLogic Ai" {
        value 5;
        description
          "XCVR type WLAi.";
      }
      enum "Sgmii" {
        value 6;
        description
          "XCVR type Sgmii.";
      }
      enum "CFP" {
        value 7;
        description
          "XCVR type CFP.";
      }
      enum "SFP" {
        value 8;
        description
          "XCVR type SFP.";
      }
      enum "SFPplus" {
        value 9;
        description
          "XCVR type SFP Plus.";
      }
      enum "XFP" {
        value 10;
        description
          "XCVR type XFP.";
      }
      enum "SFPplus tdwdm" {
        value 11;
        description
          "XCVR type SFPplus tdwdm.";
      }
      enum "CFP2" {
        value 12;
        description
          "XCVR type CFP2.";
      }
      enum "CFP2-DCO" {
        value 13;
        description
          "XCVR type CFP2-DCO.";
      }
      enum "CFP2-ACO" {
        value 14;
        description
          "XCVR type CFP2-ACO.";
      }
      enum "CEP001-OC3" {
        value 15;
        description
          "XCVR type CEP001-OC3.";
      }
      enum "CEP002-OC3-OC12" {
        value 16;
        description
          "XCVR type CEP002-OC3-OC12.";
      }
      enum "CEP003-DS3-E3" {
        value 17;
        description
          "XCVR type CEP003-DS3-E3.";
      }
      enum "GES101-OC3-STM1" {
        value 18;
        description
          "XCVR type GES101-OC3-STM1.";
      }
      enum "TDM2GE-E1" {
        value 19;
        description
          "XCVR type TDM2GE-E1.";
      }
      enum "TDM4GE-DS1" {
        value 20;
        description
          "XCVR type TDM4GE-DS1.";
      }
      enum "TSOP01-OC3-STM1" {
        value 21;
        description
          "XCVR type TSOP01-OC3-STM1.";
      }
      enum "TSOP02-OC12-STM4" {
        value 22;
        description
          "XCVR type TSOP02-OC12-STM4.";
      }
      enum "TSOP03-OC48-STM16" {
        value 23;
        description
          "XCVR type TSOP03-OC48-STM16.";
      }
      enum "NTTP04CDE6-OC3-OC12" {
        value 24;
        description
          "XCVR type NTTP04CDE6-OC3-OC12.";
      }
      enum "NTTP03CFE6-OC48" {
        value 25;
        description
          "XCVR type NTTP03CFE6-OC48.";
      }
      enum "QSFP56" {
        value 26;
        description
          "XCVR type QSFP56.";
      }
      enum "QSFPDD" {
        value 27;
        description
          "XCVR type QSFPDD.";
      }
      enum "SFP28" {
        value 28;
        description
          "XCVR type SFP28.";
      }
    }
    description
      "Transceiver type.";
  }

  typedef xcvr-mode {
    type enumeration {
      enum "blank" {
        description
          "XCVR/slot is blank.";
      }
      enum "auto" {
        description
          "Various speed XCVRs can be inserted (e.g. 40GbE versus 100GbE)
           as long as the hardware supports them, and the system will
           automatically adjust the port speed based on the XCVRs
           capabilities. For multi rate XCVRs, the highest speed
           supported will be selected.";
      }
      enum "100M" {
        description
          "XCVR mode FastEthernet.";
      }
      enum "1GE" {
        description
          "XCVR mode 1 Gigabit Ethernet.";
      }
      enum "10GE" {
        description
          "XCVR mode 10 Gigabit Ethernet.";
      }
      enum "25GE" {
        description
          "XCVR mode 25 Gigabit Ethernet.";
      }
      enum "40GE" {
        description
          "XCVR mode 40 Gigabit Ethernet.";
      }
      enum "100GE" {
        description
          "XCVR mode 100 Gigabit Ethernet.";
      }
      enum "400GE" {
        description
          "XCVR mode 400 Gigabit Ethernet.";
      }
      enum "35-100" {
        description
          "XCVR mode 35Gbaud, 100Gbps.";
      }
      enum "35-200" {
        description
          "XCVR mode 35Gbaud, 200Gbps.";
      }
      enum "56-100" {
        description
          "XCVR mode 56Gbaud, 100Gbps.";
      }
      enum "56-200" {
        description
          "XCVR mode 56Gbaud, 200Gbps.";
      }
      enum "56-300" {
        description
          "XCVR mode 56Gbaud, 300Gbps.";
      }
      enum "56-400" {
        description
          "XCVR mode 56Gbaud, 400Gbps.";
      }
      enum "28-100" {
        description
          "XCVR mode 28Gbaud, 100Gbps.";
      }
      enum "32-100" {
        description
          "XCVR mode 32Gbaud, 100Gbps.";
      }
      enum "32-200" {
        description
          "XCVR mode 32Gbaud, 200Gbps.";
      }
      enum "DS1-E1" {
        description
          "XCVR mode DS1-E1.";
      }
      enum "DS3-E3" {
        description
          "XCVR mode DS3-E3.";
      }
      enum "OC3-STM1" {
        description
          "XCVR mode OC3-STM1.";
      }
      enum "OC12-STM4" {
        description
          "XCVR mode OC12-STM4.";
      }
      enum "OC48-STM16" {
        description
          "XCVR mode OC48-STM16.";
      }
      enum "NATIVE-OC3-STM1" {
        description
          "XCVR mode NATIVE-OC3-STM1.";
      }
      enum "NATIVE-OC12-STM4" {
        description
          "XCVR mode NATIVE-OC12-STM4.";
      }
      enum "NATIVE-OC48-STM16" {
        description
          "XCVR mode NATIVE-OC48-STM16.";
      }
      enum "200GE" {
        description
          "XCVR mode 200 Gigabit Ethernet.";
      }
    }
    description
      "Transceiver mode.";
  }

  typedef xcvr-fec-type {
    type enumeration {
      enum "GFEC" {
        description
          "XCVR GFEC type.";
      }
      enum "EFEC" {
        description
          "XCVR EFEC type.";
      }
    }
    description
      "Transceiver FEC type.";
  }

  typedef line-sys-enum {
    type enumeration {
      enum "coloured" {
        description
          "Line system coloured.";
      }
      enum "colourless" {
        description
          "Line system colourless.";
      }
      enum "contentionless" {
        description
          "Line system contentionless.";
      }
      enum "cs-coloured" {
        description
          "Line system cs-coloured.";
      }
      enum "cs-colourless" {
        description
          "Line system cs-colourless.";
      }
    }
    description
      "Line system type.";
  }

  typedef lanes-number {
    type uint16 {
      range "0 .. 8";
    }
    description
      "Lane number common type, lane range is defined from 0 to 8.";
  }

  typedef connector-type-desc-enum {
    type enumeration {
      enum "Unknown or unspecified" {
        value 0;
        description
          "Unknown or unspecified.";
      }
      enum "SC - Subscriber Connector" {
        value 1;
        description
          "SC - Subscriber Connector.";
      }
      enum "Fibre Channel Style 1 copper connector" {
        value 2;
        description
          "Fibre Channel Style 1 copper connector.";
      }
      enum "Fibre Channel Style 2 copper connector" {
        value 3;
        description
          "Fibre Channel Style 2 copper connector.";
      }
      enum "BNC/TNC - Bayonet/Threaded Neill-Concelman" {
        value 4;
        description
          "BNC/TNC - Bayonet/Threaded Neill-Concelman.";
      }
      enum "Fibre Channel coax headers" {
        value 5;
        description
          "Fibre Channel coax headers.";
      }
      enum "Fiber Jack" {
        value 6;
        description
          "Fiber Jack.";
      }
      enum "LC - Lucent Connector" {
        value 7;
        description
          "LC - Lucent Connector.";
      }
      enum "MT-RJ - Mechanical Transfer - Registered Jack" {
        value 8;
        description
          "MT-RJ - Mechanical Transfer - Registered Jack.";
      }
      enum "MU - Multiple Optical" {
        value 9;
        description
          "MU - Multiple Optical.";
      }
      enum "SG" {
        value 10;
        description
          "SG.";
      }
      enum "Optical Pigtail" {
        value 11;
        description
          "Optical Pigtail.";
      }
      enum "MPO 1x12 - Multifiber Parallel Optic" {
        value 12;
        description
          "MPO 1x12 - Multifiber Parallel Optic.";
      }
      enum "MPO 2x16" {
        value 13;
        description
          "MPO 2x16.";
      }
      enum "HSSDC II - High Speed Serial Data Connector" {
        value 32;
        description
          "HSSDC II - High Speed Serial Data Connector.";
      }
      enum "Copper pigtail" {
        value 33;
        description
          "Copper pigtail.";
      }
      enum "RJ45 - Registered Jack" {
        value 34;
        description
          "RJ45 - Registered Jack.";
      }
      enum "No separable connector" {
        value 35;
        description
          "No separable connector.";
      }
      enum "MXC 2x16" {
        value 36;
        description
          "MXC 2x16.";
      }
    }
    description
      "Human readable description of Vendor's connector type byte value.";
    reference "SFF-8024, table 4-3";
  }

  typedef modem-frequency {
    type decimal64 {
      fraction-digits 1;
    }
    units "GHz";
    description
      "Modem frequency, in GHz. 0.0 indicates unprovisioned (default) value. L-Band
       range is 186087.5 - 190956.2 GHz, and C-Band range is 191100.0 - 196150.0 GHz.";
  }

  typedef modem-class {
    type enumeration {
      enum "terrestrial" {
        description
          "Terrestrial modem class.";
      }
      enum "submarine" {
        description
          "Submarine modem class.";
      }
      enum "unavailable" {
        description
          "Modem class is unavailable.";
      }
    }
    description
      "The modem class type, terrestrial or submarine.";
  }

  typedef link-optimization-mode {
    type enumeration {
      enum "standard" {
        description
          "Standard Mode - Default setting which provides best SNR performance.";
      }
      enum "snr-tolerant" {
        description
          "SNR Tolerant Mode - Recommended for applications that want to
           achieve maximum SNR tolerance while still providing reasonable
           polarization tracking speed and PDL tolerance.";
      }
      enum "fast-tracking" {
        description
          "Fast Tracking Mode - Recommended for applications that want to
           maximize SOP tracking.";
      }
      enum "spectral-efficiency" {
        description
          "Spectral Efficiency Mode - Recommended for applications that want
           to maximize spectral efficiency by minimizing spectral signal width.";
      }
      enum "latency" {
        description
          "Low Latency Mode - Recommended for applications that want to
           minimize transmission latency.";
      }
      enum "foreign" {
        description
          "Foreign Line Mode - Recommended for applications that require the
           transmitted signal to be be recognized/controlled by a foreign line
           system.";
      }
      enum "narrow" {
        description
          "Narrow Channel Mode - Recommended for applications that want to
           achieve maximum SNR tolerance over heavily filtered optical link.";
      }
      enum "non-linear" {
        description
          "Non-Linear Channel Mode - Recommended for applications that want
           to achieve maximum SNR tolerance on a non-linear fiber link.";
      }
      enum "reserved-1" {
        description
          "Reserved Mode 1.";
      }
      enum "reserved-2" {
        description
          "Reserved Mode 2.";
      }
      enum "reserved-3" {
        description
          "Reserved Mode 3.";
      }
      enum "custom" {
        description
          "Custom Link Optimization Mode.";
      }
    }
    description
      "Link Optimization Modes for the WaveLogic modems.";
  }

  typedef supported-link-optimization-modes {
    type bits {
      bit standard {
        description
          "Supports standard link-optimization-mode.";
      }
      bit snr-tolerant {
        description
          "Supports snr-tolerant link-optimization-mode.";
      }
      bit fast-tracking {
        description
          "Supports fast-tracking link-optimization-mode.";
      }
      bit spectral-efficiency {
        description
          "Supports spectral-efficiency link-optimization-mode.";
      }
      bit latency {
        description
          "Supports latency link-optimization-mode.";
      }
      bit foreign {
        description
          "Supports foreign link-optimization-mode.";
      }
      bit narrow {
        description
          "Supports narrow link-optimization-mode.";
      }
      bit non-linear {
        description
          "Supports non-linear link-optimization-mode.";
      }
      bit reserved-1 {
        description
          "Supports reserved-1 link-optimization-mode.";
      }
      bit reserved-2 {
        description
          "Supports reserved-2 link-optimization-mode.";
      }
      bit reserved-3 {
        description
          "Supports reserved-3 link-optimization-mode.";
      }
      bit custom {
        description
          "Supports custom link-optimization-mode.";
      }
    }
    description
      "Type definition for supported link-optimization-mode values for PTPs
       associated with modem XCVR objects.";
  }

  typedef tx-power-lvl {
    type decimal64 {
      fraction-digits 1;
      range "-9.0 .. 4.0";
    }
    units "dBm";
    description
      "Modem Tx Power Level.";
  }

  typedef module-type-enum {
    type enumeration {
      enum "unknown" {
        description
          "Module type unknown.";
      }
      enum "integrated" {
        description
          "Module type integrated.";
      }
      enum "field-replaceable" {
        description
          "Module type field-replaceable.";
      }
    }
    description
      "Module type enum.";
  }

  typedef module-type-bits {
    type bits {
      bit integrated {
        position 0;
        description
          "Module type integrated.";
      }
      bit field-replaceable {
        position 1;
        description
          "Module type field-replaceable.";
      }
    }
    description
      "Module type bits.";
  }

  typedef restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef conditioning-type {
    type enumeration {
      enum "none" {
        value 0;
        description
          "No consequent action.";
      }
      enum "laser-off" {
        value 1;
        description
          "Disable the transmitter consequent action.";
      }
      enum "ethernet" {
        value 2;
        description
          "Ethernet Local Fault consequent action.";
      }
      enum "otn" {
        value 3;
        description
          "OTN consequent action as defined in ITU-T G.798.";
      }
    }
    description
      "Egress UNI port consequent action for an EPL service to be applied on a
       far-end ingress UNI failure or network failure.";
  }

  typedef conditioning-holdoff {
    type int16 {
      range "0|10|20|30|40|50|60|70|80|90|100|200|300|400|500|600|700|800|900|1000";
    }
    units "ms";
    description
      "Number of milliseconds to delay Egress UNI port consequent action for an
       EPL service.";
  }

  typedef trace-mismatch-mode {
    type enumeration {
      enum "operator-only" {
        value 1;
        description
          "Trace mismatch detection criteria includes operator-specific trace
           string only. Other fields are ignored.";
      }
      enum "sapi" {
        value 2;
        description
          "Trace mismatch detection criteria includes source access point
           identifier (SAPI) trace string only. Other fields are ignored.";
      }
      enum "dapi" {
        value 3;
        description
          "Trace mismatch detection criteria includes destination access point
           identifier (DAPI) trace string only. Other fields are ignored.";
      }
      enum "sapi-and-dapi" {
        value 4;
        description
          "Trace mismatch detection criteria includes SAPI and DAPI strings. A
           mismatch of either of these fields will result in TTI mismatch. The
           operator specific field is ignored.";
      }
    }
    description
      "The trail trace identifier (TTI) mismatch mode, indicating which fields of
       the TTI overhead are used for trace mismatch detection.";
  }

  typedef trace-mismatch-fail-mode {
    type enumeration {
      enum "none" {
        description
          "TTI mismatch detection is disable or ignored. Do not raise an alarm on
           TTI mismatch condition.";
      }
      enum "alarm-only" {
        description
          "Raise an alarm when TTI mismatch occurs, but do not squelch traffic.";
      }
      enum "squelch-traffic" {
        description
          "Squelch the traffic via signal conditioning when TTI mismatch occurs.";
      }
    }
    description
      "The trail trace identifier (TTI) mismatch failure mode. When TTI mismatch
       condition occurs, this indicates the consequent action taken, e.g. whether
       or not to raise an alarm.";
  }
}
