module ciena-system-telemetry {
  // Generated by yanger -t ncs
  tailf:mount-id "saos1051-nc-1.0:saos1051-nc-1.0";
  tailf:ncs-device-type "netconf";

  namespace "urn:ciena:params:xml:ns:yang:ciena-pn::ciena-system-telemetry";
  prefix ciena-sys-tmet;

  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's global configuration for system settings.

     Copyright (c) 2016 Ciena Corporation.  All rights
     reserved.

     All information contained herein is, and remains
     the property of Ciena Corporation. Dissemination of this
     information or reproduction of this material is strictly
     forbidden unless prior written permission is obtained from
     Ciena Corporation.";

  revision 2020-04-30 {
    description
      "Added new enum type health-state to define health state(Normal/Warning/Degraded/Fault).
       Added new leaf state under container cpu-percent and memory for reporting health state.
       Added new list partition for reporting partition utilization statistics.
       Added notification objects for reporting CPU, partition and memory utilization events(threshold exceeded/recovered).";
    reference
      "RFC 6020: YANG - A Data Modeling Language for
       the Network Configuration Protocol (NETCONF).
       No specific reference; standard not available.";
  }
  revision 2016-10-10 {
    description
      "Initial version";
    reference
      "RFC 6020: YANG - A Data Modeling Language for
       the Network Configuration Protocol (NETCONF).
       No specific reference; standard not available.";
  }

  typedef ncs_template_ciena-system-decimal2 {
    type string;
  }

  typedef ncs_template_ciena-system-decimal2-percent {
    type string;
  }

  typedef ncs_template_health-state {
    type string;
  }

  typedef ncs_rpc_notif_ciena-system-decimal2 {
    type decimal64 {
      fraction-digits 2;
    }
  }

  typedef ncs_rpc_notif_ciena-system-decimal2-percent {
    type decimal64 {
      fraction-digits 2;
    }
  }

  typedef ncs_rpc_notif_health-state {
    type enumeration {
      enum "normal" {
        description
          "The Normal health state";
      }
      enum "warning" {
        description
          "The Warning health state";
      }
      enum "degraded" {
        description
          "The Degraded health state";
      }
      enum "fault" {
        description
          "The Fault health state";
      }
    }
  }

  typedef live_ncs_ciena-system-decimal2 {
    type decimal64 {
      fraction-digits 2;
    }
  }

  typedef live_ncs_ciena-system-decimal2-percent {
    type decimal64 {
      fraction-digits 2;
    }
  }

  typedef live_ncs_health-state {
    type enumeration {
      enum "normal" {
        description
          "The Normal health state";
      }
      enum "warning" {
        description
          "The Warning health state";
      }
      enum "degraded" {
        description
          "The Degraded health state";
      }
      enum "fault" {
        description
          "The Fault health state";
      }
    }
  }

  typedef ciena-system-decimal2 {
    type decimal64 {
      fraction-digits 2;
    }
  }

  typedef ciena-system-decimal2-percent {
    type decimal64 {
      fraction-digits 2;
    }
  }

  typedef health-state {
    type enumeration {
      enum "normal" {
        description
          "The Normal health state";
      }
      enum "warning" {
        description
          "The Warning health state";
      }
      enum "degraded" {
        description
          "The Degraded health state";
      }
      enum "fault" {
        description
          "The Fault health state";
      }
    }
  }

  augment "/ncs:devices/ncs:device/ncs:netconf-notifications/ncs:received-notifications/ncs:notification/ncs:data" {
    container partition-utilization-event {
      presence "";
      config false;
      description
        "Event notifications for partition utilization exceeded/recovered from defined threshold limits.";
      leaf state {
        type ncs_rpc_notif_health-state;
        description
          "Partition utilization state based on defined thresholds.";
      }
      leaf partition-name {
        type string;
        description
          "The Partition name.";
      }
    }
  }
  augment "/ncs:devices/ncs:device/ncs:netconf-notifications/ncs:received-notifications/ncs:notification/ncs:data" {
    container memory-utilization-event {
      presence "";
      config false;
      description
        "Event notifications for memory utilization exceeded/recovered from defined threshold limits.";
      leaf state {
        type ncs_rpc_notif_health-state;
        description
          "Memory utilization state based on defined thresholds.";
      }
    }
  }
  augment "/ncs:devices/ncs:device/ncs:netconf-notifications/ncs:received-notifications/ncs:notification/ncs:data" {
    container cpu-utilization-event {
      presence "";
      config false;
      description
        "Event notifications for CPU utilization exceeded/recovered from defined threshold limits.";
      leaf state {
        type ncs_rpc_notif_health-state;
        description
          "CPU utilization state based on defined thresholds limits.";
      }
    }
  }
  augment "/ncs:devices/ncs:device/ncs:config" {
    // NCS drop config false container 'system-state'
  }
  augment "/ncs:devices/ncs:device/ncs:live-status" {
    container system-state {
      tailf:ncs-device-type "netconf";
      tailf:display-when "not(../../ncs:module) or ../../ncs:module[ncs:name='ciena-system-telemetry'] or (../../ncs:live-status-protocol[not(ncs:capability)]) or (../../ncs:live-status-protocol/ncs:capability/ncs:module[.='ciena-system-telemetry'])";
      description
        "System group operational state.";
      container sys-info {
        description
          "Individual units of system information.";
        leaf logical-core-count {
          type uint32;
          description
            "Number of logical cores in the system";
        }
        leaf physical-core-count {
          type uint32;
          description
            "Number of physical cores in the system";
        }
        leaf advertised-cpu-speed {
          type string;
          description
            "Vendor advertised CPU speed in GigaHertz";
        }
        leaf core-temperature {
          type live_ncs_ciena-system-decimal2;
          units "centigrade";
          description
            "CPU core temperature";
        }
      }
      list process {
        key "pid";
        description
          "List of processes on the system.";
        leaf name {
          type string;
          description
            "System process name.";
        }
        leaf pid {
          type string;
          description
            "Process identifier.";
        }
        leaf state {
          type string;
          description
            "The state the process is in.";
        }
        leaf cpu-percent {
          type live_ncs_ciena-system-decimal2-percent;
          units "percent";
          description
            "Process CPU utilization as a percentage of the total CPU utilization.";
        }
        leaf cpu-time-user {
          type live_ncs_ciena-system-decimal2;
          units "seconds";
          description
            "The amount of time this process spent in user-space.";
        }
        leaf cpu-time-system {
          type live_ncs_ciena-system-decimal2;
          units "seconds";
          description
            "The amount of time this process spent in kernel-space.";
        }
      }
      container cpu-time {
        description
          "The amount of time the CPUs have spent in each CPU mode.";
        leaf cpu-idle {
          type live_ncs_ciena-system-decimal2;
          units "seconds";
          description
            "Amount of the time the CPU was idle";
        }
        leaf cpu-interrupt {
          type live_ncs_ciena-system-decimal2;
          units "seconds";
          description
            "Amount of the time the CPU spent in servicing system interrupts.";
        }
        leaf cpu-nice {
          type live_ncs_ciena-system-decimal2;
          units "seconds";
          description
            "Amount of the time the CPU spent in running processes that have been niced.";
        }
        leaf cpu-softirq {
          type live_ncs_ciena-system-decimal2;
          units "seconds";
          description
            "Amount of the time the CPU spent in servicing softirqs (Linux-only).";
        }
        leaf cpu-steal {
          type live_ncs_ciena-system-decimal2;
          units "seconds";
          description
            "Amount of the time the CPU was idle.";
        }
        leaf cpu-system {
          type live_ncs_ciena-system-decimal2;
          units "seconds";
          description
            "Amount of the time the CPU spent in running the kernel.";
        }
        leaf cpu-user {
          type live_ncs_ciena-system-decimal2;
          units "seconds";
          description
            "Amount of the time the CPU spent in running user-space processes.";
        }
        leaf cpu-wait {
          type live_ncs_ciena-system-decimal2;
          units "seconds";
          description
            "Amount of the time the CPU was idle because of pending I/O operations.";
        }
      }
      container cpu-percent {
        description
          "Proportion of time the CPUs have spent in each CPU mode.";
        leaf cpu-idle {
          type live_ncs_ciena-system-decimal2-percent;
          units "percent";
          description
            "Amount of the time the CPU was idle";
        }
        leaf cpu-interrupt {
          type live_ncs_ciena-system-decimal2-percent;
          units "percent";
          description
            "Amount of the time the CPU spent in servicing system interrupts.";
        }
        leaf cpu-nice {
          type live_ncs_ciena-system-decimal2-percent;
          units "percent";
          description
            "Amount of the time the CPU spent in running processes that have been niced.";
        }
        leaf cpu-softirq {
          type live_ncs_ciena-system-decimal2-percent;
          units "percent";
          description
            "Amount of the time the CPU spent in servicing softirqs (Linux-only).";
        }
        leaf cpu-steal {
          type live_ncs_ciena-system-decimal2-percent;
          units "percent";
          description
            "Amount of the time the CPU was idle.";
        }
        leaf cpu-system {
          type live_ncs_ciena-system-decimal2-percent;
          units "percent";
          description
            "Amount of the time the CPU spent in running the kernel.";
        }
        leaf cpu-user {
          type live_ncs_ciena-system-decimal2-percent;
          units "percent";
          description
            "Amount of the time the CPU spent in running user-space processes.";
        }
        leaf cpu-wait {
          type live_ncs_ciena-system-decimal2-percent;
          units "percent";
          description
            "Amount of the time the CPU was idle because of pending I/O operations.";
        }
        leaf state {
          type live_ncs_health-state;
          description
            "CPU utilization state based on defined thresholds limits.";
        }
      }
      container memory {
        description
          "System memory statistics";
        leaf total {
          type uint64;
          units "bytes";
          description
            "System physical memory size";
        }
        leaf available {
          type uint64;
          units "bytes";
          description
            "Memory avaialble to processes without system using the swap space";
        }
        leaf used-percent {
          type live_ncs_ciena-system-decimal2-percent;
          units "percent";
          description
            "Physical memory used in percentage";
        }
        leaf used {
          type uint64;
          units "bytes";
          description
            "System physical memory used";
        }
        leaf free {
          type uint64;
          units "bytes";
          description
            "System memory not it in use";
        }
        leaf active {
          type uint64;
          units "bytes";
          description
            "Memory current in use or used very recently";
        }
        leaf inactive {
          type uint64;
          units "bytes";
          description
            "Memory marked as not used";
        }
        leaf buffers {
          type uint64;
          units "bytes";
          description
            "Physical memory used for file buffers";
        }
        leaf cached {
          type uint64;
          units "bytes";
          description
            "Physical memory used for cache memory";
        }
        leaf state {
          type live_ncs_health-state;
          description
            "Memory utilization state based on defined thresholds limits.";
        }
      }
      container disk {
        description
          "System disk statistics";
        leaf total {
          type uint64;
          units "bytes";
          description
            "System disk size";
        }
        leaf used {
          type uint64;
          units "bytes";
          description
            "Used capacity of the system disk";
        }
        leaf free {
          type uint64;
          units "bytes";
          description
            "Free/unused capacity of the system disk";
        }
        leaf percentage {
          type live_ncs_ciena-system-decimal2-percent;
          units "percent";
          description
            "Proportion of the disk in use.";
        }
      }
      list partition {
        key "name";
        description
          "List of different partition utilization statistics on the system.";
        leaf name {
          type string;
          description
            "Partition name.";
        }
        leaf total {
          type uint64;
          units "bytes";
          description
            "Total allocated partition size.";
        }
        leaf used {
          type uint64;
          units "bytes";
          description
            "Used capacity of the partition.";
        }
        leaf free {
          type uint64;
          units "bytes";
          description
            "Free/unused capacity of the partition.";
        }
        leaf percentage {
          type live_ncs_ciena-system-decimal2-percent;
          units "percent";
          description
            "Proportion of the total partition in use.";
        }
        leaf state {
          type live_ncs_health-state;
          description
            "Partition utilization state based on defined thresholds limits.";
        }
      }
      list logical-core-times {
        key "cpu-id";
        description
          "The amount of time the logical cores have spent in each logical core mode.";
        leaf cpu-id {
          type string;
          description
            "logical core identifier";
        }
        leaf cpu-idle {
          type live_ncs_ciena-system-decimal2;
          units "seconds";
          description
            "Amount of the time the logical core was idle";
        }
        leaf cpu-interrupt {
          type live_ncs_ciena-system-decimal2;
          units "seconds";
          description
            "Amount of the time the logical core spent in servicing system interrupts.";
        }
        leaf cpu-nice {
          type live_ncs_ciena-system-decimal2;
          units "seconds";
          description
            "Amount of the time the logical core spent in running processes that have been niced.";
        }
        leaf cpu-softirq {
          type live_ncs_ciena-system-decimal2;
          units "seconds";
          description
            "Amount of the time the logical core spent in servicing softirqs (Linux-only).";
        }
        leaf cpu-steal {
          type live_ncs_ciena-system-decimal2;
          units "secondsage";
          description
            "Amount of the time the logical core was idle.";
        }
        leaf cpu-system {
          type live_ncs_ciena-system-decimal2;
          units "secondsage";
          description
            "Amount of the time the logical core spent in running the kernel.";
        }
        leaf cpu-user {
          type live_ncs_ciena-system-decimal2;
          units "secondsage";
          description
            "Amount of the time the logical core spent in running user-space processes.";
        }
        leaf cpu-wait {
          type live_ncs_ciena-system-decimal2;
          units "secondsage";
          description
            "Amount of the time the logical core was idle because of pending I/O operations.";
        }
      }
      list logical-core-percent {
        key "cpu-id";
        description
          "Proportion of time the logical cores have spent in each logical core mode.";
        leaf cpu-id {
          type string;
          description
            "logical core identifier";
        }
        leaf cpu-idle {
          type live_ncs_ciena-system-decimal2-percent;
          units "percent";
          description
            "Amount of the time the logical core was idle";
        }
        leaf cpu-interrupt {
          type live_ncs_ciena-system-decimal2-percent;
          units "percent";
          description
            "Amount of the time the logical core spent in servicing system interrupts.";
        }
        leaf cpu-nice {
          type live_ncs_ciena-system-decimal2-percent;
          units "percent";
          description
            "Amount of the time the logical core spent in running processes that have been niced.";
        }
        leaf cpu-softirq {
          type live_ncs_ciena-system-decimal2-percent;
          units "percent";
          description
            "Amount of the time the logical core spent in servicing softirqs (Linux-only).";
        }
        leaf cpu-steal {
          type live_ncs_ciena-system-decimal2-percent;
          units "percent";
          description
            "Amount of the time the logical core was idle.";
        }
        leaf cpu-system {
          type live_ncs_ciena-system-decimal2-percent;
          units "percent";
          description
            "Amount of the time the logical core spent in running the kernel.";
        }
        leaf cpu-user {
          type live_ncs_ciena-system-decimal2-percent;
          units "percent";
          description
            "Amount of the time the logical core spent in running user-space processes.";
        }
        leaf cpu-wait {
          type live_ncs_ciena-system-decimal2-percent;
          units "percent";
          description
            "Amount of the time the logical core was idle because of pending I/O operations.";
        }
      }
    }
  }
  augment "/ncs:devices/ncs:template/ncs:ned-id/ncs:config" {
    // NCS drop config false container 'system-state'
  }
}
