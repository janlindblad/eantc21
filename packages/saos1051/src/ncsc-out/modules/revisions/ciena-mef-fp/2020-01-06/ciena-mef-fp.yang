module ciena-mef-fp {
  // Generated by yanger -t ncs
  tailf:mount-id "saos1051-nc-1.0:saos1051-nc-1.0";
  tailf:ncs-device-type "netconf";

  namespace "urn:ciena:params:xml:ns:yang:ciena-pn:ciena-mef-fp";
  prefix mef-fp;

  import ciena-mef-fd {
    prefix mef-fd;
  }
  import ciena-mef-logical-port {
    prefix mef-logical-port;
  }
  import ciena-mef-classifier {
    prefix classifier;
  }
  import ciena-mef-cos-to-frame-map {
    prefix ctf;
  }
  import ciena-mef-frame-to-cos-map {
    prefix ftc;
  }
  import ciena-mef-flood-containment-profile {
    prefix mef-fc;
  }
  import ciena-mef-meter-profile {
    prefix meter;
  }
  import ciena-mef-egress-qos {
    prefix mef-egress-qos;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines Ciena's management data definition for the
     management of fp.";

  revision 2020-01-06 {
    description
      "Update descriptions of normalized-vid";
  }
  revision 2018-01-09 {
    description
      "10.0 Version.";
    reference "UNI and EVC Definition of Managed Objects (MEF 40), January 2013";
  }

  typedef ncs_template_fp-ref {
    type string;
    description
      "This type is used by the data models that need to reference
       configured flow points";
  }

  typedef ncs_template_vlan-id {
    type string;
    description
      "Represents a IEEE 802.1Q VLAN-ID.";
  }

  typedef ncs_rpc_notif_fp-ref {
    type string;
    description
      "This type is used by the data models that need to reference
       configured flow points";
  }

  typedef ncs_rpc_notif_vlan-id {
    type uint16 {
      range "1..4094";
    }
    description
      "Represents a IEEE 802.1Q VLAN-ID.";
  }

  typedef live_ncs_fp-ref {
    type leafref {
      path "/ncs:devices/ncs:device/ncs:live-status/mef-fp:fps/mef-fp:fp/mef-fp:name" {
        tailf:xpath-root 3;
      }
    }
    description
      "This type is used by the data models that need to reference
       configured flow points";
  }

  typedef live_ncs_vlan-id {
    type uint16 {
      range "1..4094";
    }
    description
      "Represents a IEEE 802.1Q VLAN-ID.";
  }

  typedef fp-ref {
    type leafref {
      path "/ncs:devices/ncs:device/ncs:config/mef-fp:fps/mef-fp:fp/mef-fp:name" {
        tailf:xpath-root 3;
      }
    }
    description
      "This type is used by the data models that need to reference
       configured flow points";
  }

  typedef vlan-id {
    type uint16 {
      range "1..4094";
    }
    description
      "Represents a IEEE 802.1Q VLAN-ID.";
  }

  grouping ncs_template_transform {
    choice frame-type {
      case stack {
        list vlan-stack {
          // NCS patched for predictable order
          ordered-by user;
          key "tag";
          leaf tag {
            type string;
            description
              "Dependent on the xform operation, the tag numbers are
                stamp => '1' represents outermost tag, '2' next outermost (next inner)
                pop => '1' represents pop outermost, '2' represents pop outermost, (always pop from outer)
                push => '1' represents push outermost, '2' represents push outermost (always push to outer)";
          }
          choice action {
            case push {
              leaf push-tpid {
                type string;
                // NCS drop default statement
              }
              leaf push-pcp {
                type string;
              }
              leaf push-dei {
                type string;
              }
              leaf push-vid {
                type ncs_template_vlan-id;
                // NCS drop mandatory statement
              }
            }
            case pop {
              leaf pop-type {
                type empty;
              }
            }
            case stamp {
              leaf stamp-tpid {
                type string;
              }
              leaf stamp-pcp {
                type string;
              }
              leaf stamp-dei {
                type string;
              }
              choice stamp-vid {
                case no-op {
                  leaf no-op {
                    type empty;
                  }
                }
                case vid-value {
                  leaf stamp-vid-value {
                    type ncs_template_vlan-id;
                  }
                }
              }
            }
          }
        }
      }
      case untagged {
        leaf untagged-tpid {
          type string;
        }
        leaf untagged-pcp {
          type string;
        }
        leaf untagged-dei {
          type string;
        }
        leaf untagged-vid {
          type ncs_template_vlan-id;
        }
      }
    }
  }

  grouping ncs_rpc_notif_transform {
    choice frame-type {
      case stack {
        list vlan-stack {
          key "tag";
          leaf tag {
            type uint8;
            description
              "Dependent on the xform operation, the tag numbers are
                stamp => '1' represents outermost tag, '2' next outermost (next inner)
                pop => '1' represents pop outermost, '2' represents pop outermost, (always pop from outer)
                push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                default "tpid-8100";
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
              }
              leaf push-dei {
                type enumeration {
                  enum "enabled";
                  enum "disabled";
                }
              }
              leaf push-vid {
                type ncs_rpc_notif_vlan-id;
                mandatory true;
              }
            }
            case pop {
              leaf pop-type {
                type empty;
              }
            }
            case stamp {
              leaf stamp-tpid {
                type enumeration {
                  enum "no-op";
                  enum "tpid-8100" {
                    value 33024;
                  }
                  enum "tpid-88a8" {
                    value 34984;
                  }
                  enum "tpid-9100" {
                    value 37120;
                  }
                }
              }
              leaf stamp-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "no-op";
                  enum "map";
                }
              }
              leaf stamp-dei {
                type enumeration {
                  enum "no-op";
                  enum "enabled";
                  enum "disabled";
                }
              }
              choice stamp-vid {
                case no-op {
                  leaf no-op {
                    type empty;
                  }
                }
                case vid-value {
                  leaf stamp-vid-value {
                    type ncs_rpc_notif_vlan-id;
                  }
                }
              }
            }
          }
        }
      }
      case untagged {
        leaf untagged-tpid {
          type enumeration {
            enum "tpid-8100" {
              value 33024;
            }
            enum "tpid-88a8" {
              value 34984;
            }
            enum "tpid-9100" {
              value 37120;
            }
          }
        }
        leaf untagged-pcp {
          type enumeration {
            enum "pcp-0" {
              value 0;
            }
            enum "pcp-1" {
              value 1;
            }
            enum "pcp-2" {
              value 2;
            }
            enum "pcp-3" {
              value 3;
            }
            enum "pcp-4" {
              value 4;
            }
            enum "pcp-5" {
              value 5;
            }
            enum "pcp-6" {
              value 6;
            }
            enum "pcp-7" {
              value 7;
            }
            enum "map";
          }
        }
        leaf untagged-dei {
          type enumeration {
            enum "enabled";
            enum "disabled";
          }
        }
        leaf untagged-vid {
          type ncs_rpc_notif_vlan-id;
        }
      }
    }
  }

  grouping live_ncs_transform {
    choice frame-type {
      case stack {
        list vlan-stack {
          key "tag";
          leaf tag {
            type uint8;
            description
              "Dependent on the xform operation, the tag numbers are
                stamp => '1' represents outermost tag, '2' next outermost (next inner)
                pop => '1' represents pop outermost, '2' represents pop outermost, (always pop from outer)
                push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                // NCS drop default statement
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
              }
              leaf push-dei {
                type enumeration {
                  enum "enabled";
                  enum "disabled";
                }
              }
              leaf push-vid {
                type live_ncs_vlan-id;
                // NCS drop mandatory statement
              }
            }
            case pop {
              leaf pop-type {
                type empty;
              }
            }
            case stamp {
              leaf stamp-tpid {
                type enumeration {
                  enum "no-op";
                  enum "tpid-8100" {
                    value 33024;
                  }
                  enum "tpid-88a8" {
                    value 34984;
                  }
                  enum "tpid-9100" {
                    value 37120;
                  }
                }
              }
              leaf stamp-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "no-op";
                  enum "map";
                }
              }
              leaf stamp-dei {
                type enumeration {
                  enum "no-op";
                  enum "enabled";
                  enum "disabled";
                }
              }
              choice stamp-vid {
                case no-op {
                  leaf no-op {
                    type empty;
                  }
                }
                case vid-value {
                  leaf stamp-vid-value {
                    type live_ncs_vlan-id;
                  }
                }
              }
            }
          }
        }
      }
      case untagged {
        leaf untagged-tpid {
          type enumeration {
            enum "tpid-8100" {
              value 33024;
            }
            enum "tpid-88a8" {
              value 34984;
            }
            enum "tpid-9100" {
              value 37120;
            }
          }
        }
        leaf untagged-pcp {
          type enumeration {
            enum "pcp-0" {
              value 0;
            }
            enum "pcp-1" {
              value 1;
            }
            enum "pcp-2" {
              value 2;
            }
            enum "pcp-3" {
              value 3;
            }
            enum "pcp-4" {
              value 4;
            }
            enum "pcp-5" {
              value 5;
            }
            enum "pcp-6" {
              value 6;
            }
            enum "pcp-7" {
              value 7;
            }
            enum "map";
          }
        }
        leaf untagged-dei {
          type enumeration {
            enum "enabled";
            enum "disabled";
          }
        }
        leaf untagged-vid {
          type live_ncs_vlan-id;
        }
      }
    }
  }

  grouping transform {
    choice frame-type {
      case stack {
        list vlan-stack {
          key "tag";
          leaf tag {
            type uint8;
            description
              "Dependent on the xform operation, the tag numbers are
                stamp => '1' represents outermost tag, '2' next outermost (next inner)
                pop => '1' represents pop outermost, '2' represents pop outermost, (always pop from outer)
                push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                default "tpid-8100";
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
              }
              leaf push-dei {
                type enumeration {
                  enum "enabled";
                  enum "disabled";
                }
              }
              leaf push-vid {
                type vlan-id;
                mandatory true;
              }
            }
            case pop {
              leaf pop-type {
                type empty;
              }
            }
            case stamp {
              leaf stamp-tpid {
                type enumeration {
                  enum "no-op";
                  enum "tpid-8100" {
                    value 33024;
                  }
                  enum "tpid-88a8" {
                    value 34984;
                  }
                  enum "tpid-9100" {
                    value 37120;
                  }
                }
              }
              leaf stamp-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "no-op";
                  enum "map";
                }
              }
              leaf stamp-dei {
                type enumeration {
                  enum "no-op";
                  enum "enabled";
                  enum "disabled";
                }
              }
              choice stamp-vid {
                case no-op {
                  leaf no-op {
                    type empty;
                  }
                }
                case vid-value {
                  leaf stamp-vid-value {
                    type vlan-id;
                  }
                }
              }
            }
          }
        }
      }
      case untagged {
        leaf untagged-tpid {
          type enumeration {
            enum "tpid-8100" {
              value 33024;
            }
            enum "tpid-88a8" {
              value 34984;
            }
            enum "tpid-9100" {
              value 37120;
            }
          }
        }
        leaf untagged-pcp {
          type enumeration {
            enum "pcp-0" {
              value 0;
            }
            enum "pcp-1" {
              value 1;
            }
            enum "pcp-2" {
              value 2;
            }
            enum "pcp-3" {
              value 3;
            }
            enum "pcp-4" {
              value 4;
            }
            enum "pcp-5" {
              value 5;
            }
            enum "pcp-6" {
              value 6;
            }
            enum "pcp-7" {
              value 7;
            }
            enum "map";
          }
        }
        leaf untagged-dei {
          type enumeration {
            enum "enabled";
            enum "disabled";
          }
        }
        leaf untagged-vid {
          type vlan-id;
        }
      }
    }
  }

  augment "/ncs:devices/ncs:device/ncs:rpc" {
    container rpc-fps-clear-statistics {
      tailf:ncs-device-type "netconf";
      tailf:display-when "not(../../ncs:module) or ../../ncs:module[ncs:name='ciena-mef-fp']";
      tailf:action fps-clear-statistics {
        tailf:actionpoint ncsproxy {
          tailf:internal;
        }
        description
          "An RPC operation to clear the statistics for one or all Flow-Points.";
        input {
          choice clear-scope {
            case flow-point {
              leaf flow-point {
                type mef-fp:ncs_rpc_notif_fp-ref;
              }
              description
                "Clear stats for this flow-point.";
            }
            case all {
              leaf all {
                type empty;
              }
              description
                "Clear stats for all flow-points.";
            }
          }
        }
        output {
          leaf status {
            type string;
            description
              "Status of the clear statistics operation.";
          }
        }
      }
    }
  }
  augment "/ncs:devices/ncs:device-group/ncs:ned-id/ncs:rpc" {
    container rpc-fps-clear-statistics {
      tailf:ncs-device-type "netconf";
      tailf:display-when "/ncs:devices/ncs:device[ncs:name=current()/../../../ncs:member]/ncs:module[ncs:name='ciena-mef-fp']";
      tailf:action fps-clear-statistics {
        tailf:actionpoint ncsproxy {
          tailf:internal;
        }
        description
          "An RPC operation to clear the statistics for one or all Flow-Points.";
        input {
          choice clear-scope {
            case flow-point {
              leaf flow-point {
                type mef-fp:ncs_rpc_notif_fp-ref;
              }
              description
                "Clear stats for this flow-point.";
            }
            case all {
              leaf all {
                type empty;
              }
              description
                "Clear stats for all flow-points.";
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:config" {
    container fps {
      tailf:ncs-device-type "netconf";
      tailf:display-when "not(../../ncs:module) or ../../ncs:module[ncs:name='ciena-mef-fp']";
      list fp {
        key "name";
        description
          "A list of all mef-fp configuration entries.";
        leaf name {
          type string;
          description
            "This object indicates the flow point identifier.
             The identifier is a text string that is used to identify
             a flow point.

             Unique string values are chosen to uniquely identify the
             flow point.

             Octet values of 0x00 through 0x1f are illegal.

             MEF 26.1 restricts the maximum size identifiers to 45
             octets.";
          reference "[MEF 6.1] 6.1; [MEF 7.2] 6.2.1.3";
        }
        leaf description {
          type string;
          description
            "A editable string used to describe this entry.";
        }
        leaf fd-name {
          type leafref {
            path "/ncs:devices/ncs:device/ncs:config/mef-fd:fds/mef-fd:fd/mef-fd:name" {
              tailf:xpath-root 3;
            }
          }
        }
        leaf logical-port {
          type mef-logical-port:logical-port-ref;
        }
        choice type {
          case q-in-q {
            leaf svlan {
              type uint32;
            }
          }
          case mpls-pw {
            leaf mpls-pw {
              type empty;
            }
          }
          case uni {
            leaf uni {
              type empty;
            }
          }
          case other {
            leaf other {
              type empty;
            }
          }
        }
        leaf mtu-size {
          type uint32;
          units "octets";
          description
            "This object indicates the configured EVC maximum service
             frame format size. It must be less than or equal to the
             max-mtu-size. Vendors may choose to go beyond this limit.";
          reference "[MEF 6.1] 6.1; [MEF 7.2] 6.2.1.3";
          default "2000";
        }
        leaf admin-state {
          type enumeration {
            enum "enabled";
            enum "disabled";
          }
        }
        list ingress-l2-transform {
          key "ingress-name";
          leaf ingress-name {
            type string;
            description
              "Need a key for this list. It cannot be
               a choice of several objects but objects
               that will always be specified.";
          }
          uses transform;
        }
        list egress-l2-transform {
          key "egress-name";
          leaf egress-name {
            type string;
            description
              "Need a key for this list. It cannot be
               a choice of several objects but objects
               that will always be specified.";
          }
          uses transform;
        }
        choice ingress-l3-transform {
          case map {
            leaf ingress-l3-mapped {
              type empty;
            }
          }
          case remark-dscp {
            leaf ingress-remark-dscp-value {
              type uint8 {
                range "0..63";
              }
            }
          }
        }
        choice egress-l3-transform {
          case map {
            leaf egress-l3-mapped {
              type empty;
            }
          }
          case remark-dscp {
            leaf egress-remark-dscp-value {
              type uint8 {
                range "0..63";
              }
            }
          }
        }
        choice frame-to-cos {
          case map {
            leaf map-policy {
              type enumeration {
                enum "outer-tag" {
                  description
                    "Map to internal cos and color based on outer vlan tag of vlan-tagged frame (one or more tags present).
                     Any L2 frame which does not have at least 1 vlan tag is considered non-conforming from frame-to-cos map perspective,
                     and the resolution to an internal cos and color is platform specific for non-conforming frames.";
                }
                enum "inner-tag" {
                  description
                    "Map to internal cos and color based on inner vlan tag of vlan-tagged frame (at least 2 tags present).
                     Any L2 frame which does not have at least 2 vlan tags is considered non-conforming from frame-to-cos map perspective,
                     and the resolution to an internal cos and color is platform specific for non-conforming frames.";
                }
                enum "mpls-tc" {
                  description
                    "Map to internal cos and color based on mpls-tc of outer MPLS Label of L2-frame (if MPLS Label present).
                     Any L2 frame which is non-MPLS (after vlan tags) is considered non-conforming from frame-to-cos map perspective,
                     and the resolution to an internal cos and color is platform specific for non-conforming frames.";
                }
                enum "dscp" {
                  description
                    "Map to internal cos and color based on dscp field of IP of L2-frame (if IP present).
                     Any L2 frame which is non-IP (after vlan tags) is considered non-conforming from frame-to-cos map perspective,
                     and the resolution to an internal cos and color is platform specific for non-conforming frames.";
                }
                enum "dscp-mpls-tc" {
                  description
                    "Map to internal cos and color based on on dscp field of IP of L2-frame (if IP present),
                     or mpls-tc of outer MPLS Label of L2-frame (if MPLS Label present).
                     Any L2 frame which is non-IP or non-MPLS (after vlan tags) is considered non-conforming from frame-to-cos map perspective,
                     and the resolution to an internal cos and color is platform specific for non-conforming frames.";
                }
              }
            }
            leaf frame-to-cos-map {
              type ftc:frame-to-cos-ref;
            }
          }
          case fixed {
            leaf cos {
              type uint8 {
                range "0..63";
              }
            }
            leaf color {
              type enumeration {
                enum "green";
                enum "yellow";
                enum "red";
              }
            }
          }
        }
        leaf cos-to-frame-map {
          type ctf:cos-to-frame-ref;
        }
        leaf flood-containment-profile {
          type mef-fc:flood-containment-profile-ref;
          description
            "Reference to a Flood Containment Profile definition.";
        }
        leaf-list classifier-list {
          type classifier:classifier-ref;
        }
        leaf classifier-list-precedence {
          type uint32;
        }
        leaf mac-learning {
          type enumeration {
            enum "enabled";
            enum "disabled";
          }
        }
        leaf meter-profile {
          type meter:meter-ref;
          description
            "A reference to a Meter Profile.";
        }
        leaf pfg-group {
          type enumeration {
            enum "leaf";
            enum "root";
            enum "mesh";
            enum "spoke";
            enum "group-A";
            enum "group-B";
            enum "group-C";
            enum "group-D";
          }
          description
            "The Private-Forwarding-Group that the flow-point belongs to for the scope of a
             Private-Forwarding-Group-Profile.
             Can be leaf/root for a PFG-profile with PFG-type of leaf-and-root or spokemesh-and-leafroot.
             Can be mesh/spoke for a PFG-profile with PFG-type of spoke-and-mesh or spokemesh-and-leafroot.
             Can be groupA/B/C/D for a PFG-profile with PFG-type of pfg-groups";
        }
        leaf queue-group-instance {
          type mef-egress-qos:queue-group-ref;
          description
            "A reference to a Queue Group Instance.";
        }
        leaf stats-collection {
          type enumeration {
            enum "on";
            enum "off";
          }
          description
            "Determines whether stats collection will be turned on or not for a flow-point";
        }
        list normalized-vid {
          key "tag";
          description
            "Used to represent normalized-vid values for EVPN FXC, e.g. MPLS label + vid lookup.
             The tag number represents the position of the normalized-vid. tag '1' represents outer most tag, tag '2' next outer most, etc.
             Note that the normalized-vid is used in conjunction with an ingress-l2-transform of the same flow-point.
             That is, an ingress-l2-xform operation of push/stamp is generally used to ensure that the frame contains the normalized-vid
             in flow-point to EVPN service-tunnel direction.
             In the case of the ingress-l2-transform stamp operation:
                - ingress-l2-transform stamp tag 1 (outer) matches normalized-vid tag 1 (outer).
                - ingress-l2-transform stamp tag 2 (next outer) matches normalized-vid tag 2 (next outer (aka inner)).
             In the case of the ingress-l2-transform push operation:
                - ingress-l2-transform push tag 1 (outer most) matches normalized-vid tag 1 (outer), when 1 tag is being pushed via the ingress-l2-transform.
                - ingress-l2-transform push tag 2 (next outer most) matches normalized-vid tag 1 (outer), when 2 tags are being pushed via the ingress-l2-transform.
                - ingress-l2-transform push tag 1 (outer most) matches normalized-vid tag 2 (next outer (aka inner)), when 2 tags are being pushed via the ingress-l2-transform.";
          leaf tag {
            type uint8;
            description
              "The tag number represents the position of the normalized-vid. '1' represents outer most tag, '2' next outer most, etc. Note that the normalized-vid
               is used in conjunction with an ingress-l2-transform of the same flow-point. That is, an ingress-l2-xform operation of push/stamp is generally used
               to ensure that the frame contains the normalized-vid in flow-point to EVPN service-tunnel direction.
               In the case of the ingress-l2-transform stamp operation:
                  - ingress-l2-transform stamp tag 1 (outer) matches normalized-vid tag 1 (outer).
                  - ingress-l2-transform stamp tag 2 (next outer) matches normalized-vid tag 2 (next outer (aka inner)).
               In the case of the ingress-l2-transform push operation:
                  - ingress-l2-transform push tag 1 (outer most) matches normalized-vid tag 1 (outer), when 1 tag is being pushed via the ingress-l2-transform.
                  - ingress-l2-transform push tag 2 (next outer most) matches normalized-vid tag 1 (outer), when 2 tags are being pushed via the ingress-l2-transform.
                  - ingress-l2-transform push tag 1 (outer most) matches normalized-vid tag 2 (next outer (aka inner)), when 2 tags are being pushed via the ingress-l2-transform.";
          }
          leaf vlan-id {
            type uint16 {
              range "1..4094";
            }
          }
        }
      }
    }
    // NCS drop config false container 'fps-state'
  }
  augment "/ncs:devices/ncs:device/ncs:live-status" {
    container fps {
      tailf:ncs-device-type "netconf";
      tailf:display-when "not(../../ncs:module) or ../../ncs:module[ncs:name='ciena-mef-fp'] or (../../ncs:live-status-protocol[not(ncs:capability)]) or (../../ncs:live-status-protocol/ncs:capability/ncs:module[.='ciena-mef-fp'])";
      list fp {
        key "name";
        description
          "A list of all mef-fp configuration entries.";
        leaf name {
          type string;
          description
            "This object indicates the flow point identifier.
             The identifier is a text string that is used to identify
             a flow point.

             Unique string values are chosen to uniquely identify the
             flow point.

             Octet values of 0x00 through 0x1f are illegal.

             MEF 26.1 restricts the maximum size identifiers to 45
             octets.";
          reference "[MEF 6.1] 6.1; [MEF 7.2] 6.2.1.3";
        }
        leaf description {
          type string;
          description
            "A editable string used to describe this entry.";
        }
        leaf fd-name {
          type leafref {
            path "/ncs:devices/ncs:device/ncs:live-status/mef-fd:fds/mef-fd:fd/mef-fd:name" {
              tailf:xpath-root 3;
            }
          }
        }
        leaf logical-port {
          type mef-logical-port:live_ncs_logical-port-ref;
        }
        choice type {
          case q-in-q {
            leaf svlan {
              type uint32;
            }
          }
          case mpls-pw {
            leaf mpls-pw {
              type empty;
            }
          }
          case uni {
            leaf uni {
              type empty;
            }
          }
          case other {
            leaf other {
              type empty;
            }
          }
        }
        leaf mtu-size {
          type uint32;
          units "octets";
          description
            "This object indicates the configured EVC maximum service
             frame format size. It must be less than or equal to the
             max-mtu-size. Vendors may choose to go beyond this limit.";
          reference "[MEF 6.1] 6.1; [MEF 7.2] 6.2.1.3";
          // NCS drop default statement
        }
        leaf admin-state {
          type enumeration {
            enum "enabled";
            enum "disabled";
          }
        }
        list ingress-l2-transform {
          key "ingress-name";
          leaf ingress-name {
            type string;
            description
              "Need a key for this list. It cannot be
               a choice of several objects but objects
               that will always be specified.";
          }
          uses live_ncs_transform;
        }
        list egress-l2-transform {
          key "egress-name";
          leaf egress-name {
            type string;
            description
              "Need a key for this list. It cannot be
               a choice of several objects but objects
               that will always be specified.";
          }
          uses live_ncs_transform;
        }
        choice ingress-l3-transform {
          case map {
            leaf ingress-l3-mapped {
              type empty;
            }
          }
          case remark-dscp {
            leaf ingress-remark-dscp-value {
              type uint8 {
                range "0..63";
              }
            }
          }
        }
        choice egress-l3-transform {
          case map {
            leaf egress-l3-mapped {
              type empty;
            }
          }
          case remark-dscp {
            leaf egress-remark-dscp-value {
              type uint8 {
                range "0..63";
              }
            }
          }
        }
        choice frame-to-cos {
          case map {
            leaf map-policy {
              type enumeration {
                enum "outer-tag" {
                  description
                    "Map to internal cos and color based on outer vlan tag of vlan-tagged frame (one or more tags present).
                     Any L2 frame which does not have at least 1 vlan tag is considered non-conforming from frame-to-cos map perspective,
                     and the resolution to an internal cos and color is platform specific for non-conforming frames.";
                }
                enum "inner-tag" {
                  description
                    "Map to internal cos and color based on inner vlan tag of vlan-tagged frame (at least 2 tags present).
                     Any L2 frame which does not have at least 2 vlan tags is considered non-conforming from frame-to-cos map perspective,
                     and the resolution to an internal cos and color is platform specific for non-conforming frames.";
                }
                enum "mpls-tc" {
                  description
                    "Map to internal cos and color based on mpls-tc of outer MPLS Label of L2-frame (if MPLS Label present).
                     Any L2 frame which is non-MPLS (after vlan tags) is considered non-conforming from frame-to-cos map perspective,
                     and the resolution to an internal cos and color is platform specific for non-conforming frames.";
                }
                enum "dscp" {
                  description
                    "Map to internal cos and color based on dscp field of IP of L2-frame (if IP present).
                     Any L2 frame which is non-IP (after vlan tags) is considered non-conforming from frame-to-cos map perspective,
                     and the resolution to an internal cos and color is platform specific for non-conforming frames.";
                }
                enum "dscp-mpls-tc" {
                  description
                    "Map to internal cos and color based on on dscp field of IP of L2-frame (if IP present),
                     or mpls-tc of outer MPLS Label of L2-frame (if MPLS Label present).
                     Any L2 frame which is non-IP or non-MPLS (after vlan tags) is considered non-conforming from frame-to-cos map perspective,
                     and the resolution to an internal cos and color is platform specific for non-conforming frames.";
                }
              }
            }
            leaf frame-to-cos-map {
              type ftc:live_ncs_frame-to-cos-ref;
            }
          }
          case fixed {
            leaf cos {
              type uint8 {
                range "0..63";
              }
            }
            leaf color {
              type enumeration {
                enum "green";
                enum "yellow";
                enum "red";
              }
            }
          }
        }
        leaf cos-to-frame-map {
          type ctf:live_ncs_cos-to-frame-ref;
        }
        leaf flood-containment-profile {
          type mef-fc:live_ncs_flood-containment-profile-ref;
          description
            "Reference to a Flood Containment Profile definition.";
        }
        leaf-list classifier-list {
          type classifier:live_ncs_classifier-ref;
        }
        leaf classifier-list-precedence {
          type uint32;
        }
        leaf mac-learning {
          type enumeration {
            enum "enabled";
            enum "disabled";
          }
        }
        leaf meter-profile {
          type meter:live_ncs_meter-ref;
          description
            "A reference to a Meter Profile.";
        }
        leaf pfg-group {
          type enumeration {
            enum "leaf";
            enum "root";
            enum "mesh";
            enum "spoke";
            enum "group-A";
            enum "group-B";
            enum "group-C";
            enum "group-D";
          }
          description
            "The Private-Forwarding-Group that the flow-point belongs to for the scope of a
             Private-Forwarding-Group-Profile.
             Can be leaf/root for a PFG-profile with PFG-type of leaf-and-root or spokemesh-and-leafroot.
             Can be mesh/spoke for a PFG-profile with PFG-type of spoke-and-mesh or spokemesh-and-leafroot.
             Can be groupA/B/C/D for a PFG-profile with PFG-type of pfg-groups";
        }
        leaf queue-group-instance {
          type mef-egress-qos:live_ncs_queue-group-ref;
          description
            "A reference to a Queue Group Instance.";
        }
        leaf stats-collection {
          type enumeration {
            enum "on";
            enum "off";
          }
          description
            "Determines whether stats collection will be turned on or not for a flow-point";
        }
        list normalized-vid {
          key "tag";
          description
            "Used to represent normalized-vid values for EVPN FXC, e.g. MPLS label + vid lookup.
             The tag number represents the position of the normalized-vid. tag '1' represents outer most tag, tag '2' next outer most, etc.
             Note that the normalized-vid is used in conjunction with an ingress-l2-transform of the same flow-point.
             That is, an ingress-l2-xform operation of push/stamp is generally used to ensure that the frame contains the normalized-vid
             in flow-point to EVPN service-tunnel direction.
             In the case of the ingress-l2-transform stamp operation:
                - ingress-l2-transform stamp tag 1 (outer) matches normalized-vid tag 1 (outer).
                - ingress-l2-transform stamp tag 2 (next outer) matches normalized-vid tag 2 (next outer (aka inner)).
             In the case of the ingress-l2-transform push operation:
                - ingress-l2-transform push tag 1 (outer most) matches normalized-vid tag 1 (outer), when 1 tag is being pushed via the ingress-l2-transform.
                - ingress-l2-transform push tag 2 (next outer most) matches normalized-vid tag 1 (outer), when 2 tags are being pushed via the ingress-l2-transform.
                - ingress-l2-transform push tag 1 (outer most) matches normalized-vid tag 2 (next outer (aka inner)), when 2 tags are being pushed via the ingress-l2-transform.";
          leaf tag {
            type uint8;
            description
              "The tag number represents the position of the normalized-vid. '1' represents outer most tag, '2' next outer most, etc. Note that the normalized-vid
               is used in conjunction with an ingress-l2-transform of the same flow-point. That is, an ingress-l2-xform operation of push/stamp is generally used
               to ensure that the frame contains the normalized-vid in flow-point to EVPN service-tunnel direction.
               In the case of the ingress-l2-transform stamp operation:
                  - ingress-l2-transform stamp tag 1 (outer) matches normalized-vid tag 1 (outer).
                  - ingress-l2-transform stamp tag 2 (next outer) matches normalized-vid tag 2 (next outer (aka inner)).
               In the case of the ingress-l2-transform push operation:
                  - ingress-l2-transform push tag 1 (outer most) matches normalized-vid tag 1 (outer), when 1 tag is being pushed via the ingress-l2-transform.
                  - ingress-l2-transform push tag 2 (next outer most) matches normalized-vid tag 1 (outer), when 2 tags are being pushed via the ingress-l2-transform.
                  - ingress-l2-transform push tag 1 (outer most) matches normalized-vid tag 2 (next outer (aka inner)), when 2 tags are being pushed via the ingress-l2-transform.";
          }
          leaf vlan-id {
            type uint16 {
              range "1..4094";
            }
          }
        }
      }
    }
    container fps-state {
      tailf:ncs-device-type "netconf";
      tailf:display-when "not(../../ncs:module) or ../../ncs:module[ncs:name='ciena-mef-fp'] or (../../ncs:live-status-protocol[not(ncs:capability)]) or (../../ncs:live-status-protocol/ncs:capability/ncs:module[.='ciena-mef-fp'])";
      description
        "Flow Point operational data for all Flow-Points.";
      list fp {
        key "name";
        description
          "The operational data for this Flow Point.";
        leaf name {
          type string;
          description
            "A string that identifies the flow point.";
        }
        leaf rxAcceptedBytes {
          type uint64;
          description
            "Ingress accepted byte count";
        }
        leaf rxAcceptedFrames {
          type uint64;
          description
            "Ingress accepted frame count";
        }
        leaf txForwardedBytes {
          type uint64;
          description
            "Egress forwarded byte count";
        }
        leaf txForwardedFrames {
          type uint64;
          description
            "Egress forwarded frame count";
        }
        leaf rxYellowBytes {
          type uint64;
          description
            "Ingress yellow byte count";
        }
        leaf rxYellowFrames {
          type uint64;
          description
            "Ingress yellow frame count";
        }
        leaf rxDroppedBytes {
          type uint64;
          description
            "Ingress dropped byte count";
        }
        leaf rxDroppedFrames {
          type uint64;
          description
            "Ingress dropped frame count";
        }
      }
    }
  }
  augment "/ncs:devices/ncs:template/ncs:ned-id/ncs:config" {
    container fps {
      list fp {
        // NCS patched for predictable order
        ordered-by user;
        key "name";
        description
          "A list of all mef-fp configuration entries.";
        leaf name {
          type string;
          description
            "This object indicates the flow point identifier.
             The identifier is a text string that is used to identify
             a flow point.

             Unique string values are chosen to uniquely identify the
             flow point.

             Octet values of 0x00 through 0x1f are illegal.

             MEF 26.1 restricts the maximum size identifiers to 45
             octets.";
          reference "[MEF 6.1] 6.1; [MEF 7.2] 6.2.1.3";
        }
        leaf description {
          type string;
          description
            "A editable string used to describe this entry.";
        }
        leaf fd-name {
          type string;
        }
        leaf logical-port {
          type mef-logical-port:ncs_template_logical-port-ref;
        }
        choice type {
          case q-in-q {
            leaf svlan {
              type string;
            }
          }
          case mpls-pw {
            leaf mpls-pw {
              type empty;
            }
          }
          case uni {
            leaf uni {
              type empty;
            }
          }
          case other {
            leaf other {
              type empty;
            }
          }
        }
        leaf mtu-size {
          type string;
          units "octets";
          description
            "This object indicates the configured EVC maximum service
             frame format size. It must be less than or equal to the
             max-mtu-size. Vendors may choose to go beyond this limit.";
          reference "[MEF 6.1] 6.1; [MEF 7.2] 6.2.1.3";
          // NCS drop default statement
        }
        leaf admin-state {
          type string;
        }
        list ingress-l2-transform {
          // NCS patched for predictable order
          ordered-by user;
          key "ingress-name";
          leaf ingress-name {
            type string;
            description
              "Need a key for this list. It cannot be
               a choice of several objects but objects
               that will always be specified.";
          }
          uses ncs_template_transform;
        }
        list egress-l2-transform {
          // NCS patched for predictable order
          ordered-by user;
          key "egress-name";
          leaf egress-name {
            type string;
            description
              "Need a key for this list. It cannot be
               a choice of several objects but objects
               that will always be specified.";
          }
          uses ncs_template_transform;
        }
        choice ingress-l3-transform {
          case map {
            leaf ingress-l3-mapped {
              type empty;
            }
          }
          case remark-dscp {
            leaf ingress-remark-dscp-value {
              type string;
            }
          }
        }
        choice egress-l3-transform {
          case map {
            leaf egress-l3-mapped {
              type empty;
            }
          }
          case remark-dscp {
            leaf egress-remark-dscp-value {
              type string;
            }
          }
        }
        choice frame-to-cos {
          case map {
            leaf map-policy {
              type string;
            }
            leaf frame-to-cos-map {
              type ftc:ncs_template_frame-to-cos-ref;
            }
          }
          case fixed {
            leaf cos {
              type string;
            }
            leaf color {
              type string;
            }
          }
        }
        leaf cos-to-frame-map {
          type ctf:ncs_template_cos-to-frame-ref;
        }
        leaf flood-containment-profile {
          type mef-fc:ncs_template_flood-containment-profile-ref;
          description
            "Reference to a Flood Containment Profile definition.";
        }
        leaf-list classifier-list {
          // NCS patched for predictable order
          ordered-by user;
          type classifier:ncs_template_classifier-ref;
        }
        leaf classifier-list-precedence {
          type string;
        }
        leaf mac-learning {
          type string;
        }
        leaf meter-profile {
          type meter:ncs_template_meter-ref;
          description
            "A reference to a Meter Profile.";
        }
        leaf pfg-group {
          type string;
          description
            "The Private-Forwarding-Group that the flow-point belongs to for the scope of a
             Private-Forwarding-Group-Profile.
             Can be leaf/root for a PFG-profile with PFG-type of leaf-and-root or spokemesh-and-leafroot.
             Can be mesh/spoke for a PFG-profile with PFG-type of spoke-and-mesh or spokemesh-and-leafroot.
             Can be groupA/B/C/D for a PFG-profile with PFG-type of pfg-groups";
        }
        leaf queue-group-instance {
          type mef-egress-qos:ncs_template_queue-group-ref;
          description
            "A reference to a Queue Group Instance.";
        }
        leaf stats-collection {
          type string;
          description
            "Determines whether stats collection will be turned on or not for a flow-point";
        }
        list normalized-vid {
          // NCS patched for predictable order
          ordered-by user;
          key "tag";
          description
            "Used to represent normalized-vid values for EVPN FXC, e.g. MPLS label + vid lookup.
             The tag number represents the position of the normalized-vid. tag '1' represents outer most tag, tag '2' next outer most, etc.
             Note that the normalized-vid is used in conjunction with an ingress-l2-transform of the same flow-point.
             That is, an ingress-l2-xform operation of push/stamp is generally used to ensure that the frame contains the normalized-vid
             in flow-point to EVPN service-tunnel direction.
             In the case of the ingress-l2-transform stamp operation:
                - ingress-l2-transform stamp tag 1 (outer) matches normalized-vid tag 1 (outer).
                - ingress-l2-transform stamp tag 2 (next outer) matches normalized-vid tag 2 (next outer (aka inner)).
             In the case of the ingress-l2-transform push operation:
                - ingress-l2-transform push tag 1 (outer most) matches normalized-vid tag 1 (outer), when 1 tag is being pushed via the ingress-l2-transform.
                - ingress-l2-transform push tag 2 (next outer most) matches normalized-vid tag 1 (outer), when 2 tags are being pushed via the ingress-l2-transform.
                - ingress-l2-transform push tag 1 (outer most) matches normalized-vid tag 2 (next outer (aka inner)), when 2 tags are being pushed via the ingress-l2-transform.";
          leaf tag {
            type string;
            description
              "The tag number represents the position of the normalized-vid. '1' represents outer most tag, '2' next outer most, etc. Note that the normalized-vid
               is used in conjunction with an ingress-l2-transform of the same flow-point. That is, an ingress-l2-xform operation of push/stamp is generally used
               to ensure that the frame contains the normalized-vid in flow-point to EVPN service-tunnel direction.
               In the case of the ingress-l2-transform stamp operation:
                  - ingress-l2-transform stamp tag 1 (outer) matches normalized-vid tag 1 (outer).
                  - ingress-l2-transform stamp tag 2 (next outer) matches normalized-vid tag 2 (next outer (aka inner)).
               In the case of the ingress-l2-transform push operation:
                  - ingress-l2-transform push tag 1 (outer most) matches normalized-vid tag 1 (outer), when 1 tag is being pushed via the ingress-l2-transform.
                  - ingress-l2-transform push tag 2 (next outer most) matches normalized-vid tag 1 (outer), when 2 tags are being pushed via the ingress-l2-transform.
                  - ingress-l2-transform push tag 1 (outer most) matches normalized-vid tag 2 (next outer (aka inner)), when 2 tags are being pushed via the ingress-l2-transform.";
          }
          leaf vlan-id {
            type string;
          }
        }
      }
    }
    // NCS drop config false container 'fps-state'
  }
}
