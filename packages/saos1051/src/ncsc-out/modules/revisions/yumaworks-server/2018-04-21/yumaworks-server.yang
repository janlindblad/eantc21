module yumaworks-server {
  // Generated by yanger -t ncs
  tailf:mount-id "saos1051-nc-1.0:saos1051-nc-1.0";
  tailf:ncs-device-type "netconf";

  namespace "http://yumaworks.com/ns/yumaworks-server";
  prefix yser;

  import ietf-netconf-acm {
    prefix nacm;
  }
  import netconfd-pro {
    prefix ndpro;
  }
  import yumaworks-extensions {
    prefix ywx;
  }
  import tailf-common {
    prefix tailf;
  }
  import tailf-ncs {
    prefix ncs;
  }

  organization
    "YumaWorks, Inc.";
  contact
    "Support <support at yumaworks.com>";
  description
    "Runtime access to netconfd-pro server parameters.
     The following parameters can be changed at run-time
     and the new value will be activated immediately.

     * allowed-user
     * eventlog-size
     * hello-timeout
     * idle-timeout
     * log-level
     * max-burst
     * max-cli-sessions
     * max-getbulk
     * max-sessions
     * subsys-timeout

     The rest of the CLI parameters can be edited for
     activation at the next reboot.

     If the server has write permission to the
     configuration file (e.g., netconfd-pro.conf) then
     the parameters will be saved when the server exits.


     Copyright (c) 2017 - 2018, YumaWorks, Inc. All rights reserved.

     Redistribution and use in source and binary forms, with or
     without modification, is permitted pursuant to, and subject
     to the license terms contained in, the BSD 3-Clause License
     http://opensource.org/licenses/BSD-3-Clause";

  revision 2018-04-21 {
    description
      "Add no-nvstore to server";
  }
  revision 2017-12-30 {
    description
      "Initial version";
  }

  augment "/ncs:devices/ncs:device/ncs:config" {
    container server {
      tailf:ncs-device-type "netconf";
      tailf:display-when "not(../../ncs:module) or ../../ncs:module[ncs:name='yumaworks-server']";
      description
        "Runtime access to netconfd-pro CLI parameters for
         immediate change or activate-on-restart";
      nacm:default-deny-all;
      ywx:no-nvstore;
      uses ndpro:netconfd-pro-parms;
    }
  }
  augment "/ncs:devices/ncs:device/ncs:live-status" {
    container server {
      tailf:ncs-device-type "netconf";
      tailf:display-when "not(../../ncs:module) or ../../ncs:module[ncs:name='yumaworks-server'] or (../../ncs:live-status-protocol[not(ncs:capability)]) or (../../ncs:live-status-protocol/ncs:capability/ncs:module[.='yumaworks-server'])";
      description
        "Runtime access to netconfd-pro CLI parameters for
         immediate change or activate-on-restart";
      nacm:default-deny-all;
      ywx:no-nvstore;
      uses ndpro:live_ncs_netconfd-pro-parms;
    }
  }
  augment "/ncs:devices/ncs:template/ncs:ned-id/ncs:config" {
    container server {
      description
        "Runtime access to netconfd-pro CLI parameters for
         immediate change or activate-on-restart";
      nacm:default-deny-all;
      ywx:no-nvstore;
      uses ndpro:ncs_template_netconfd-pro-parms;
    }
  }
}
