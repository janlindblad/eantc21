module ciena-gateway-protection-group {
  // Generated by yanger -t ncs
  tailf:mount-id "saos1051-nc-1.0:saos1051-nc-1.0";
  tailf:ncs-device-type "netconf";

  namespace "http://www.ciena.com/ns/yang/ciena-gateway-protection-group";
  prefix ciena-gpg;

  import ietf-yang-types {
    prefix yang;
  }
  import ietf-inet-types {
    prefix inet;
  }
  import openconfig-interfaces {
    prefix oc-if;
  }
  import ciena-types {
    prefix cn-type;
  }
  import ciena-openconfig-interfaces {
    prefix cn-if;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines gateway protection group.

     Copyright (c) 2020  Ciena Corporation. All rights
     reserved.

     All information contained herein is, and remains the
     property of Ciena Corporation. Dissemination of this
     information or reproduction of this material is strictly
     forbidden unless prior written permission is obtained
     from Ciena Corporation.";

  revision 2020-03-25 {
    description
      "Initial revision of gateway protection group data model.";
    reference "";
  }

  augment "/ncs:devices/ncs:device/ncs:config" {
    container gateway-protection-group {
      tailf:ncs-device-type "netconf";
      tailf:display-when "not(../../ncs:module) or ../../ncs:module[ncs:name='ciena-gateway-protection-group']";
      description
        "Gateway protection group.";
      container groups {
        description
          "Gateway protection groups.";
        list group {
          key "name";
          max-elements 1;
          description
            "List of gateway protection groups.";
          leaf name {
            type string {
              length "1..128";
            }
            description
              "A unique name associated with each group.";
          }
          list path {
            key "id";
            max-elements 3;
            unique "interface destination-address";
            description
              "List of gateway protection paths in a group.";
            leaf id {
              type uint32;
              description
                "A unique identifier of a path.";
            }
            leaf priority {
              type uint8;
              mandatory true;
              description
                "The priority associated with each gateway path.";
            }
            leaf interface {
              type leafref {
                path "/ncs:devices/ncs:device/ncs:config/oc-if:interfaces/oc-if:interface/oc-if:name" {
                  tailf:xpath-root 3;
                }
              }
              // NCS dropped bad must statement - YANG_ERR_XPATH_BAD_REF
              description
                "Interface that the path uses for gateway reachability.";
            }
            leaf destination-address {
              type inet:ip-address;
              description
                "IP address of the gateway/peer/neighbor where the path ends.";
            }
            leaf source-address {
              type inet:ip-address;
              description
                "Local IP address from where the path originates.";
            }
            leaf admin-state {
              type cn-type:admin-state;
              default "enabled";
              description
                "Admin-state of the gateway-protection path.";
            }
          }
        }
      }
      // NCS drop config false container 'group-state'
    }
  }
  augment "/ncs:devices/ncs:device/ncs:live-status" {
    container gateway-protection-group {
      tailf:ncs-device-type "netconf";
      tailf:display-when "not(../../ncs:module) or ../../ncs:module[ncs:name='ciena-gateway-protection-group'] or (../../ncs:live-status-protocol[not(ncs:capability)]) or (../../ncs:live-status-protocol/ncs:capability/ncs:module[.='ciena-gateway-protection-group'])";
      description
        "Gateway protection group.";
      container groups {
        description
          "Gateway protection groups.";
        list group {
          key "name";
          // NCS drop max-elements statement
          description
            "List of gateway protection groups.";
          leaf name {
            type string {
              length "1..128";
            }
            description
              "A unique name associated with each group.";
          }
          list path {
            key "id";
            // NCS drop max-elements statement
            unique "interface destination-address";
            description
              "List of gateway protection paths in a group.";
            leaf id {
              type uint32;
              description
                "A unique identifier of a path.";
            }
            leaf priority {
              type uint8;
              // NCS drop mandatory statement
              description
                "The priority associated with each gateway path.";
            }
            leaf interface {
              type leafref {
                path "/ncs:devices/ncs:device/ncs:live-status/oc-if:interfaces/oc-if:interface/oc-if:name" {
                  tailf:xpath-root 3;
                }
              }
              // NCS drop must statement
              description
                "Interface that the path uses for gateway reachability.";
            }
            leaf destination-address {
              type inet:ip-address;
              description
                "IP address of the gateway/peer/neighbor where the path ends.";
            }
            leaf source-address {
              type inet:ip-address;
              description
                "Local IP address from where the path originates.";
            }
            leaf admin-state {
              type cn-type:live_ncs_admin-state;
              // NCS drop default statement
              description
                "Admin-state of the gateway-protection path.";
            }
          }
        }
      }
      container group-state {
        description
          "Operational state of gateway protection group.";
        list group {
          key "name";
          description
            "List of gateway protection groups.";
          leaf name {
            type string {
              length "1..128";
            }
            description
              "A name associated with each group.";
          }
          leaf-list selected-paths {
            type uint32;
            description
              "List of selected paths in the group.";
          }
          leaf group-flap-count {
            type yang:counter64;
            description
              "Total number of flap counts in a group across all the paths.";
          }
          list path-state {
            key "id";
            description
              "List of gateway protection paths.";
            leaf id {
              type uint32;
              description
                "A unique identifier of a path.";
            }
            leaf priority {
              type uint8;
              description
                "The priority associated with each gateway path.";
            }
            leaf interface {
              type string;
              description
                "Interface that the path uses for gateway reachability.";
            }
            leaf destination-address {
              type inet:ip-address;
              description
                "IP address of the gateway/peer/neighbor where the path ends.";
            }
            leaf source-address {
              type inet:ip-address;
              description
                "Local IP address from where the path originates.";
            }
            leaf oper-state {
              type cn-type:live_ncs_oper-state;
              description
                "Operational state of the gateway-protection path.";
            }
            leaf up-time {
              type uint64;
              units "seconds";
              description
                "Time since the path is up.";
            }
            leaf selected {
              type boolean;
              description
                "Flag to indicate whether path is selected to carry traffic.";
            }
            leaf path-flap-count {
              type yang:counter32;
              description
                "Number of times the path flaps.";
            }
          }
        }
      }
    }
  }
  augment "/ncs:devices/ncs:template/ncs:ned-id/ncs:config" {
    container gateway-protection-group {
      description
        "Gateway protection group.";
      container groups {
        description
          "Gateway protection groups.";
        list group {
          // NCS patched for predictable order
          ordered-by user;
          key "name";
          // NCS drop max-elements statement
          description
            "List of gateway protection groups.";
          leaf name {
            type string;
            description
              "A unique name associated with each group.";
          }
          list path {
            // NCS patched for predictable order
            ordered-by user;
            key "id";
            // NCS drop max-elements statement
            unique "interface destination-address";
            description
              "List of gateway protection paths in a group.";
            leaf id {
              type string;
              description
                "A unique identifier of a path.";
            }
            leaf priority {
              type string;
              // NCS drop mandatory statement
              description
                "The priority associated with each gateway path.";
            }
            leaf interface {
              type string;
              // NCS drop must statement
              description
                "Interface that the path uses for gateway reachability.";
            }
            leaf destination-address {
              type string;
              description
                "IP address of the gateway/peer/neighbor where the path ends.";
            }
            leaf source-address {
              type string;
              description
                "Local IP address from where the path originates.";
            }
            leaf admin-state {
              type cn-type:ncs_template_admin-state;
              // NCS drop default statement
              description
                "Admin-state of the gateway-protection path.";
            }
          }
        }
      }
      // NCS drop config false container 'group-state'
    }
  }
}
