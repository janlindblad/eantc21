module yumaworks-sil-sa {
    namespace "http://yumaworks.com/ns/yumaworks-sil-sa";

    prefix "ysil";

    import yuma-types { prefix yt; }
    import yumaworks-ycontrol { prefix yctl; }
    import yumaworks-agt-profile { prefix yprof; }

    organization "YumaWorks, Inc.";

    contact
        "Support <support at yumaworks.com>";

    description
       "YumaPro SIL Sub-Agent message definitions.

     Copyright (c) 2014 - 2019 YumaWorks, Inc. All rights reserved.

     Redistribution and use in source and binary forms, with or
     without modification, is permitted pursuant to, and subject
     to the license terms contained in, the BSD 3-Clause License
     http://opensource.org/licenses/BSD-3-Clause";

    revision 2019-09-07 {
        description
          "Add client-addr to transaction messages to support
           sil_sa_get_client_addr function";
    }

    revision 2019-04-20 {
        description
          "Added ACTION support:
            * Add action-path to register-request message
            * Add action-request message
            * Add action-response message";
    }

    revision 2019-01-31 {
        description
          "Added user-id-obj grouping used by start-transaction,
           get-request and rpc-request messages";
    }

    revision 2019-01-20 {
        description
          "Add deviation parm to config-response message.";
    }

    revision 2018-12-05 {
        description
          "Add load-config parameter to start-transaction message";
    }

    revision 2018-10-03 {
        description
          "Add bundle parameter to register-request message";
    }

    revision 2018-06-03 {
        description
          "Add rpc-request and rpc-response messages";
    }

    revision 2017-09-19 {
        description
          "Fix broken augment statement for payload";
    }

    revision 2015-11-01 {
        description
          "Added support for GETBULK to get-response message.";
    }
    revision 2015-08-17 {
        description
          "Added 'select' node support to get2 SIL-SA get-request
           message";
    }
    revision 2015-04-17 {
        description
          "Updated notification container for release";
    }

    revision 2015-01-15 {
        description
          "Add get and notification support";
    }

    revision 2014-11-18 {
        description
          "Fix module type, supposed to be NcModuleNameSpec
           to allow foo@2000-01-01, not just foo.
           Add bundle-module leaf-list to register msg
           Add bundle-load-event to inform server of any modules
           loaded from a SIL-SA bundle; Remove shutdown-event.";
    }

    revision 2014-09-06 {
        description
          "Add agt-profile container to config-parms grouping
           used in the <config-response> from server to subsystem.";
    }

    revision 2014-08-01 {
        description
          "Initial version.";
    }

    grouping bundle-module-parm {
      leaf-list bundle-module {
        type yt:NcModuleSpec;
        description
          "Module parameters that were loaded as a result of
           any bundle parameters. They will be returned in the
           form modname@revision-date.";
      }
    }

    grouping bundle-parm {
      leaf-list bundle {
        type yt:NcxName;
        description
          "Bundle names that were loaded as a result of
           any bundle parameters.";
      }
    }

    grouping path-parm {
      leaf path {
        mandatory true;
        type string;
        description
          "Object identifier string:

            * matches 'path' in the register-request message
              for an EDIT callback
            * matches 'get-path' in the register-request message
              for a GET2 callback
            * matches 'action-path' in the register-request message
              for an ACTION callback

           The path string is generated with YANG prefixes using
           the obj_gen_object_id_prefix function in ncx/obj.h
          ";
      }
    }

    augment "/yctl:ycontrol/yctl:message-payload/yctl:payload/yctl:payload" {
      container sil-sa {

        description
          "Server Instrumentation Library Sub-Agent API Messages

           SIL-SA Protocol Initialization:

           1) subsys sends a <config-request> subsys-request msg
           2) server replies with <config-response> server-response
              msg with the agt_profile data
           3) subsys sends a <register-request> subsys-request msg
              with modules and object path-expressions to register.
              Any bundle and bundle-module info is also sent.
           4) server sends <ok> server-response
           5) subsys sends a <trigger-replay> subsys-event;
              if any config for this subsystem, server will send
              a <start-transaction> server-request with a config-replay
              transaction

           SIL-SA Protocol Edit Operation:

           1) the server sends a <start-transaction> server-request msg
              with the edit list
           2) the subsys validates the request and sends an
              <ok> subsys-response (or error)
           3) the server sends a <continue-transaction> for the apply
              phase
           4) the subsys applies the request and sends an
              <ok> subsys-response (or error)
           5) the server sends a <continue-transaction> for the commit
              phase
           6) the subsys commits the request and sends an
              <ok> subsys-response (or error).

           If the server does not get to step (5) because of an error,
           a <continue-transaction> server-request msg will be sent
           for the rollback phase.

           If the server does not get to step (3) because of an error,
           it will send a <cancel-transaction> server-event msg so
           the subsystem can release any saved state.

           RPC Operation:

           1) the server sends an <rpc-request> with the input parameters.
           2) the subsystem performs VALIDATE and INVOKE phases
           3) the subsystem returns <rpc-ok> or <rpc-data>.
              YControl error is used for any errors

           ACTION Operation:

           1) the server sends an <action-request> with the input parameters.
           2) the subsystem performs VALIDATE and INVOKE phases
           3) the subsystem returns <action-ok> or <action-data>.
              YControl error is used for any errors

           ";

        grouping transaction-id-obj {

          leaf transaction-id {
            mandatory true;
            type string;
            description
              "Server specific transaction identifier.";
          }
        }

        grouping user-id-obj {

          leaf user-id {
            type string;
            description
              "Identifies the user that initiated this transaction.";
          }
        }

        grouping client-addr-obj {

          leaf client-addr {
            type string;
            description
              "Identifies the address of the client that initiated
               this transaction.";
          }
        }

        grouping config-parms {
          uses yprof:agt-profile;

          leaf-list bundle {
            type yt:NcxName;
            description "Bundle SIL SA libraries to load";
          }

          leaf-list module {
            type yt:NcModuleSpec;
            description "Module SIL SA libraries to load";
          }

          leaf-list deviation {
            type yt:NcModuleSpec;
            description "Deviations and annotations to load";
          }

        }

        choice message-type {
//FIXME         choice message-type {
//FIXME           mandatory true;

          leaf config-request {
            type empty;
            description
             "Message type: subsys-request;
              Purpose: register the service with the server
              and request the service configuration from server.
              Expected Response Message: config-response";
          }

          container config-response {
            description
             "Message type: server-reply;
              Purpose: server will send this element containing the
              requested sub-system configuration.
              Expected Response Message: none";

            uses config-parms;
          }

          container register-request {
            description
             "Message type: subsys-request;
              Purpose: register the SIL-SA callback functions
              for this sub-system.
              Expected Response Message: ok";

            uses bundle-parm;
            uses bundle-module-parm;

            list register {
              description
                "Specifies the path strings of all the objects
                 in each module that is supported by the subsystem.";

              key "module";
              leaf module {
                type yt:NcxName;
                description
                  "Module name for the target object.";
              }
              leaf-list path {
                type string;
                description
                  "Path string for object for an EDIT callback";
              }
              leaf-list get-path {
                type string;
                description
                  "Path string for object for a GET callback";
              }
              leaf-list rpc-name {
                type yt:NcxName;
                description
                  "Name of the RPC operation callback";
              }
              leaf-list action-path {
                type string;
                description
                  "Path string for object for an ACTION callback";
              }
            }
          }

          container start-transaction {
            description
             "Message type: server-request;
              Purpose: Start an edit transaction which may require the
              SIL-SA callback functions on the subsystem to be invoked.

              This message requests that a new edit transaction be
              started on the subsystem.  Only 1 transaction can be in
              progress at a time.

              If this transaction is for a validate operation then
              there will not be any followup messages.  Otherwise,
              the subsystem will retain this message until a
              cancel-transaction message has been received with the
              same transaction-id value, or a continue-transaction
              message has been received with the same transaction-id
              value for the 'rollback' or 'commit' phase.

              Expected Response Message: ok or error";

            uses transaction-id-obj;

            uses user-id-obj {
              refine "user-id" {
                mandatory true;
              }
            }
            uses client-addr-obj;

            leaf target {
              mandatory true;
              type string;
              description
                "Identifies the target datastore being edited.
                 The values 'candidate' and 'running' are supported.";
            }

            leaf validate {
              type boolean;
              default false;
              description
                "If 'true' then this start-transaction is for a validate
                 operation or edit that is not on the running
                 configuration datastore, so there will not be
                 any followup messages at all for this message.
                 The subsystem will release this info instead of caching it,
                 and not expect any more messages for the same value of
                 'transaction-id'.

                 If 'false' then this is a normal edit operation and
                 the apply and commit/rollback followup messages
                 will be sent. The subsystem will cache this data
                 until the transaction is cancelled or completed.";
            }

            leaf reverse-edit {
              type boolean;
              default false;
              description
                "If 'true' then this start-transaction is for a
                 reverse-edit operation.  All the phases should
                 be invoked in sequence for the provided edit-list.
                 The transaction can be discarded after sending
                 a response, like the 'validate=true' flag.
                 If 'false' then this is a normal edit operation.";
            }

            leaf load-config {
              type boolean;
              default false;
              description
                "If 'true' then this start-transaction is for a
                 <trigger-replay> operation. If 'false' then this is
                 a normal edit operation, probably caused by
                 a client <edit-config> operation.";
            }


            list edit {
              key "id";

              leaf id {
                type uint32;
                description "Arbitrary edit identifier.";
              }

              leaf operation {
                mandatory true;
                type enumeration {
                  enum merge;
                  enum replace;
                  enum create;
                  enum delete;
                  enum load;
                  enum commit;
                }
                description
                  "Operation matching op_editop_t enumeration list.";
              }

              uses path-parm;

              anyxml newval {
                description
                  "Represents the new value, if any.
                   Should be present if operation is 'merge'
                   'replace', 'create', or 'load'.";
              }

              anyxml curval {
                description
                  "Represents the current value, if any.
                   Should be present if operation is 'replace',
                   'delete', or 'commit'";
              }

              anyxml keys {
                description
                  "List of all ancestor or self key values for the
                   object being edited, identified by the 'path' value.
                   There will be one child leaf for each key in each list.";
              }
            }  // list edit
          }  // container start-transaction

          container continue-transaction {
            description
             "Message type: server-request;
              Purpose: Invoke a callback phase for an edit transaction
              in progress.


              Expected Response Message: ok or error";

            uses transaction-id-obj;

            leaf phase {
              mandatory true;
              type enumeration {
                enum apply {
                  description
                    "Apply the curent transaction.
                     Resources can be reserved that will be
                     used in the commit phase.";
                }
                enum commit {
                  description
                    "Commit the current transaction.";
                }
                enum rollback {
                  description
                    "Rollback the current transaction.";
                }
              }
              description
                "The SIL-SA callback phase in progress.";
            }
          }  // container continue-transaction



          container cancel-transaction {
            description
             "Message type: server-event;
              Purpose: Cancel an edit transaction in progress.
              Expected Response Message: none";

            uses transaction-id-obj;

          }  // container cancel-transaction


          leaf trigger-replay {
            type empty;
            description
             "Message type: subsys-event;
              Purpose: Trigger a configueration replay to load
                 the running config data into the SIL-SA
                 instrumentation.
              Expected Response Message: none; server will send
                 a <start-transaction> if there is any
                 config for the SIL-SA functions registered
                 by the subsystem.";
          }  // leaf trigger-replay


          container load-event {
            description
             "Message type: server-event;
              Purpose: A module or bundle has been loaded or
                 unloaded at run-time. Subsys wil load SIL-SA code.
                 and trigger a register event for any SIL calls
                 registered.
              Expected Response Message: none";

            leaf load {
              type boolean;
              default true;
              description
                "Set to 'true' if this is a load event.
                 Set to 'false' if this is an unload event.";
            }

            uses config-parms;
          }  // container load-event


          container bundle-load-event {
            description
             "Message type: subsys-event;
              Purpose: A SIL-SA bundle has been loaded with
               a load-event sent from the server.  This has
               caused some modules to be loaded on the subsystem,
               that need to be reported back to the main server
               so the datastore validation, agt_state, and other
               system book-keeping can be done.
              Expected Response Message: none";

            uses bundle-parm;
            uses bundle-module-parm;

          }  // container bundle-load-event


          container get-request {
            description
              "Composite retrieval request to support NETCONF
               and RESTCONF get operations.
               Type: server-request
               Expected Response Message: subsys-response
                                   (get-response or error)";

            uses transaction-id-obj;

            uses user-id-obj;

            uses client-addr-obj;

            leaf flags {
              type bits {
                bit keys {
                  description
                    "Return only the key values";
                }
                bit config {
                  description
                    "Return config=true data nodes";
                }
                bit oper {
                  description
                    "Return config=false data nodes";
                }
                bit getnext {
                  description
                    "This is a get-next request instead of a
                    get request";
                }
                bit withdef {
                  description
                    "Return default values for missing nodes";
                }
                bit select {
                  description
                    "Return only the select nodes and any key leafs.
                     Ignore the config, oper, withdef flags if this
                     bit is set.";
                }
              }
              default "";
              description
                "Set of get request modifier flags";
            }

            leaf max-entries {
              type uint32;
              description
                "Max number of entries requested.
                 The default is '0' == all for leaf-list and
                 '1' for all other node types.";
            }

            uses path-parm;

            anyxml keys {
              description
                "List of all ancestor or self key values for the
                 object being retrieved, identified by the 'path'
                 value. There will be one child leaf for each key
                 in each list.";
            }

            anyxml matches {
              description
                "Represents any content-match child leafs for the
                 request. All leafs in this container must match the
                 corresponding child nodes in an instance of the
                 requested list or container, for that instance to
                 be returned.

                 Any content-match nodes must match in addition
                 to any key leafs specified in the 'keys' container.";
            }

            container select-nodes {
              list select-node {
                description
                  "Only requesting these nodes be returned. If no
                   entries and the 'select' bit is set in the flags
                   leaf, then no objects except list keys are
                   returned.";

                key objname;
                leaf objname {
                  type string;
                  description
                    "Object name of the select node";
                }
                leaf modname {
                  type string;
                  description
                    "Module name of the select node; If missing then
                     use the module-name of the path target object.";
                }
              }
            }

          }


          container get-response {
            description
              "Composite retrieval response to support NETCONF
               and RESTCONF get operations.
               Type: subsys-response
               Expected Response Message: none";

            uses transaction-id-obj;

            leaf more-data {
              type boolean;
              default false;
              description
                "Indicates if the GET callback has more data to send";
            }

            leaf match-test-done {
              type boolean;
              default false;
              description
                "Indicates if the requested content-match tests have
                 be performed. Ignored if the 'matches' parameter
                 is missing or empty.";
            }

            leaf active-case-modname {
              type string;
              description
                "Module name of the active case if there is one.
                 Only applies if the GET2 object callback is for
                 a YANG choice-stmt.";
            }

            leaf active-case {
              type string;
              description
                "Name of the active case if there is one.
                 Only applies if the GET2 object callback is for
                 a YANG choice-stmt.";

            }

            grouping return-val {
              anyxml return-keys {
                description
                  "List of all ancestor or self key values for the
                   object being retrieved, identified by the 'path'
                   value. There will be one child leaf for each key
                   in each list.";
              }

              anyxml values {
                description
                  "Represents the retrieved values, if any.
                   There will be one child node for each returned
                   value.";
              }
            }

            choice return-choice {
              case return-one {
                description
                  "For all objects except YANG list, one entry
                   will be returned.  This can also be used
                   for YANG list, except in GETBULK mode.";
                uses return-val;
              }
//FIXME               case return-getbulk {
//FIXME                 description
//FIXME                   "For YANG list GETBULK mode.  There will be one entry
//FIXME                    for each list instance that met the search criteria.
//FIXME                    If the max_entries parameter was greater than zero,
//FIXME                    there the number of instances of 'entry' should not
//FIXME                    exceed this value.";
//FIXME                 list entry {
//FIXME                   // no key!!
//FIXME                   uses return-val;
//FIXME                 }
//FIXME               }
            }
          }


          container notification {
            description
              "Subsystem generated YANG notification event
               for NETCONF and RESTCONF streams.
               Type: subsys-event
               Expected Response Message: none";

            leaf module-name {
              mandatory true;
              type string;
              description
                "Module name containing the notification definition";
            }

            leaf event-name {
              mandatory true;
              type string;
              description
                "Notification statement name";
            }

            leaf event-time {
              mandatory true;
              type string;
              description
                "Notification creation timestamp";
            }


            anyxml parms {
              description
                "List of all parameters that this notification
                 is sending in the payload.";
            }
          }


          container rpc-request {
            description
             "Message type: server-request;
              Purpose: Start an RPC transaction which may require the
              SIL-SA callback functions on the subsystem to be invoked.

              This message requests that a new remote procedure
              call be validated and invoked on the subsystem.

              If there are input parameters the subsystem
              must validate them.

              If not valid or if the operation cannot be performed,
              the subsystem must return an error.

              Expected Response Message: rpc-response";

            uses transaction-id-obj;

            uses user-id-obj;

            uses client-addr-obj;

            leaf rpc-module {
              type yt:NcxName;
              mandatory true;
              description
                "Identifies the module name of the RPC definition.";
            }

            leaf rpc-name {
              type yt:NcxName;
              mandatory true;
              description
                "Identifies the name of the RPC definition.";
            }

            anyxml rpc-input {
              description
                "Contains the RPC input data (if any).";
            }
          }


          container rpc-response {
            description
             "Message type: subsys-response
              Purpose: Return RPC data or status
              Expected Response Message: none";

            uses transaction-id-obj;

            choice response-type {
              leaf rpc-ok {
                type empty;
                description
                  "RPC successfully invoked";
              }
              anyxml rpc-output {
                description
                  "Contains the RPC output data (if any).";
              }
            }
          }


          container action-request {
            description
             "Message type: server-request;
              Purpose: Start an ACTION transaction which may require the
              SIL-SA callback functions on the subsystem to be invoked.

              This message requests that a new action call be validated
              and invoked on the subsystem.

              If there are input parameters the subsystem
              must validate them.

              If not valid or if the operation cannot be performed,
              the subsystem must return an error.

              Expected Response Message: action-response";

            uses transaction-id-obj;

            uses user-id-obj;

            uses client-addr-obj;

            uses path-parm;

            anyxml keys {
              description
                "List of all ancestor key values for the
                 action being invoked, identified by the 'path' value.
                 There will be one child leaf for each key in each list.";
            }

            anyxml action-input {
              description
                "Contains the ACTION input data (if any).";
            }
          }


          container action-response {
            description
             "Message type: subsys-response
              Purpose: Return ACTION data or status
              Expected Response Message: none";

            uses transaction-id-obj;

            choice response-type {
              leaf action-ok {
                type empty;
                description
                  "ACTION successfully invoked";
              }
              anyxml action-output {
                description
                  "Contains the ACTION output data (if any).";
              }
            }
          }

        } // choice message-type
      } // container sil-sa
    } // augment
}
