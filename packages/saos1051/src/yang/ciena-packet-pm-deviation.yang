module ciena-packet-pm-deviation {
  namespace "http://www.ciena.com/ns/yang/ciena-packet-pm-deviation";
  prefix ciena-pm-deviation;

  import ciena-packet-pm {
    prefix ciena-pm;
  }

  organization
    "Ciena Corporation";
  contact
    "Web URL: http://www.ciena.com/
     Postal:  7035 Ridge Road
             Hanover, Maryland 21076
             U.S.A.
     Phone:   +1 800-921-1144
     Fax:     +1 410-694-5750";


  revision 2018-11-07 {
    description
      "Initial revision";
  }

  deviation /ciena-pm:pm/ciena-pm:ethernet-performance-instances {
     deviate not-supported;
  }
}
