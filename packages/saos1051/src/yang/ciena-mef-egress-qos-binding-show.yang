module ciena-mef-egress-qos-binding-show{
    yang-version 1.1;
    namespace "http://www.ciena.com/ns/ciena-mef-egress-qos-binding-show";
    prefix ciena-mef-egress-qos-binding-show;
    import yangcli-pro { prefix yp; }
    
    description
       "Show command extensions by ciena for ciena-mef-egress-qos-binding";    
    
    revision 2017-09-28 {
       description
         "Initial version";
    }
    
    augment "/yp:show/yp:input/yp:showtype" {
    
        case egress-qos-binding{
            leaf egress-qos-binding{
            type empty;
            }
        }
         
    }
}
