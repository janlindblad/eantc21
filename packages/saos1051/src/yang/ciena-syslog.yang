module ciena-syslog {
  namespace "http://www.ciena.com/ns/yang/ciena-syslog";
  prefix "ciena-syslog";

  import ietf-inet-types {
    prefix inet;
  }

  import ciena-types {
    prefix ciena;
  }

  import ietf-syslog {
    prefix syslog;
  }
  
  import ietf-syslog-types {
    prefix syslogtypes;
  }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
  
  description
    "This YANG module defines Ciena's global configuration for syslog settings.

     Copyright (c) 2016 Ciena Corporation.  All rights 
     reserved.

     All information contained herein is, and remains
     the property of Ciena Corporation. Dissemination of this 
     information or reproduction of this material is strictly 
     forbidden unless prior written permission is obtained from 
     Ciena Corporation.";

  revision 2020-04-22 {
    description
      "Removed max-elements limit from leaf severity.";
    reference
      "RFC 6020: YANG - A Data Modeling Language for
       the Network Configuration Protocol (NETCONF).
       No specific reference; standard not available.";
  }
 
  revision 2019-01-31 {
    description
      "Added defaults to leaves.";
    reference
      "RFC 6020: YANG - A Data Modeling Language for
       the Network Configuration Protocol (NETCONF).
       No specific reference; standard not available.";
  }
  revision 2016-08-14 {
    description 
      "Initial version";
    reference
      "RFC 6020: YANG - A Data Modeling Language for
       the Network Configuration Protocol (NETCONF).
       No specific reference; standard not available.";
  }
    
  /*
   * Configuration data nodes
   */
  augment /syslog:syslog/syslog:log-actions/syslog:remote {
    description
      "A replacement for the syslog destination in the ietf-syslog YANG model.
         SAOS only supports one facility per syslog collector and a list of severities per facility.";

    leaf admin-state {
      type ciena:admin-state;
      default enabled;
      description
        "The administrative state of Syslog.";
    }

    list dest {
      key address;
      description
        "A replacement for the ietf-syslog destination list.";
      
      leaf address {
        type "inet:host";
        description
          "Syslog UDP address.";
      }

      leaf admin-state {
        type ciena:admin-state;
        default enabled;
        description
          "The administrative state of the Syslog server.";
      }
      
      leaf port {
        type "inet:port-number" {
          range "514..65535";
        }
        default 514;
        description
          "UDP port number.";
      }
        
      leaf facility {
        type identityref {
          base syslogtypes:syslog-facility;
        }
        default syslogtypes:local6;
        description
          "Describes the Syslog facility.";
      }
        
      leaf-list severity {
        type syslogtypes:severity;
        description
          "Set a list of severities for the facility.
           The severity will default to LOG_INFO if
           none is specified.";
      }
      
      leaf custom-prefix {
        type string {
          length "0..15";
        }
        description
          "Syslog message prefix.";
      }
    }
  }
}
