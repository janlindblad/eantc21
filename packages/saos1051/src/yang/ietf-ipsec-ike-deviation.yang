module ietf-ipsec-ike-deviation {
  namespace "http://www.ciena.com/ns/yang/ietf-ipsec-ike-deviation";
  prefix ike-dev;

  import ietf-ipsec-ike {
    prefix ike;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's specific deviations
     to the ietf-ipsec-ike yang model.

     Copyright (c) 2020 Ciena Corporation.  All rights
     reserved.

     All information contained herein is, and remains the
     property of Ciena Corporation. Dissemination of this
     information or reproduction of this material is strictly
     forbidden unless prior written permission is obtained
     from Ciena Corporation.";

  revision 2020-03-11 {
    description
      "Initial version";
    reference "";
  }

  deviation "/ike:ipsec-ike/ike:number-ike-sas" {
    deviate not-supported;
  }

  deviation "/ike:ipsec-ike/ike:pad/ike:pad-entry/ike:identity/ike:ipv4-address" {
    deviate not-supported;
  }

  deviation "/ike:ipsec-ike/ike:pad/ike:pad-entry/ike:identity/ike:ipv6-address" {
    deviate not-supported;
  }
  deviation "/ike:ipsec-ike/ike:pad/ike:pad-entry/ike:identity/ike:fqdn-string" {

    deviate not-supported;
  }

  deviation "/ike:ipsec-ike/ike:pad/ike:pad-entry/ike:identity/ike:rfc822-address-string" {
    deviate not-supported;
  }

  deviation "/ike:ipsec-ike/ike:pad/ike:pad-entry/ike:identity/ike:dnx509" {
    deviate not-supported;
  }

  deviation "/ike:ipsec-ike/ike:pad/ike:pad-entry/ike:identity/ike:gnx509" {
    deviate not-supported;
  }

  deviation "/ike:ipsec-ike/ike:pad/ike:pad-entry/ike:identity/ike:id-null" {
    deviate not-supported;
  }

  deviation "/ike:ipsec-ike/ike:pad/ike:pad-entry/ike:auth-protocol" {
    deviate not-supported;
  }

  deviation "/ike:ipsec-ike/ike:pad/ike:pad-entry/ike:peer-authentication/ike:eap-method" {
    deviate not-supported;
  }

  deviation "/ike:ipsec-ike/ike:pad/ike:pad-entry/ike:peer-authentication/ike:digital-signature/ike:ca-data" {
    deviate not-supported;
  }

  deviation "/ike:ipsec-ike/ike:conn-entry/ike:authalg" {
    deviate not-supported;
  }

  deviation "/ike:ipsec-ike/ike:conn-entry/ike:encalg" {
    deviate not-supported;
  }

  deviation "/ike:ipsec-ike/ike:conn-entry/ike:autostartup" {
    deviate not-supported;
  }

  deviation "/ike:ipsec-ike/ike:conn-entry/ike:initial-contact" {
    deviate not-supported;
  }

  deviation "/ike:ipsec-ike/ike:conn-entry/ike:version" {
    deviate not-supported;
  }

  deviation "/ike:ipsec-ike/ike:conn-entry/ike:half-open-ike-sa-timer" {
    deviate not-supported;
  }

  deviation "/ike:ipsec-ike/ike:conn-entry/ike:half-open-ike-sa-cookie-threshold" {
    deviate not-supported;
  }

  deviation "/ike:ipsec-ike/ike:conn-entry/ike:local/ike:local-pad-entry-name" {
    deviate replace {
      type leafref {
        path "/ike:ipsec-ike/ike:pad/ike:pad-entry/ike:name";
      }
    }
  }

  deviation "/ike:ipsec-ike/ike:conn-entry/ike:remote/ike:remote-pad-entry-name" {
    deviate replace {
      type leafref {
        path "/ike:ipsec-ike/ike:pad/ike:pad-entry/ike:name";
      }
    }
  }

  deviation "/ike:ipsec-ike/ike:conn-entry/ike:encapsulation-type" {
    deviate not-supported;
  }

  deviation "/ike:ipsec-ike/ike:conn-entry/ike:spd/ike:spd-entry/ike:ipsec-policy-config" {
    deviate not-supported;
  }

  deviation "/ike:ipsec-ike/ike:conn-entry/ike:child-sa-info/ike:pfs-groups" {
    deviate not-supported;
  }

  deviation "/ike:ipsec-ike/ike:conn-entry/ike:child-sa-info/ike:child-sa-lifetime-soft/ike:action" {
    deviate not-supported;
  }

  deviation "/ike:ipsec-ike/ike:conn-entry/ike:child-sa-info/ike:child-sa-lifetime-soft/ike:bytes" {
    deviate not-supported;
  }

  deviation "/ike:ipsec-ike/ike:conn-entry/ike:child-sa-info/ike:child-sa-lifetime-hard/ike:bytes" {
    deviate not-supported;
  }

  deviation "/ike:ipsec-ike/ike:conn-entry/ike:state" {
    deviate not-supported;
  }
}
