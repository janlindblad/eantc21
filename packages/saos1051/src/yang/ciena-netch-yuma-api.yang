module ciena-netch-yuma-api {

    namespace "urn:ciena:params:xml:ns:yang:ciena-pn:ciena-netch-yuma-api";

    prefix "netchyumaapi";

    import yuma-ncx { prefix ncx; }
    import yumaworks-ycontrol { prefix yctl; }

    organization "Ciena";

    description 
     "This yang model defines Ciena defined netch-yuma-api service over Ycontrol";

    revision 2018-05-17 {
        description
          "Add authorization-request";
    }

    revision 2016-05-02 {
        description
          "Add load-bundle-request";
    }

    revision 2015-07-06 {
        description
          "Initial version";
    }

    augment "/yctl:ycontrol/yctl:message-payload/yctl:payload/yctl:payload" {
        container netch-yuma-api {
            choice message-type {

                leaf register-request {
                    type empty;
                    description
                     "Message type: subsys-request;
                      Purpose: register the NETCH-YUMA-API subsystem
                      Expected Response Message: ok or error";
                }

                container edit-request {
                    description
                     "Message type: subsys-request;
                      Purpose: Ask the main server to accept an edit request
                      Expected Response Message: ok or error";

                    leaf log-level {
                        type string;
                        description
                         "Message type: subsys-request;
                          Purpose: Set the server log level 
                          Expected Response Message: ok or error";
                    }
                  
                    leaf allowed-user {
                        type string;
                        description
                         "Message type: subsys-request;
                          Purpose: Add user to yumapro server user database 
                          Expected Response Message: ok or error";
                    }
                    
                    leaf load-bundle {
                        type string;
                        description
                         "Message type: subsys-request;
                          Purpose: Ask the yumapro server to load a bundle
                          Expected Response Message: ok or error";
                    }                    
                }

		container authorization-request {
                  description
                    "Message type: subsys-request;
                     Purpose: Ask the main server to authorize
		     path.
                     Expected Response Message: authorization-response or
		     error";

                  leaf username {
                    type string;
                    description
                      "The user that is being authorized.";
                  }
                  
                  leaf path {
                    type string;
                    description
                      "The xpath to the container or list that
                       will checked.";
                  }                  
                }

		container authorization-response {
                  description
                    "Message type: server-reply
                     Purpose: Send back the nodes the user is authorized
		     to access.
                     Expected Response Message: none";

                  leaf access-denied {
		    type boolean;
                    description
		      "Is access-denied to the node.";
		  }

                  leaf-list access-denied-children {
                    type string;
                    description
                      "The list of children nodes the user is not
                       authorized to access.";
                  }
                }
            }
        } 
    }
}
