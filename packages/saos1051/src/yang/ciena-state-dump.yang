module ciena-state-dump {
  namespace "http://www.ciena.com/ns/yang/ciena-state-dump";
  prefix "ciena-state-dump";

  import ciena-file-transfer-types {
    prefix ciena-ftt;
  }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
   
  description
    "This YANG module defines Ciena's state dump rpc.

     Copyright (c) 2020 Ciena Corporation.  All rights 
     reserved.

     All information contained herein is, and remains
     the property of Ciena Corporation. Dissemination of this 
     information or reproduction of this material is strictly 
     forbidden unless prior written permission is obtained from 
     Ciena Corporation.";

  revision 2020-02-03 {
    description 
      "Initial version";
  }

  typedef state-dump-status-enum {
    type enumeration {
      enum idle {
        description
          "state-dump operation is not initiated";
      }
      enum state-dump-started {
        description
          "state-dump operation is initiated";
      }
      enum state-dump-failed {
        description
          "state-dump operation failed";
      }
      enum state-dump-in-progress {
        description
          "state-dump operation in progress";
      }
      enum state-dump-complete {
        description
          "state-dump operation completed successfully";
      }
    }
  }

  container state-dump-status {
    config false;
    leaf status {
      type state-dump-status-enum;
      description
         "Status of state-dump operation";
    }
  }

  rpc state-dump {
    description
      "Initiates a system state dump.  The status of the state dump
       can be checked in state-dump-status";

    input {
      uses ciena-ftt:file-transfer-parameters; 

      leaf target-path {
        type string;
        description
          "The destination path";
      }

      leaf timeout {
        type uint64; 
        units "seconds";
        description
          "How long should statedump wait in seconds before timing out";
      }
    }
  }
}
