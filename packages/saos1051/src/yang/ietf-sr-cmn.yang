module ietf-sr-cmn {
  namespace "urn:ietf:params:xml:ns:yang:ietf-segment-routing-common";
  prefix sr-cmn;

  import ietf-inet-types {
    prefix inet;
  }

  organization
    "IETF SPRING - SPRING Working Group";

  contact
    "WG Web:   <http://tools.ietf.org/wg/spring/>
     WG List:  <mailto:spring@ietf.org>

     Editor:    Stephane Litkowski





               <mailto:stephane.litkowski@orange.com>
     Editor:    Yingzhen Qu
               <mailto:yingzhen.qu@huawei.com>

     Author:    Acee Lindem
               <mailto:acee@cisco.com>
     Author:    Pushpasis Sarkar
               <mailto:pushpasis.ietf@gmail.com>
     Author:    Jeff Tantsura
               <jefftant.ietf@gmail.com>

    ";
  description
    "The YANG module defines a collection of types and groupings for
     Segment routing.

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  reference "RFC XXXX";

  revision 2018-06-25 {
    description
      "
      * Renamed readable-label-stack-depth to entropy-readable-label-depth;
      ";
    reference "RFC XXXX: YANG Data Model for Segment Routing.";
  }
  revision 2017-07-01 {
    description
      "
       *Conform to RFC6087BIS Appendix C
      ";
    reference "RFC XXXX: YANG Data Model for Segment Routing.";
  }
  revision 2017-03-10 {
    description
      "





       * Add support of SRLB
      ";
    reference "RFC XXXX: YANG Data Model for Segment Routing.";
  }
  revision 2016-10-28 {
    description
      "
       * Add support of MSD (Maximum SID Depth)
       * Update contact info
      ";
    reference "RFC XXXX: YANG Data Model for Segment Routing.";
  }
  revision 2016-10-24 {
    description
      "Initial";
    reference "RFC XXXX: YANG Data Model for Segment Routing.";
  }

  feature sid-last-hop-behavior {
    description
      "Configurable last hop behavior.";
  }

  identity segment-routing-transport {
    description
      "Base identity for segment routing transport.";
  }

  identity segment-routing-transport-mpls {
    base segment-routing-transport;
    description
      "This identity represents MPLS transport for segment
       routing.";
  }

  identity segment-routing-transport-ipv6 {
    base segment-routing-transport;
    description
      "This identity represents IPv6 transport for segment
       routing.";
  }

  identity prefix-sid-algorithm {
    description
      "Base identity for prefix-sid algorithm.";
  }

  identity prefix-sid-algorithm-shortest-path {





    base prefix-sid-algorithm;
    description
      "The default behavior of prefix-sid algorithm.";
  }

  identity prefix-sid-algorithm-strict-spf {
    base prefix-sid-algorithm;
    description
      "This algorithm mandates that the packet is forwared
       according to ECMP-aware SPF algorithm.";
  }

  grouping srlr {
    description
      "Grouping for SR Label Range configuration.";
    leaf lower-bound {
        type uint32;
        description
          "Lower value in the block.";
      }
    leaf upper-bound {
        type uint32;
        description
          "Upper value in the block.";
      }
  }

  grouping srgb-cfg {
    description
      "Grouping for SR Label Range configuration.";
    list srgb {
      key "lower-bound upper-bound";
      ordered-by user;
      description
        "List of global blocks to be
         advertised.";
      uses srlr;
    }
  }

  grouping srlb-cfg {
    description
      "Grouping for SR Local Block range configuration.";
    list srlb {
      key "lower-bound upper-bound";
      ordered-by user;
      description
        "List of SRLBs.";





      uses srlr;
    }
  }

  grouping sid-value-type {
    description
      "Defines how the SID value is expressed.";
    leaf value-type {
      type enumeration {
        enum "index" {
          description
            "The value will be
             interpreted as an index.";
        }
        enum "absolute" {
          description
            "The value will become
             interpreted as an absolute
             value.";
        }
      }
      default "index";
      description
        "This leaf defines how value
         must be interpreted.";
    }
  }

  grouping prefix-sid {
      description
          "This grouping defines cfg of prefix SID.";
      leaf prefix {
          type inet:ip-prefix;
          description
              "connected prefix sid.";
      }
      uses prefix-sid-attributes;
  }

grouping ipv4-sid-cfg {
    description
      "This grouping defines cfg of prefix SID.";
    leaf prefix {
      type inet:ipv4-prefix;
      description
        "connected prefix sid.";
    }
    uses prefix-sid-attributes;
  }
  grouping ipv6-sid-cfg {
    description
      "This grouping defines cfg of prefix SID.";
    leaf prefix {
      type inet:ipv6-prefix;
      description
        "connected prefix sid.";
    }
    uses prefix-sid-attributes;
  }





  grouping last-hop-behavior {
    description
      "Defines last hop behavior";
    leaf last-hop-behavior {
      if-feature "sid-last-hop-behavior";
      type enumeration {
        enum "explicit-null" {
          description
            "Use explicit-null for the SID.";
        }
        enum "no-php" {
          description
            "Do no use PHP for the SID.";
        }
        enum "php" {
          description
            "Use PHP for the SID.";
        }
        enum "n-flag-clear" {
           description
            "The prefix-SID does not represent the node originating the prefix-SID";
        }
      }
      description
        "Configure last hop behavior.";
    }
  }

  grouping node-capabilities {
    description
      "Containing SR node capabilities.";
    container node-capabilities {
      config false;
      description
        "Shows the SR capability of the node.";
      list transport-planes {
        key "transport-plane";
        description
          "List of supported transport planes.";
        leaf transport-plane {
          type identityref {
            base segment-routing-transport;
          }
          description
            "Transport plane supported";
        }
      }
      leaf entropy-readable-label-depth {
        type uint8;
        description
          "Maximum label statck depth that
           the router can read. ";





      }
    }
  }

  grouping prefix-sid-attributes {
    description
      "Containing SR attributes for a prefix.";
    uses sid-value-type;
    leaf start-sid {
      type uint32;
      mandatory true;
      description
        "Value associated with
         prefix. The value must
         be interpreted in the
         context of value-type.";
    }
    leaf range {
      type uint32;
      description
        "Describes how many SIDs could be
         allocated.";
    }
    leaf algorithm {
      type identityref {
        base prefix-sid-algorithm;
      }
      description
        "Prefix-sid algorithm.";
    }
  }
}
