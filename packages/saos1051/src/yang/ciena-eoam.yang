module ciena-eoam {
    namespace "urn:ciena:params:xml:ns:yang:ciena-pn:ciena-eoam";
    prefix "ciena-eoam";

    organization
      "Ciena Corporation";

    contact
      "Web URL: http://www.ciena.com/      
       E-mail:  yang@ciena.com
       Postal:  7035 Ridge Road
                Hanover, Maryland 21076
                U.S.A.
       Phone:   +1 800-921-1144
       Fax:     +1 410-694-5750";

    description
      "This YANG module contains the schema definition for Ciena's
       global configuration of Ethernet Operations, 
       Administration and Management (EOAM).";

    revision "2017-12-27" {
      description
        " 1. Modified container names to meaningful names by adding 
             protocol name (eoam) as their prefix.
          2. Added clear-eoam-statistics RPC.";
    }
    
    revision "2015-02-25" {
      description
        "Initial Version.";
      reference
        "Ciena EOAM global configuration";
    }
    
    container eoam-global-config-status {        
        leaf admin-state {           
            type enumeration {
                enum enabled {
                    description
                        "Enable EOAM globally on this device.";
                }
                enum disabled {
                    description
                       "Disable EOAM globally on this device.";
                }
            }
            default disabled;
            description
                "Enable or disable EOAM globally on this device";
        } 
        leaf oper-state {           
            type enumeration {
                enum enabled {
                    description
                        "EOAM is globally enabled on this device.";
                }
                enum disabled {
                   description
                        "EOAM is globally enabled on this device.";
                }
            }
            config false;
            description
                "EOAM global operational status.";
        }
        description
            "EOAM global operational status on this device";
    }

    rpc clear-eoam-statistics {
        description
            "Administratively clear eoam statistics";
    }
}
