module ciena-state-dump-deviation {
  namespace "http://www.ciena.com/ns/yang/ciena-state-dump-dev";
  prefix "ciena-state-dump-dev";

  import ciena-state-dump { prefix state-dump; }

  revision 2020-02-03 {
    description
      "Initial revision";
  }

  deviation /state-dump:state-dump/state-dump:input/state-dump:tls-service-profile {
    deviate not-supported;
  }
}
