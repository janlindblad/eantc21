module ciena-ietf-ipsec-ike {
  namespace "http://www.ciena.com/ns/yang/ciena-ietf-ipsec-ike";
  prefix ciena-ike;

  import ietf-inet-types {
    prefix inet;
  }

  import ietf-yang-types {
    prefix yang;
  }

  import ietf-ipsec-ike {
    prefix ike;
  }

  import ietf-ipsec-common {
    prefix ic;
  }

  import ietf-crypto-types {
    prefix ct;
  }

  import openconfig-interfaces {
    prefix oc-if;
  }

  import ciena-openconfig-interfaces {
    prefix cn-if;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's specific augmentations
     to the ietf-ipsec-ike yang model.

     Copyright (c) 2020 Ciena Corporation.  All rights
     reserved.

     All information contained herein is, and remains the
     property of Ciena Corporation. Dissemination of this
     information or reproduction of this material is strictly
     forbidden unless prior written permission is obtained
     from Ciena Corporation.";

  revision 2020-03-11 {
    description
      "Initial version";
    reference "";
  }

  typedef encryption-type {
    type enumeration {
      enum aes128 {
        description
          "128 bit AES-CBC encryption.";
      }
      enum aes256 {
        description
          "256 bit AES-CBC encryption.";
      }
    }
    description
      "ESP encryption algoritms used for IPsec SA
       connections.";
  }

  typedef integrity-type {
    type enumeration {
      enum sha256 {
        description
          "SHA2_256_128 HMAC algorithm.";
      }
      enum sha512 {
        description
          "SHA2_512_256 HMAC algorithm.";
      }
    }
    description
      "Integrity algoritms used for IPsec SA
       connections.";
  }

  typedef dh-group-type {
    type enumeration {
      enum modp2048 {
        description
          "2048 bit modulus Diffie Hellman
           group.";
      }
      enum modp4096 {
        description
          "4096 bit modulus Diffie Hellman
           group.";
      }
    }
    description
      "Diffie Hellman groups used for IPsec SA
       connections.";
  }

  grouping ike-counters {
    description
      "IKE message counters common to IPsec global
       and connection state data.";
    leaf ike-rekey-init {
      type uint64;
      description
        "Initiated IKE_SA rekeyings.";
    }
    leaf ike-rekey-resp {
      type uint64;
      description
        "Responded IKE_SA rekeyings.";
    }
    leaf child-rekey {
      type uint64;
      description
        "Completed CHILD_SA rekeyings.";
    }
    leaf ike-init-in-req {
      type uint64;
      description
        "Received IKE_SA_INIT requests.";
    }
    leaf ike-init-in-resp {
      type uint64;
      description
        "Received IKE_SA_INIT responses.";
    }
    leaf ike-init-out-req {
      type uint64;
      description
        "Sent IKE_SA_INIT requests.";
    }
    leaf ike-init-out-resp {
      type uint64;
      description
        "Sent IKE_SA_INIT responses.";
    }
    leaf ike-auth-in-req {
      type uint64;
      description
        "Received IKE_SA_AUTH requests.";
    }
    leaf ike-auth-in-resp {
      type uint64;
      description
        "Received IKE_SA_AUTH responses.";
    }
    leaf ike-auth-out-req {
      type uint64;
      description
        "Sent IKE_SA_AUTH requests.";
    }
    leaf ike-auth-out-resp {
      type uint64;
      description
        "Sent IKE_SA_AUTH responses.";
    }
    leaf create-child-in-req {
      type uint64;
      description
        "Received CREATE_CHILD_SA requests.";
    }
    leaf create-child-in-resp {
      type uint64;
      description
        "Received CREATE_CHILD_SA responses.";
    }
    leaf create-child-out-req {
      type uint64;
      description
        "Sent CREATE_CHILD_SA requests.";
    }
    leaf create-child-out-resp {
      type uint64;
      description
        "Sent CREATE_CHILD_SA responses.";
    }
    leaf info-in-req {
      type uint64;
      description
        "Received INFORMATIONAL requests.";
    }
    leaf info-in-resp {
      type uint64;
      description
        "Received INFORMATIONAL responses.";
    }
    leaf info-out-req {
      type uint64;
      description
        "Sent INFORMATIONAL requests.";
    }
    leaf info-out-resp {
      type uint64;
      description
        "Sent INFORMATIONAL responses.";
    }
  }

  grouping ike-algorithm-state {
    description
      "Information about IKE algoritms in-use.";
    leaf encryption-algorithm-information {
      type string;
      description
        "IKE encryption algorithm.";
    }
    leaf integrity-algorithm-information {
      type string;
      description
        "IKE integrity algorithm.";
    }
    leaf dh-group-information {
      type string;
      description
        "IKE Diffie-Hellman group.";
    }
  }

  identity ike-event-type {
    description
      "Base identity IPsec IKE event types.";
  }

  identity ike-sa-up {
    base ike-event-type;
    description
      "IKE SA established event.";
  }

  identity ike-sa-down {
    base ike-event-type;
    description
      "IKE SA terminated event.";
  }

  identity ike-sa-rekey {
    base ike-event-type;
    description
      "IKE SA rekey event.";
  }

  identity ike-child-sa-up {
    base ike-event-type;
    description
      "IKE child SA established event.";
  }

  identity ike-child-sa-down {
    base ike-event-type;
    description
      "IKE child SA terminated event.";
  }

  identity ike-child-sa-rekey {
    base ike-event-type;
    description
      "IKE child SA rekey event.";
  }

  augment "/ike:ipsec-ike/ike:pad/ike:pad-entry/ike:peer-authentication/ike:digital-signature" {
    description
      "Replace ca-data leaf-list with a singular ca-data leaf.";
    leaf ca-data {
      type ct:x509;
      description
        "Trusted Certification Authorities (CA) certificate encoded
         using ASN.1 distinguished encoding rules (DER).";
      reference
        "RFC XXX: Common YANG Data
         Types for Cryptography.";
    }
  }

  augment "/ike:ipsec-ike/ike:conn-entry" {
    description
      "Add initiator leaf and nodes to specify
       authentication and encryption algorithms
       by keyword.";
    leaf-list authentication-algorithm {
      type integrity-type;
      ordered-by user;
      description
        "Authentication algorithm for establishing
         the IKE SA. This list is ordered following
         from the higher priority to lower priority.
         First node of the list will be the algorithm
         with higher priority. If this list is empty
         the default integrity algorithm value assumed
         is NONE.";
    }
    leaf-list encryption-algorithm {
      type encryption-type;
      ordered-by user;
      description
        "Encryption or AEAD algorithm for the IKE
         SAs. This list is ordered following
         from the higher priority to lower priority.
         First node of the list will be the algorithm
         with higher priority. If this list is empty
         the default encryption value assumed is
         NULL.";
    }
    leaf initiator {
      type boolean;
      default "false";
      description
        "Setting to 'true' causes the IPsec connection
         to be initiated when fully configured. If 'false'
         then the connection operates as a responder only.";
    }
  }

  augment "/ike:ipsec-ike/ike:conn-entry/ike:child-sa-info/ike:child-sa-lifetime-soft" {
    description
      "Rename child-sa-lifetime-soft 'bytes' leaf";
    leaf byte-count {
      type uint32;
      default "0";
      description
        "If the IPsec SA processes the number of bytes
         expressed in this leaf, the IPsec SA expires and
         should be rekeyed. The value 0 implies
         infinite.";
    }
  }

  augment "/ike:ipsec-ike/ike:conn-entry/ike:child-sa-info/ike:child-sa-lifetime-hard" {
    description
      "Rename child-sa-lifetime-hard 'bytes' leaf";
    leaf byte-count {
      type uint32;
      default "0";
      description
        "If the IPsec SA processes the number of bytes
         expressed in this leaf, the IPsec SA expires and
         should be rekeyed. The value 0 implies
         infinite.";
    }
  }

  augment "/ike:ipsec-ike/ike:conn-entry/ike:spd/ike:spd-entry" {
    description
      "Add ipsec-subnet-policy-config container to
       simplify SPD configuration when only a single
       subnet policy is required.";
    container ipsec-subnet-policy-config {
      description
        "Simplified policy configuration for
         connections with a single SPD policy.";
      leaf local-subnet {
        type inet:ip-prefix;
        description
          "Local IP address subnet.";
      }
      leaf remote-subnet {
        type inet:ip-prefix;
        description
          "Remote IP address subnet.";
      }
      leaf anti-replay-window {
        type uint64;
        default "32";
        description
          "A 64-bit counter used to determine whether an
           inbound ESP packet is a replay.";
        reference "Section 4.4.2.1 in RFC 4301.";
      }
      leaf ext-seq-num {
        type boolean;
        default "false";
        description
          "True if this IPsec SA is using extended
           sequence numbers. True 64 bit counter,
           False 32 bit.";
      }
      container esp-algorithms {
        description
          "Configuration of Encapsulating
           Security Payload (ESP) parameters and
           algorithms.";
        leaf integrity {
          type integrity-type;
          default "sha256";
          description
            "Configuration of ESP authentication
             based on the specified integrity
             algorithm.";
          reference "Section 3.2 in RFC 4303.";
        }
        leaf encryption {
          type encryption-type;
          default "aes256";
          description
            "Configuration of ESP encryption
             algorithms.";
          reference "Section 3.2 in RFC 4303.";
        }
        reference "RFC 4303.";
      }
      leaf ip-tunnel-interface {
        type leafref {
          path "/oc-if:interfaces/oc-if:interface/oc-if:name";
        }
        must "/oc-if:interfaces/oc-if:interface[name = current()]/oc-if:config/cn-if:type[.='ip-tunnel']" {
          error-message "Referenced interface must be of type 'ip-tunnel'.";
        }
        description
          "Name of IP tunnel interface utilized by this connection.
           TEP ip-adresses are implicitly retrieved from the
           specified interface.";
      }
    }
  }

  augment "/ike:ipsec-ike" {
    description
      "Add ipsec-ike-state container for reporting IPsec
       global, SA, and child SA operational state.";
    container ipsec-ike-state {
      config false;
      container ike-global-state {
        leaf total-ike-sas {
          type uint64;
          description
            "Total number of active IKE SAs.";
        }
        leaf invalid {
          type uint64;
          description
            "Messages with invalid types, length
             or an out-of-range value";
        }
        leaf invalid-spi {
          type uint64;
          description
            "Messages with invalid IKE SPI.";
        }
        uses ciena-ike:ike-counters;
        description
          "Global IKE state and message counters";
      }

      list ike-sa-state {
        key "name";
        description
          "IKE SA operational state information including child SA
           state instances." ;
        leaf name {
          type string;
          mandatory true;
          description
            "SA connection entry name.";
        }
        leaf unique-id {
          type string;
          description
            "IKE SA unique identifier.";
        }
        leaf ike-state-information {
          type string;
          description
            "IKE state information.";
        }
        leaf local-host {
          type string;
          description
            "local IKE endpoint address.";
        }
        leaf local-id {
          type string;
          description
            "local IKE endpoint identifier.";
        }
        leaf remote-host {
          type string;
          description
            "remote IKE endpoint address.";
        }
        leaf remote-id {
          type string;
          description
            "remote IKE endpoint identifier.";
        }
        leaf initiator {
          type boolean;
          description
            "It is acting as initiator for this connection.";
        }
        leaf initiator-ikesa-spi {
          type ike:ike-spi;
          description
            "Initiator's IKE SA SPI.";
        }
        leaf responder-ikesa-spi {
          type ike:ike-spi;
          description
            "Responder's IKE SA SPI.";
        }
        leaf nat-local {
          type boolean;
          description
            "True, if local endpoint is behind a NAT.";
        }
        leaf nat-remote {
          type boolean;
          description
            "True, if remote endpoint is behind a NAT.";
        }
        container encapsulation-type {
          uses ic:encap;
          description
            "This container provides information about the
             source and destination ports of encapsulation
             that IKE is using, and the type of encapsulation
             when NAT traversal is required.";
          reference
            "RFC 8229.";
        }
        leaf established {
          type uint64;
          units seconds;
          description
            "Seconds since this IKE SA has been established.";
        }
        leaf current-rekey-time {
          type uint64;
          units seconds;
          description
            "Seconds before IKE SA must be rekeyed.";
        }
        leaf current-reauth-time {
          type uint64;
          units seconds;
          description
            "Seconds before IKE SA must be re-authenticated.";
        }
        uses ciena-ike:ike-algorithm-state;
        uses ciena-ike:ike-counters;

        list child-sa-state {
          key "name";
          leaf name {
            type string;
            mandatory true;
            description
              "Child SA name.";
          }
          leaf unique-id {
            type string;
            description
              "Child SA unique identifier.";
          }
          leaf request-id {
            type string;
            description
              "Child SA reqid.";
          }
          leaf ike-state-information {
            type string;
            description
              "Child SA IKE state information.";
          }
          leaf mode {
            type ic:ipsec-mode;
            description
              "IPsec mode";
          }
          leaf protocol {
            type ic:ipsec-protocol-parameters;
            description
              "IPsec protocol.";
          }
          leaf udp-encap {
            type boolean;
            description
              "UDP encapsulation is in-use.";
          }
          leaf esn {
            type boolean;
            description
              "Extended sequence numbers are in-use.";
          }
          leaf spi-inbound {
            type yang:hex-string;
            description
              "Inbound SPI";
          }
          leaf spi-outbound {
            type yang:hex-string;
            description
              "Outbound SPI.";
          }
          leaf mark-inbound {
            type yang:hex-string;
            description
              "Inbound mark value";
          }
          leaf mark-outbound {
            type yang:hex-string;
            description
              "Outbound mark value.";
          }
          uses ciena-ike:ike-algorithm-state;
          leaf rekey-time {
            type uint32;
            units seconds;
            description
              "Time in seconds before child SA is rekeyed.";
          }
          leaf life-time {
            type uint32;
            units seconds;
            description
              "Time in seconds before child SA expires.";
          }
          leaf install-time {
            type uint32;
            units seconds;
            description
              "Time in seconds since child SA was installed.";
          }
          leaf last-inbound-time {
            type uint32;
            units seconds;
            description
              "Time in seconds since last inbound packet.";
          }
          leaf last-outbound-time {
            type uint32;
            units seconds;
            description
              "Time in seconds since last outbound packet.";
          }
          leaf tx-bytes {
            type uint64;
            description
              "Total number of bytes transmitted.";
          }
          leaf rx-bytes {
            type uint64;
            description
              "Total number of bytes received.";
          }
          leaf tx-packets {
            type uint64;
            description
              "Total number of packets transmitted.";
          }
          leaf rx-packets {
            type uint64;
            description
              "Total number of packets received.";
          }
          description
            "Child SA operational state and statistics";
        } // ike-child-sa-state
      } // ike-sa-state

      description
        "IPsec global, SA, and child SA operational state.";
    } // ipsec-ike-state
  } // ipsec-ike

  notification ipsec-ike-event {
    description
      "A notification of an operational event
       for an IPsec tunnel connection or child
       SA";
    container event {
      description
        "Data definitions related to event on
         a specific instance.";
      leaf sa-name {
        type string;
        description
          "The name of the IPsec SA tunnel
           connection instance.";
      }
      leaf child-sa-name {
        type string;
        description
          "The name of the IPsec child SA
           instance.";
      }
      leaf ike-event {
        type identityref {
          base ike-event-type;
        }
        description
          "IKE event issued for the SA or
           child SA.";
      }
    }
  }

  rpc clear-ipsec-ike-global-counters {
    description
      "Clear IPsec global IKE message counters";
  }

  rpc clear-ipsec-ike-sa-counters {
    description
      "Clear IPsec IKE message counters for a
       specific SA.";
    input {
      leaf name {
        type leafref {
          path "/ike:ipsec-ike/ike:conn-entry/ike:name";
        }
        description
          "IKE SA name.";
      }
    }
  }
}
