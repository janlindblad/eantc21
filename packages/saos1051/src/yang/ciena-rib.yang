module ciena-rib {
    namespace   "http://ciena.com/ns/yang/ciena/ciena-rib";
    prefix "rib";

    import openconfig-interfaces {
        prefix "oc-if";
    }

  import ciena-openconfig-interfaces {
       prefix cn-if;
   }

    import ietf-inet-types {
        prefix inet;
    }

    import ciena-vrf {
        prefix "vrf";
    }

    import ciena-l3-types {
        prefix cn-l3-types;
    }
    organization
        "Ciena Corporation";

    contact
        "Web URL: http://www.ciena.com/
         E-mail:  yang@ciena.com
         Postal:  7035 Ridge Road
                  Hanover, Maryland 21076
                      U.S.A.
         Phone:   +1 800-921-1144
         Fax:     +1 410-694-5750";

    description
        "This YANG module defines Ciena's specific rib yang model.
        Copyright (c) 2018  Ciena Corporation.  All rights
        reserved.
        All information contained herein is, and remains the
        property of Ciena Corporation. Dissemination of this
        information or reproduction of this material is strictly
        forbidden unless prior written permission is obtained
        from Ciena Corporation.";

    revision "2020-09-03" {
        description
           "Add a new RIB key to filter FIB installed routes & allow
            partial key filtering of empty destination prefixes.
            Add Must statement addition to ensure outgoing interface is binded to the same VRF.";
    }

    revision "2020-02-10" {
        description
           "Changing RW yang to allow configuring multiple next-hops for Ipv4.
            Changing Rib-state next-hop address type to ip-address for Ipv4 and Ipv6.
            Adding next-hop interface as a leaf for Ipv6 rib route configuration and
            Adding Must statement to allow specific types of interfaces for Ipv4 and Ipv6.
            Blocking config of IPv6 outgoing-interface only option to be inline with IPv4.
            Adding option to retrieve longest prefix matched route when IPv4/IPv6 address is provided.";
    }

    revision "2020-01-21" {
        description
            "Changing RO yang to have route-preference as a key";
    }

    revision "2017-06-21" {
        description
            "Initial version of Rib model.";
    }

    grouping routing-attributes {
        description
            "Routing attributes";
        leaf route-preference  {
            type uint32 {
                range "1..255";
            }
            description
                "Numerical value that allows for comparing  routes from different protocols.
                Also known as administrative-distance.";
        }
        leaf tag  {
            type  int64 {
                range "0..4294967295";
            }
            default "0";
            description
                "Route tag";
        }
        leaf description {
            type cn-l3-types:string-max-256;
            description
                "Description of the route";
        }
    }

    grouping  rib-grouping {
        description
            "Rib config grouping";
        container rib {
            description
                "IP routing table";

            list vrf {
                key "name";
                description
                    "VRF routing instance";
                leaf name {
                    type leafref {
                        path "/vrf:vrf/vrf:vrfName";
                    }
                    description
                        "Virtual Routing and Forwarding instance";
                }

                list ipv4 {
                    key "destination-prefix";
                                        description
                                                "Ipv4 routes";
                    leaf destination-prefix  {
                        type  inet:ipv4-prefix;
                        description
                            "IPv4 destination prefix";
                    }
                    choice next-hop-options {
                        mandatory "true";

                        case outgoing-interfaces {
                            list outgoing-interface {
                                min-elements 1;
                                key "name";
                                description
                                    "Name of the outgoing interface";
                                leaf name  {
                                    type string
                                    {
                                        pattern "Null0";
                                    }
                                    description
                                        "Name of the outgoing interface";
                                }
                                uses routing-attributes;
                            }
                        }
                        case next-hops {
                            list next-hop {
                                min-elements 1;
                                key "address";
                                description
                                    "IPv4 address of the next hop";
                                leaf address  {
                                    type inet:ipv4-address;
                                    description
                                        "IPv4 address or blackhole config for the next hop.";
                                }
                                leaf outgoing-interface-name {
                                    type  leafref {
                                        path "/oc-if:interfaces/oc-if:interface/oc-if:name";
                                     }
                                     must "/oc-if:interfaces/oc-if:interface[oc-if:name=current()]/oc-if:config/" +
                                          "cn-if:vrfName=../../../name and " +
                                          "/oc-if:interfaces/oc-if:interface[oc-if:name=current()]/oc-if:config/" +
                                          "cn-if:type[.='ip' or .='system' or .='loopback' or .='ip-unnumbered' or .='ip-tunnel']" {
                                         error-message "Referenced interface cannot be configured for this static route.";
                                     }
                                    description
                                        "Name of the outgoing interface";
                                }
                                uses routing-attributes;
                            }
                        }
                    }
                }

                list ipv6 {
                    key "destination-prefix";
                    description
                        "Ipv6 routes";
                    leaf destination-prefix  {
                        type  inet:ipv6-prefix;
                        description
                            "IPv6 destination prefix.";
                    }

                    choice next-hop-options {
                        mandatory "true";
                        case outgoing-interfaces {
                            list outgoing-interface {
                                min-elements 1;
                                key "name";
                                description
                                    "List of the outgoing interfaces";
                                leaf name  {
                                    type string {
                                        pattern "Null0";
                                    }
                                    description
                                    "Name of the outgoing interface";
                                }
                                leaf route-preference  {
                                    type  uint32 {
                                        range "1..255";
                                    }
                                    description
                                        "Numerical value that allows for comparing
                                        routes from different protocols.
                                        Also known as administrative-distance.";
                                }
                            }
                        }

                        case next-hops {
                            list next-hop {
                                min-elements 1;
                                key "address";
                                description
                                    "IPv6 address of the next hop";
                                leaf address  {
                                    type  inet:ipv6-address;
                                    description
                                        "IPv6 address of the next hop";
                                }
                                leaf route-preference  {
                                    type  uint32 {
                                        range "1..255";
                                    }
                                    description
                                        "Numerical value that allows for comparing
                                        routes from different protocols.
                                        Also known as administrative-distance.";
                                }
                                leaf outgoing-interface-name {
                                    type  leafref {
                                        path "/oc-if:interfaces/oc-if:interface/oc-if:name";
                                    }
                                    must "/oc-if:interfaces/oc-if:interface[oc-if:name=current()]/oc-if:config/" +
                                         "cn-if:vrfName=../../../name and " +
                                         "/oc-if:interfaces/oc-if:interface[oc-if:name=current()]/oc-if:config/" +
                                         "cn-if:type[.='ip' or .='system' or .='loopback' or .='ip-unnumbered' or .='ip-tunnel']" {
                                         error-message "Referenced interface cannot be configured for this static route.";
                                    }

                                    description
                                        "Name of the outgoing interface";
                                }
                            }
                        }
                    }
                }
            }
        }
    }
    uses rib-grouping;

    grouping source-protocol {
        description
            "Source-protocol attributes";
        leaf protocol-subtype  {
            type string;
            description
                "Protocol Subtype";
        }
        leaf route-preference  {
            type  uint8;
            description
                "Numerical value that allows for comparing
                routes from different protocols.
                Also known as administrative-distance.";
        }
        leaf metric  {
            type  uint32;
            description
                "Route metric";
        }
        leaf blackhole  {
            type string;
            description
                "Silently discard the packet.";
        }
        leaf last-updated  {
            type string;
            description
                "Time stamp of the last modification of the route.  If the
                route was never modified, it is the time when the route was
                inserted into the RIB.";
        }
        leaf active  {
            type boolean;
            description
                "Presence of this leaf indicates that the route is preferred
                among all routes in the same RIB that have the same
                destination prefix.";
        }
    }

    grouping  rib-state-grouping {
        description
            "Rib state attributes";
        container rib-state {
            description
                "Rib state container";
            config false;
            list vrf {
                key "name";
                leaf name  {
                    type leafref {
                        path "/vrf:vrf/vrf:vrfName";
                    }
                    description
                        "Routing and Forwarding Instance name";
                }
                list ipv4 {
                    description
                        "IPv4 routing table";
                    key "destination-prefix type route-preference selected-only";
                    leaf destination-prefix  {
                        type union{
                           type inet:ipv4-address;
                           type inet:ipv4-prefix;
type string {length 0;}
                        }
                        description
                            "IPv4 destination prefix or destination address.";
                    }
                    leaf type  {
                         type string;
                         description
                            "Type of the routing protocol from which the route
                             originated.";
                    }
                    leaf matched-prefix  {
                        type  inet:ipv4-prefix;
                        description
                            "IPv4 matched destination prefix";
                    }
                    leaf selected-only {
                        type boolean;
                        description
                            "FIB installed selected route for IPv4.";
                    }
                    uses source-protocol;
                    list next-hops {
                        key "index";
                        description
                            "Next hop state attributes ";
                        leaf index  {
                            type  uint8;
                            description
                                "Index for next hop";
                        }
                        leaf address  {
                            type  inet:ip-address;
                            description
                                "Ipv4 address";
                        }
                        leaf outgoing-interface  {
                            type string;
                            description
                                "Name of the outgoing interface";
                        }
                        leaf selected-route  {
                            type boolean;
                            description
                               "Preferred route among all routes in the same
                                RIB that have the same destination prefix";
                         }
                         leaf recursive-next-hop {
                             type string;
                             description
                                 "Recursive next-hop information.";
                         }
                       }
                    }
                list ipv6 {
                    description
                        "IPv6 routing table";
                    key "destination-prefix type route-preference selected-only";
                    leaf destination-prefix  {
                         type union{
                             type inet:ipv6-address;
                             type inet:ipv6-prefix;
type string {length 0;}
                         }
                         description
                            "IPv6 destination prefix or destination address.";
                    }
                        leaf type  {
                            type string;
                            description
                                "Type of the routing protocol from which the route
                                originated.";
                        }
                        leaf matched-prefix  {
                            type  inet:ipv6-prefix;
                            description
                                "IPv6 matched destination prefix";
                        }
                        leaf selected-only {
                            type boolean;
                            description
                                "FIB installed selected route for IPv6.";
                        }
                        uses source-protocol;
                        list next-hops {
                            key "index";
                            description
                                "Next hop state attributes ";
                            leaf index  {
                                type  uint8;
                                description
                                    "Index for next hop";
                            }
                            leaf address  {
                                type  inet:ip-address;
                                description
                                    "Ipv6 address";
                            }
                            leaf outgoing-interface  {
                                type string;
                                description
                                    "Name of the outgoing interface";
                            }
                            leaf selected-route  {
                                type boolean;
                                description
                                    "Preferred route among all routes in the same
                                    RIB that have the same destination prefix";
                            }
                            leaf recursive-next-hop {
                                type string;
                                description
                                    "Recursive next-hop information.";
                        }
                    }
                }

                list summary {
                    key "protocol-index";
                    description
                        "Summary of all routes";

                    leaf protocol-index  {
                        type  uint32;
                        description "Index for count of routes for IPv4/IPv6";
                    }

                    leaf total-routes  {
                        type  uint32;
                        description "Total Routes in the RIB from all protocols";
                    }

                    leaf total-paths  {
                        type  uint32;
                        description "Total Paths [all destinations]in the
                                     RIB from all protocols including ECMP";
                    }

                    leaf fib-count  {
                        type  uint32;
                        description "Total Routes in the FIB from all protocols";
                    }

                    leaf ecmp-routes  {
                        type  uint32;
                        description "Total ECMP routes in the RIB from all protocols";
                    }

                    leaf ecmp-paths  {
                        type  uint32;
                        description "Total ECMP paths [all destinations]
                                     in the RIB from all protocols";
                    }

                    leaf ecmp-path-counters  {
                        type  string;
                        description "ECMP path counters detailed description from all protocols";
                    }

                    list route-source {
                        key "type";
                        description
                            "Statistics of different Route Types";

                        leaf type  {
                            type  string;
                            description "Type of Route from all protocols";
                        }

                        leaf type-count  {
                            type  uint32;
                            description "Total number routes for each Route type";
                        }
                    }
                }
            }
        }
    }
    uses rib-state-grouping;

    rpc clear-rib {
        input  {
            leaf destination-prefix  {
                type cn-l3-types:ip-prefix;
                description
                    "Ip prefix address";
            }
            leaf vrf  {
                type leafref {
                    path "/vrf:vrf/vrf:vrfName";
                }
                description
                    "Routing and Forwarding Instance name.";
            }
        }
        output{
            leaf response {
                type string;
                description
                    "The response could be 'success', or the reason for rib route clear failure";
            }
        }
    }
}
