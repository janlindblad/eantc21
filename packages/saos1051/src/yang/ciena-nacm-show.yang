module ciena-nacm-show{
    yang-version 1.1;
    namespace "http://www.ciena.com/ns/ciena-nacm-show";
    prefix ciena-nacm-show;
    import yangcli-pro { prefix yp; }
    
    description
       "Show command extensions by ciena for ciena-nacm";    
    
    revision 2017-09-28 {
       description
         "Initial version";
    }
    
    augment "/yp:show/yp:input/yp:showtype" {
    
        case nacm{
            leaf nacm{
                type empty;
            }
        }
         
    }
}
