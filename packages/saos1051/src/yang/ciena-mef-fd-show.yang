module ciena-mef-fd-show{
    yang-version 1.1;
    namespace "http://www.ciena.com/ns/ciena-mef-fd-show";
    prefix ciena-mef-fd-show;
    import yangcli-pro { prefix yp; }
    
    description
       "Show command extensions by ciena for ciena-mef-fd";    
    
    revision 2017-09-28 {
       description
         "Initial version";
    }
    
    augment "/yp:show/yp:input/yp:showtype" {
    
        case forwarding-domain{
            leaf forwarding-domain{
                type union{
                    type string;
                }
            }
        }
         
    }
}
