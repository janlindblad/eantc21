module ciena-rss-queue {
  namespace "http://www.ciena.com/ns/yang/ciena-rss-queue";
  prefix "cn-rss-queue";

  import openconfig-interfaces {
    prefix oc-if;
  }

  import ciena-openconfig-interfaces {
    prefix cn-oc-if;
  }

  import ciena-subsystem-resource {
    prefix cn-res;
  }

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description
    "YANG module for scale queues used in software forwarding
     planes.

     The module provides a means of creating multiple Receive Side
     Scaling (RSS) Queues for network interfaces and mapping those
     queues to a set of worker threads in the virtual forwarding
     plane that will service those queues.

     This module reports the number of receive and transmit scaling
     queues per interface and the worker threads assigned to those
     queues.

    Copyright (c) 2020 Ciena Corporation.  All rights reserved.

    All information contained herein is, and remains
    the property of Ciena Corporation. Dissemination of this
    information or reproduction of this material is strictly
    forbidden unless prior written permission is obtained from
    Ciena Corporation.";

  revision 2020-09-17 {
    description
      "Add transmit packet scaling (XPS) queue state container";
    reference
      "No specific reference.";
  }

  revision 2020-03-02 {
    description
      "Initial version.";
    reference
      "RFC 6020: YANG - A Data Modeling Language for
       the Network Configuration Protocol (NETCONF).
       No specific reference; standard not available.";
  }

  typedef queue-index {
    type uint16 {
      range "1..1024";
    }
    description
      "Limit the range of scale queue indices";
  }

  container rss-queue-config {
    description
      "Configuration for RSS queue management.";

    list interface {
      key name;
      description
        "List of ETTP interfaces.";

      leaf name {
        type leafref {
           path "/oc-if:interfaces/oc-if:interface/oc-if:name";
        }
        must "/oc-if:interfaces/oc-if:interface[name = current()]" +
             "/oc-if:config/cn-oc-if:type = 'ettp'" {
          error-message
            "Referenced interface must be of type 'ettp'.";
        }
        description
          "Interface on which RSS has to be enabled.";
      }

      leaf num-rss-queues {
        type uint16;
        description
          "Number of receive queues to be created for the interface.";
      }

      list queue {
        key queue-id;
        description
          "List of receive queues created for this interface.";

        leaf queue-id {
          type queue-index;
          description
            "Identifier of the receive queue.";
        }

        leaf worker-thread {
          type leafref {
            path "/cn-res:subsystems/cn-res:subsystem/"
                 + "cn-res:worker-threads/cn-res:worker-thread/"
                 + "cn-res:thread-name";
          }
          description
            "Identifier of the worker thread that processes the packets
             received on this queue.";
        }
      }
    }
  }

  container rss-queue-state {
    config false;
    description
      "Operational data for RSS queue management.";

    list interface {
      key name;
      description
        "List of ETTP interfaces.";

      leaf name {
        type string;
        description
          "Interface on which RSS is enabled.";
      }

      leaf num-rss-queues {
        type uint16;
        description
          "Number of receive queues active on the interface.";
      }

      list queue {
        key queue-id;
        description
          "List of receive queues created for this interface.";

        leaf queue-id {
          type queue-index;
          description
            "Identifier of the receive queue.";
        }

        leaf worker-thread {
          type string;
          description
            "Identifier of the worker thread that processes the packets
             received on this queue.";
        }
      }
    }
  }

  container xps-queue-state {
    config false;
    description
      "The current state of the Transmit Packet Steering (XPS) queue
       assignments.";

    list interface {
      key name;
      description
        "The list of ETTP interfaces using XPS.";

      leaf name {
        type string;
        description
          "The name of the interface using XPS.";
      }

      leaf num-xps-queues {
        type uint16;
        description
          "The number of transmit packet steering queues created for the
           interface.";
      }

      list active-xps-queue {
        key queue-id;
        description
          "List of active transmit packet steering queues on this
           interface.";

        leaf queue-id {
          type queue-index;
          description
            "Identifier of the transmit queue.";
        }

        leaf-list worker-threads {
          type string;
          description
            "Name of the worker-threads that feed this transmit queue.";
        }
      }
    }
  }
}
