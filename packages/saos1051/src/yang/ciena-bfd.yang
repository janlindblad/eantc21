module ciena-bfd {

  namespace "http://ciena.com/ns/yang/ciena-bfd";

  prefix "bfd";

  import openconfig-interfaces {
     prefix "oc-if";
  }

  import ciena-mpls-tp-corouted {
     prefix "mpls-tp";
  }

  import ciena-bfd-types {
     prefix "bfd-types";
  }

  import ietf-inet-types {
     prefix "inet";
  }

  organization
      "Ciena Corporation";

  contact
      "Web URL: http://www.ciena.com/
       E-mail:  yang@ciena.com
       Postal:  7035 Ridge Road
                Hanover, Maryland 21076
                    U.S.A.
       Phone:   +1 800-921-1144
       Fax:     +1 410-694-5750";

  description
      "This YANG module defines Ciena's specific BFD protocol.
      Copyright (c) 2019  Ciena Corporation.  All rights
      reserved.
      All information contained herein is, and remains the
      property of Ciena Corporation. Dissemination of this
      information or reproduction of this material is strictly
      forbidden unless prior written permission is obtained
      from Ciena Corporation.";

  revision 2020-08-19 {
    description 
      "Added Notification for BFD session state change.
       Added global-state container to get global bfd session statistics.
       Added session-summary information in bfd global-state container.
       Added a configurable global container.";
  }

  revision 2010-02-14 {
    description "Initial revision.";
  }

  container bfd {
    description "BFD configuration and operational data.";

    container global {
      description
        "BFD global configuration data.";
      leaf admin-down {
        type boolean;
        default false;
        description
           "Is BFD global administratively down.";
      }
    }

    container global-state {
      description
        "Bfd global operational data.";

      config false;
      container ipv4-bfd-summary {
         description
           "Ipv4 bfd session summary.";

         uses bfd-types:session-statistics-summary;
      }

      container ipv6-bfd-summary {
         description
           "Ipv6 bfd session summary.";

         uses bfd-types:session-statistics-summary;
      }

      container lsp-bfd-summary {
         description
           "Lsp bfd session summary.";

         uses bfd-types:session-statistics-summary;
      }
    }
  }

  notification bfd-notification {
    description
      "Notification for BFD session state change.";

    leaf session-index {
       type uint32;
       description
          "An index used to uniquely identify BFD sessions.";
    }
    leaf session-type {
      type bfd-types:bfd-session-type;
      description
        "BFD session type, this indicates the path type that BFD is
         running on";
    }
    leaf dest-addr {
       type inet:ip-address;
       description
          "IP address of the peer.";
    }
    leaf source-addr {
       type inet:ip-address;
       description
          "Local IP address.";
    }
    leaf interface {
       type leafref  {
          path "/oc-if:interfaces/oc-if:interface/oc-if:name";
       }
       description
          "L3 interface on which the BFD session is running.";
    }
    leaf tunnel-name {
       when "../session-type = 'tp-ingress-corout' or
             ../session-type = 'tp-egress-corout'" {
          description
             "Tunnel name applicable when session-type is tp-ingress-corout
              or tp-egress-corout.";
       }
       type leafref  {
          path "/mpls-tp:tp-corouted-tunnels/mpls-tp:tunnel/mpls-tp:name";
       }
       description
          "Tunnel on which the BFD session is running.";
    }
    leaf local-state {
       type bfd-types:state;
       description
          "Local state of the BFD session.";
    }
    leaf remote-state {
       type bfd-types:state;
       description
          "Remote state of the BFD session.";
    }
  }
}
