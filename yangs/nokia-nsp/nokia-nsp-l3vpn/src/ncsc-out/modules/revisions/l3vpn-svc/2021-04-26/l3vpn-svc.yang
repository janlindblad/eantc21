module l3vpn-svc {
  // Generated by yanger -t ncs
  tailf:mount-id "nokia-nsp-l3vpn-nc-1.0:nokia-nsp-l3vpn-nc-1.0";
  tailf:ncs-device-type "netconf";

  namespace "http://www.nokia.com/ietf-l3vpn-ntw:l3vpn-ntw/vpn-services";
  prefix l3vpn-svc;

  import tailf-common {
    prefix tailf;
  }
  import tailf-ncs {
    prefix ncs;
  }

  organization
    "NOKIA Corp";
  contact
    "";
  description
    "";

  revision 2021-04-26 {
    description
      "Initial revision.";
  }

  augment "/ncs:devices/ncs:device/ncs:config" {
    container l3vpn-svc {
      tailf:ncs-device-type "netconf";
      tailf:display-when "not(../../ncs:module) or ../../ncs:module[ncs:name='l3vpn-svc']";
      container vpn-services {
        list vpn-service {
          key "vpn-id";
          leaf vpn-id {
            type string;
          }
          leaf rd {
            type string;
          }
          container vpn-targets {
            list vpn-target {
              key "route-target";
              leaf route-target {
                type string;
              }
              leaf route-target-type {
                type string;
              }
            }
          }
        }
      }
      container sites {
        list site {
          key "site-id";
          leaf site-id {
            type string;
          }
          container locations {
            list location {
              key "location-id";
              leaf location-id {
                type string;
              }
            }
          }
          container devices {
            list device {
              key "device-id";
              leaf device-id {
                type string;
              }
              leaf location {
                type string;
              }
            }
          }
          container management {
            leaf type {
              type string;
            }
          }
          container vpn-policies {
            list vpn-policy {
              key "vpn-policy-id";
              leaf vpn-policy-id {
                type int16;
              }
              container entries {
                leaf id {
                  type int16;
                }
                container vpn {
                  leaf vpn-id {
                    type string;
                  }
                  leaf router-id {
                    type string;
                  }
                  leaf autonomous-system {
                    type string;
                  }
                  leaf site-role {
                    type string;
                  }
                }
              }
            }
          }
          container site-bearer {
            leaf port-id {
              type string;
            }
          }
          container site-network-accesses {
            list site-network-access {
              key "site-network-access-id";
              leaf site-network-access-id {
                type string;
              }
              container status {
                leaf admin-enabled {
                  type boolean;
                }
              }
              container bearer {
                container connection {
                  leaf encapsulation-type {
                    type string;
                  }
                  container tagged-interface {
                    container dot1q-vlan-tagged {
                      leaf cvlan-id {
                        type string;
                      }
                      leaf tq-type {
                        type string;
                      }
                    }
                    leaf type {
                      type string;
                    }
                  }
                }
              }
              container ip-connection {
                container ipv4 {
                  leaf address-allocation-type {
                    type string;
                  }
                  container addresses {
                    leaf prefix-length {
                      type string;
                    }
                    leaf provider-address {
                      type string;
                    }
                  }
                }
              }
              container routing-protocols {
                list routing-protocol {
                  key "type";
                  leaf type {
                    type string;
                  }
                  leaf address-family {
                    type string;
                  }
                  leaf peer-as {
                    type string;
                  }
                  leaf peer-address {
                    type string;
                  }
                  leaf peer-description {
                    type string;
                  }
                  leaf peer-status {
                    type string;
                  }
                }
              }
              leaf device-reference {
                type string;
              }
              container service {
                leaf svc-input-bandwidth {
                  type string;
                }
                leaf svc-output-bandwidth {
                  type string;
                }
                leaf svc-mtu {
                  type int16;
                }
              }
              container vpn-attachment {
                leaf vpn-id {
                  type string;
                }
              }
            }
          }
        }
      }
    }
  }
  augment "/ncs:devices/ncs:device/ncs:live-status" {
    container l3vpn-svc {
      tailf:ncs-device-type "netconf";
      tailf:display-when "not(../../ncs:module) or ../../ncs:module[ncs:name='l3vpn-svc'] or (../../ncs:live-status-protocol[not(ncs:capability)]) or (../../ncs:live-status-protocol/ncs:capability/ncs:module[.='l3vpn-svc'])";
      container vpn-services {
        list vpn-service {
          key "vpn-id";
          leaf vpn-id {
            type string;
          }
          leaf rd {
            type string;
          }
          container vpn-targets {
            list vpn-target {
              key "route-target";
              leaf route-target {
                type string;
              }
              leaf route-target-type {
                type string;
              }
            }
          }
        }
      }
      container sites {
        list site {
          key "site-id";
          leaf site-id {
            type string;
          }
          container locations {
            list location {
              key "location-id";
              leaf location-id {
                type string;
              }
            }
          }
          container devices {
            list device {
              key "device-id";
              leaf device-id {
                type string;
              }
              leaf location {
                type string;
              }
            }
          }
          container management {
            leaf type {
              type string;
            }
          }
          container vpn-policies {
            list vpn-policy {
              key "vpn-policy-id";
              leaf vpn-policy-id {
                type int16;
              }
              container entries {
                leaf id {
                  type int16;
                }
                container vpn {
                  leaf vpn-id {
                    type string;
                  }
                  leaf router-id {
                    type string;
                  }
                  leaf autonomous-system {
                    type string;
                  }
                  leaf site-role {
                    type string;
                  }
                }
              }
            }
          }
          container site-bearer {
            leaf port-id {
              type string;
            }
          }
          container site-network-accesses {
            list site-network-access {
              key "site-network-access-id";
              leaf site-network-access-id {
                type string;
              }
              container status {
                leaf admin-enabled {
                  type boolean;
                }
              }
              container bearer {
                container connection {
                  leaf encapsulation-type {
                    type string;
                  }
                  container tagged-interface {
                    container dot1q-vlan-tagged {
                      leaf cvlan-id {
                        type string;
                      }
                      leaf tq-type {
                        type string;
                      }
                    }
                    leaf type {
                      type string;
                    }
                  }
                }
              }
              container ip-connection {
                container ipv4 {
                  leaf address-allocation-type {
                    type string;
                  }
                  container addresses {
                    leaf prefix-length {
                      type string;
                    }
                    leaf provider-address {
                      type string;
                    }
                  }
                }
              }
              container routing-protocols {
                list routing-protocol {
                  key "type";
                  leaf type {
                    type string;
                  }
                  leaf address-family {
                    type string;
                  }
                  leaf peer-as {
                    type string;
                  }
                  leaf peer-address {
                    type string;
                  }
                  leaf peer-description {
                    type string;
                  }
                  leaf peer-status {
                    type string;
                  }
                }
              }
              leaf device-reference {
                type string;
              }
              container service {
                leaf svc-input-bandwidth {
                  type string;
                }
                leaf svc-output-bandwidth {
                  type string;
                }
                leaf svc-mtu {
                  type int16;
                }
              }
              container vpn-attachment {
                leaf vpn-id {
                  type string;
                }
              }
            }
          }
        }
      }
    }
  }
  augment "/ncs:devices/ncs:template/ncs:ned-id/ncs:config" {
    container l3vpn-svc {
      container vpn-services {
        list vpn-service {
          // NCS patched for predictable order
          ordered-by user;
          key "vpn-id";
          leaf vpn-id {
            type string;
          }
          leaf rd {
            type string;
          }
          container vpn-targets {
            list vpn-target {
              // NCS patched for predictable order
              ordered-by user;
              key "route-target";
              leaf route-target {
                type string;
              }
              leaf route-target-type {
                type string;
              }
            }
          }
        }
      }
      container sites {
        list site {
          // NCS patched for predictable order
          ordered-by user;
          key "site-id";
          leaf site-id {
            type string;
          }
          container locations {
            list location {
              // NCS patched for predictable order
              ordered-by user;
              key "location-id";
              leaf location-id {
                type string;
              }
            }
          }
          container devices {
            list device {
              // NCS patched for predictable order
              ordered-by user;
              key "device-id";
              leaf device-id {
                type string;
              }
              leaf location {
                type string;
              }
            }
          }
          container management {
            leaf type {
              type string;
            }
          }
          container vpn-policies {
            list vpn-policy {
              // NCS patched for predictable order
              ordered-by user;
              key "vpn-policy-id";
              leaf vpn-policy-id {
                type string;
              }
              container entries {
                leaf id {
                  type string;
                }
                container vpn {
                  leaf vpn-id {
                    type string;
                  }
                  leaf router-id {
                    type string;
                  }
                  leaf autonomous-system {
                    type string;
                  }
                  leaf site-role {
                    type string;
                  }
                }
              }
            }
          }
          container site-bearer {
            leaf port-id {
              type string;
            }
          }
          container site-network-accesses {
            list site-network-access {
              // NCS patched for predictable order
              ordered-by user;
              key "site-network-access-id";
              leaf site-network-access-id {
                type string;
              }
              container status {
                leaf admin-enabled {
                  type string;
                }
              }
              container bearer {
                container connection {
                  leaf encapsulation-type {
                    type string;
                  }
                  container tagged-interface {
                    container dot1q-vlan-tagged {
                      leaf cvlan-id {
                        type string;
                      }
                      leaf tq-type {
                        type string;
                      }
                    }
                    leaf type {
                      type string;
                    }
                  }
                }
              }
              container ip-connection {
                container ipv4 {
                  leaf address-allocation-type {
                    type string;
                  }
                  container addresses {
                    leaf prefix-length {
                      type string;
                    }
                    leaf provider-address {
                      type string;
                    }
                  }
                }
              }
              container routing-protocols {
                list routing-protocol {
                  // NCS patched for predictable order
                  ordered-by user;
                  key "type";
                  leaf type {
                    type string;
                  }
                  leaf address-family {
                    type string;
                  }
                  leaf peer-as {
                    type string;
                  }
                  leaf peer-address {
                    type string;
                  }
                  leaf peer-description {
                    type string;
                  }
                  leaf peer-status {
                    type string;
                  }
                }
              }
              leaf device-reference {
                type string;
              }
              container service {
                leaf svc-input-bandwidth {
                  type string;
                }
                leaf svc-output-bandwidth {
                  type string;
                }
                leaf svc-mtu {
                  type string;
                }
              }
              container vpn-attachment {
                leaf vpn-id {
                  type string;
                }
              }
            }
          }
        }
      }
    }
  }
}
