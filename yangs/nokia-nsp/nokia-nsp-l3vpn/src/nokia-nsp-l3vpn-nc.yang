module nokia-nsp-l3vpn-nc {
  yang-version 1.1;
  namespace "http://tail-f.com/ns/ned-id/nokia-nsp-l3vpn-nc";
  prefix nokia-nsp-l3vpn-nc;

  import tailf-common {
    prefix tailf;
  }

  import tailf-ncs-ned {
    prefix ned;
  }

  identity nokia-nsp-l3vpn-nc {
    tailf:abstract;
    base ned:netconf-ned-id;
  }
}
