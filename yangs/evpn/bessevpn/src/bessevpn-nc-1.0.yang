module bessevpn-nc-1.0 {
  yang-version 1.1;
  namespace "http://tail-f.com/ns/ned-id/bessevpn-nc-1.0";
  prefix bessevpn-nc-1.0;

  import bessevpn-nc {
    prefix family;
  }

  identity bessevpn-nc-1.0 {
    base family:bessevpn-nc;
  }
}
