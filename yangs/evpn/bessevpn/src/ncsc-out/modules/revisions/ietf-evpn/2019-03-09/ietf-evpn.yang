module ietf-evpn {
  // Generated by yanger -t ncs
  tailf:mount-id "bessevpn-nc-1.0:bessevpn-nc-1.0";
  tailf:ncs-device-type "netconf";

  namespace "urn:ietf:params:xml:ns:yang:ietf-evpn";
  prefix evpn;

  import ietf-inet-types {
    prefix inet;
  }
  import ietf-yang-types {
    prefix yang;
  }
  import ietf-routing-types {
    prefix rt-types;
  }
  import ietf-network-instance {
    prefix ni;
  }
  import ietf-l2vpn {
    prefix l2vpn;
  }
  import ietf-pseudowires {
    prefix pw;
  }
  import ietf-ethernet-segment {
    prefix es;
  }
  import tailf-common {
    prefix tailf;
  }
  import tailf-ncs {
    prefix ncs;
  }

  organization
    "ietf";
  contact
    "ietf";
  description
    "evpn";

  revision 2019-03-09 {
    description
      " - Incorporated ietf-ethernet-segment model and   normalised ethernet-segment entries on routes  - Updated Route-target lists to rt-types:vpn-route-targets ";
    reference "";
  }
  revision 2018-02-20 {
    description
      " - Incorporated ietf-network-instance model   on which ietf-l2vpn is now based ";
    reference "";
  }
  revision 2017-10-21 {
    description
      " - Modified the operational state augment  - Renamed evpn-instances-state to evpn-instances - Added vpws-vlan-aware to an EVPN instance  - Added a new augment to L2VPN to add EPVN  - pseudowire for the case of EVPN VPWS  - Added state change notification ";
    reference "";
  }
  revision 2017-03-13 {
    description
      " - Added an augment to base L2VPN model to    reference an EVPN instance  - Reused ietf-routing-types.yang    vpn-route-targets grouping instead of    defining it in this module ";
    reference "";
  }
  revision 2016-07-08 {
    description
      " - Added operational state - Added a configuration knob to enable/disable    underlay-multicast  - Added a configuration knob to enable/disable    flooding of unknonw unicast  - Added several configuration knobs    to manage ARP and ND";
    reference "";
  }
  revision 2016-06-23 {
    description
      "WG document adoption";
    reference "";
  }
  revision 2015-10-15 {
    description
      "Initial revision";
    reference "";
  }

  typedef ncs_template_evpn-instance-ref {
    type string;
    description
      "A leafref type to an EVPN instance";
  }

  typedef ncs_rpc_notif_evpn-instance-ref {
    type string;
    description
      "A leafref type to an EVPN instance";
  }

  typedef live_ncs_evpn-instance-ref {
    type leafref {
      path "/ncs:devices/ncs:device/ncs:live-status/evpn/evpn-instances/evpn-instance/name" {
        tailf:xpath-root 3;
      }
    }
    description
      "A leafref type to an EVPN instance";
  }

  typedef evpn-instance-ref {
    type leafref {
      path "/ncs:devices/ncs:device/ncs:config/evpn/evpn-instances/evpn-instance/name" {
        tailf:xpath-root 3;
      }
    }
    description
      "A leafref type to an EVPN instance";
  }

  grouping ncs_template_route-rd-rt-grp {
    description
      "A grouping for a route's route distinguishers and route targets";
    list rd-rt {
      // NCS patched for predictable order
      ordered-by user;
      key "route-distinguisher";
      leaf route-distinguisher {
        type rt-types:ncs_template_route-distinguisher;
        description
          "Route distinguisher";
      }
      list vpn-target {
        // NCS patched for predictable order
        ordered-by user;
        key "route-target";
        leaf route-target {
          type rt-types:ncs_template_route-target;
          description
            "BGP route target";
        }
        description
          "A list of route targets";
      }
      description
        "A list of route distinguishers and corresponding VPN route targets";
    }
  }

  grouping ncs_template_next-hop-label-grp {
    description
      "next-hop-label-grp";
    leaf next-hop {
      type string;
      description
        "next-hop";
    }
    leaf label {
      type rt-types:ncs_template_mpls-label;
      description
        "label";
    }
  }

  grouping ncs_template_next-hop-label2-grp {
    description
      "next-hop-label2-grp";
    leaf label2 {
      type rt-types:ncs_template_mpls-label;
      description
        "label2";
    }
  }

  grouping ncs_template_path-detail-grp {
    description
      "path-detail-grp";
    // NCS drop config false container detail
  }

  grouping ncs_rpc_notif_route-rd-rt-grp {
    description
      "A grouping for a route's route distinguishers and route targets";
    list rd-rt {
      key "route-distinguisher";
      leaf route-distinguisher {
        type rt-types:ncs_rpc_notif_route-distinguisher;
        description
          "Route distinguisher";
      }
      list vpn-target {
        key "route-target";
        leaf route-target {
          type rt-types:ncs_rpc_notif_route-target;
          description
            "BGP route target";
        }
        description
          "A list of route targets";
      }
      description
        "A list of route distinguishers and corresponding VPN route targets";
    }
  }

  grouping ncs_rpc_notif_next-hop-label-grp {
    description
      "next-hop-label-grp";
    leaf next-hop {
      type inet:ip-address;
      description
        "next-hop";
    }
    leaf label {
      type rt-types:ncs_rpc_notif_mpls-label;
      description
        "label";
    }
  }

  grouping ncs_rpc_notif_next-hop-label2-grp {
    description
      "next-hop-label2-grp";
    leaf label2 {
      type rt-types:ncs_rpc_notif_mpls-label;
      description
        "label2";
    }
  }

  grouping ncs_rpc_notif_path-detail-grp {
    description
      "path-detail-grp";
    container detail {
      config false;
      description
        "path details";
      container attributes {
        leaf-list extended-community {
          type string;
          description
            "extended-community";
        }
        description
          "attributes";
      }
      leaf bestpath {
        type empty;
        description
          "Indicate this path is the best path";
      }
    }
  }

  grouping live_ncs_route-rd-rt-grp {
    description
      "A grouping for a route's route distinguishers and route targets";
    list rd-rt {
      key "route-distinguisher";
      leaf route-distinguisher {
        type rt-types:live_ncs_route-distinguisher;
        description
          "Route distinguisher";
      }
      list vpn-target {
        key "route-target";
        leaf route-target {
          type rt-types:live_ncs_route-target;
          description
            "BGP route target";
        }
        description
          "A list of route targets";
      }
      description
        "A list of route distinguishers and corresponding VPN route targets";
    }
  }

  grouping live_ncs_next-hop-label-grp {
    description
      "next-hop-label-grp";
    leaf next-hop {
      type inet:ip-address;
      description
        "next-hop";
    }
    leaf label {
      type rt-types:live_ncs_mpls-label;
      description
        "label";
    }
  }

  grouping live_ncs_next-hop-label2-grp {
    description
      "next-hop-label2-grp";
    leaf label2 {
      type rt-types:live_ncs_mpls-label;
      description
        "label2";
    }
  }

  grouping live_ncs_path-detail-grp {
    description
      "path-detail-grp";
    container detail {
      description
        "path details";
      container attributes {
        leaf-list extended-community {
          type string;
          description
            "extended-community";
        }
        description
          "attributes";
      }
      leaf bestpath {
        type empty;
        description
          "Indicate this path is the best path";
      }
    }
  }

  grouping route-rd-rt-grp {
    description
      "A grouping for a route's route distinguishers and route targets";
    list rd-rt {
      key "route-distinguisher";
      leaf route-distinguisher {
        type rt-types:route-distinguisher;
        description
          "Route distinguisher";
      }
      list vpn-target {
        key "route-target";
        leaf route-target {
          type rt-types:route-target;
          description
            "BGP route target";
        }
        description
          "A list of route targets";
      }
      description
        "A list of route distinguishers and corresponding VPN route targets";
    }
  }

  grouping next-hop-label-grp {
    description
      "next-hop-label-grp";
    leaf next-hop {
      type inet:ip-address;
      description
        "next-hop";
    }
    leaf label {
      type rt-types:mpls-label;
      description
        "label";
    }
  }

  grouping next-hop-label2-grp {
    description
      "next-hop-label2-grp";
    leaf label2 {
      type rt-types:mpls-label;
      description
        "label2";
    }
  }

  grouping path-detail-grp {
    description
      "path-detail-grp";
    // NCS drop config false container detail
  }

  augment "/ncs:devices/ncs:device/ncs:netconf-notifications/ncs:received-notifications/ncs:notification/ncs:data" {
    container evpn-state-change-notification {
      presence "";
      config false;
      description
        "EVPN state change notification";
      leaf evpn-instance {
        type ncs_rpc_notif_evpn-instance-ref;
        description
          "Related EVPN instance";
      }
      leaf state {
        type identityref {
          base evpn-notification-state;
        }
        description
          "State change notification";
      }
    }
  }
  augment "/ncs:devices/ncs:device/ncs:config" {
    container evpn {
      tailf:ncs-device-type "netconf";
      tailf:display-when "not(../../ncs:module) or ../../ncs:module[ncs:name='ietf-evpn']";
      description
        "evpn";
      container common {
        description
          "common epn attributes";
        choice replication-type {
          description
            "A choice of replication type";
          case ingress-replication {
            leaf ingress-replication {
              type boolean;
              description
                "ingress-replication";
            }
          }
          case p2mp-replication {
            leaf p2mp-replication {
              type boolean;
              description
                "p2mp-replication";
            }
          }
        }
      }
      container evpn-instances {
        description
          "evpn-instances";
        list evpn-instance {
          key "name";
          description
            "An EVPN instance";
          leaf name {
            type string;
            description
              "Name of EVPN instance";
          }
          leaf evi {
            type uint32;
            description
              "evi";
          }
          container pbb-parameters {
            tailf:display-when "not(../../../../ncs:module) or boolean(/ncs:devices/ncs:device[ncs:name=current()/../../../../ncs:name]/capability/feature='evpn-pbb-params')";
            description
              "PBB parameters";
            leaf source-bmac {
              type yang:hex-string;
              description
                "source-bmac";
            }
          }
          container bgp-parameters {
            description
              "BGP parameters";
            container common {
              description
                "BGP parameters common to all pseudowires";
              list rd-rt {
                tailf:display-when "not(../../../../../ncs:module) or boolean(/ncs:devices/ncs:device[ncs:name=current()/../../../../../ncs:name]/capability/feature='evpn-bgp-params')";
                key "route-distinguisher";
                leaf route-distinguisher {
                  type rt-types:route-distinguisher;
                  description
                    "Route distinguisher";
                }
                uses rt-types:vpn-route-targets;
                description
                  "A list of route distinguishers and corresponding VPN route targets";
              }
            }
          }
          leaf arp-proxy {
            type boolean;
            default "false";
            description
              "Enable (TRUE) or disable (FALSE) ARP proxy";
          }
          leaf arp-suppression {
            type boolean;
            default "false";
            description
              "Enable (TRUE) or disable (FALSE) ARP suppression";
          }
          leaf nd-proxy {
            type boolean;
            default "false";
            description
              "Enable (TRUE) or disable (FALSE) ND proxy";
          }
          leaf nd-suppression {
            type boolean;
            default "false";
            description
              "Enable (TRUE) or disable (FALSE) ND suppression";
          }
          leaf underlay-multicast {
            type boolean;
            default "false";
            description
              "Enable (TRUE) or disable (FALSE) underlay multicast";
          }
          leaf flood-unknown-unicast-supression {
            type boolean;
            default "false";
            description
              "Enable (TRUE) or disable (FALSE) flood unknown unicast suppression";
          }
          leaf vpws-vlan-aware {
            type boolean;
            default "false";
            description
              "Enable (TRUE) or disable (FALSE) VPWS VLAN aware";
          }
          // NCS drop config false container routes
          // NCS drop config false container statistics
        }
      }
    }
  }
  augment "/ncs:devices/ncs:device/ncs:live-status" {
    container evpn {
      tailf:ncs-device-type "netconf";
      tailf:display-when "not(../../ncs:module) or ../../ncs:module[ncs:name='ietf-evpn'] or (../../ncs:live-status-protocol[not(ncs:capability)]) or (../../ncs:live-status-protocol/ncs:capability/ncs:module[.='ietf-evpn'])";
      description
        "evpn";
      container common {
        description
          "common epn attributes";
        choice replication-type {
          description
            "A choice of replication type";
          case ingress-replication {
            leaf ingress-replication {
              type boolean;
              description
                "ingress-replication";
            }
          }
          case p2mp-replication {
            leaf p2mp-replication {
              type boolean;
              description
                "p2mp-replication";
            }
          }
        }
      }
      container evpn-instances {
        description
          "evpn-instances";
        list evpn-instance {
          key "name";
          description
            "An EVPN instance";
          leaf name {
            type string;
            description
              "Name of EVPN instance";
          }
          leaf evi {
            type uint32;
            description
              "evi";
          }
          container pbb-parameters {
            // NCS drop if-feature statement
            description
              "PBB parameters";
            leaf source-bmac {
              type yang:hex-string;
              description
                "source-bmac";
            }
          }
          container bgp-parameters {
            description
              "BGP parameters";
            container common {
              description
                "BGP parameters common to all pseudowires";
              list rd-rt {
                // NCS drop if-feature statement
                key "route-distinguisher";
                leaf route-distinguisher {
                  type rt-types:live_ncs_route-distinguisher;
                  description
                    "Route distinguisher";
                }
                uses rt-types:live_ncs_vpn-route-targets;
                description
                  "A list of route distinguishers and corresponding VPN route targets";
              }
            }
          }
          leaf arp-proxy {
            type boolean;
            // NCS drop default statement
            description
              "Enable (TRUE) or disable (FALSE) ARP proxy";
          }
          leaf arp-suppression {
            type boolean;
            // NCS drop default statement
            description
              "Enable (TRUE) or disable (FALSE) ARP suppression";
          }
          leaf nd-proxy {
            type boolean;
            // NCS drop default statement
            description
              "Enable (TRUE) or disable (FALSE) ND proxy";
          }
          leaf nd-suppression {
            type boolean;
            // NCS drop default statement
            description
              "Enable (TRUE) or disable (FALSE) ND suppression";
          }
          leaf underlay-multicast {
            type boolean;
            // NCS drop default statement
            description
              "Enable (TRUE) or disable (FALSE) underlay multicast";
          }
          leaf flood-unknown-unicast-supression {
            type boolean;
            // NCS drop default statement
            description
              "Enable (TRUE) or disable (FALSE) flood unknown unicast suppression";
          }
          leaf vpws-vlan-aware {
            type boolean;
            // NCS drop default statement
            description
              "Enable (TRUE) or disable (FALSE) VPWS VLAN aware";
          }
          container routes {
            description
              "routes";
            list ethernet-auto-discovery-route {
              uses live_ncs_route-rd-rt-grp;
              leaf ethernet-segment-identifier {
                type es:live_ncs_ethernet-segment-identifier-type;
                description
                  "Ethernet segment identifier (esi)";
              }
              leaf ethernet-tag {
                type uint32;
                description
                  "An ethernet tag (etag) indentifying a broadcast domain";
              }
              list path {
                uses live_ncs_next-hop-label-grp;
                uses live_ncs_path-detail-grp;
                description
                  "path";
              }
              description
                "ethernet-auto-discovery-route";
            }
            list mac-ip-advertisement-route {
              uses live_ncs_route-rd-rt-grp;
              leaf ethernet-segment-identifier {
                type es:live_ncs_ethernet-segment-identifier-type;
                description
                  "Ethernet segment identifier (esi)";
              }
              leaf ethernet-tag {
                type uint32;
                description
                  "An ethernet tag (etag) indentifying a broadcast domain";
              }
              leaf mac-address {
                type yang:mac-address;
                description
                  "Route mac address";
              }
              leaf mac-address-length {
                type uint8 {
                  range "0..48";
                }
                description
                  "mac address length";
              }
              leaf ip-prefix {
                type inet:ip-prefix;
                description
                  "ip-prefix";
              }
              list path {
                uses live_ncs_next-hop-label-grp;
                uses live_ncs_next-hop-label2-grp;
                uses live_ncs_path-detail-grp;
                description
                  "path";
              }
              description
                "mac-ip-advertisement-route";
            }
            list inclusive-multicast-ethernet-tag-route {
              uses live_ncs_route-rd-rt-grp;
              leaf originator-ip-prefix {
                type inet:ip-prefix;
                description
                  "originator-ip-prefix";
              }
              list path {
                uses live_ncs_next-hop-label-grp;
                uses live_ncs_path-detail-grp;
                description
                  "path";
              }
              description
                "inclusive-multicast-ethernet-tag-route";
            }
            list ethernet-segment-route {
              uses live_ncs_route-rd-rt-grp;
              leaf ethernet-segment-identifier {
                type es:live_ncs_ethernet-segment-identifier-type;
                description
                  "Ethernet segment identifier (esi)";
              }
              leaf originator-ip-prefix {
                type inet:ip-prefix;
                description
                  "originator ip-prefix";
              }
              list path {
                leaf next-hop {
                  type inet:ip-address;
                  description
                    "next-hop";
                }
                uses live_ncs_path-detail-grp;
                description
                  "path";
              }
              description
                "ethernet-segment-route";
            }
            list ip-prefix-route {
              uses live_ncs_route-rd-rt-grp;
              leaf ethernet-segment-identifier {
                type es:live_ncs_ethernet-segment-identifier-type;
                description
                  "Ethernet segment identifier (esi)";
              }
              leaf ip-prefix {
                type inet:ip-prefix;
                description
                  "ip-prefix";
              }
              list path {
                uses live_ncs_next-hop-label-grp;
                uses live_ncs_path-detail-grp;
                description
                  "path";
              }
              description
                "ip-prefix route";
            }
          }
          container statistics {
            description
              "Statistics";
            leaf tx-count {
              type yang:zero-based-counter32;
              description
                "transmission count";
            }
            leaf rx-count {
              type yang:zero-based-counter32;
              description
                "receive count";
            }
            container detail {
              description
                "Detailed statistics";
              leaf broadcast-tx-count {
                type yang:zero-based-counter32;
                description
                  "broadcast transmission count";
              }
              leaf broadcast-rx-count {
                type yang:zero-based-counter32;
                description
                  "broadcast receive count";
              }
              leaf multicast-tx-count {
                type yang:zero-based-counter32;
                description
                  "multicast transmission count";
              }
              leaf multicast-rx-count {
                type yang:zero-based-counter32;
                description
                  "multicast receive count";
              }
              leaf unknown-unicast-tx-count {
                type yang:zero-based-counter32;
                description
                  "unknown unicast transmission count";
              }
              leaf unknown-unicast-rx-count {
                type yang:zero-based-counter32;
                description
                  "unknown-unicast receive count";
              }
            }
          }
        }
      }
    }
  }
  augment "/ncs:devices/ncs:template/ncs:ned-id/ncs:config" {
    container evpn {
      description
        "evpn";
      container common {
        description
          "common epn attributes";
        choice replication-type {
          description
            "A choice of replication type";
          case ingress-replication {
            leaf ingress-replication {
              type string;
              description
                "ingress-replication";
            }
          }
          case p2mp-replication {
            leaf p2mp-replication {
              type string;
              description
                "p2mp-replication";
            }
          }
        }
      }
      container evpn-instances {
        description
          "evpn-instances";
        list evpn-instance {
          // NCS patched for predictable order
          ordered-by user;
          key "name";
          description
            "An EVPN instance";
          leaf name {
            type string;
            description
              "Name of EVPN instance";
          }
          leaf evi {
            type string;
            description
              "evi";
          }
          container pbb-parameters {
            // NCS drop if-feature statement
            description
              "PBB parameters";
            leaf source-bmac {
              type string;
              description
                "source-bmac";
            }
          }
          container bgp-parameters {
            description
              "BGP parameters";
            container common {
              description
                "BGP parameters common to all pseudowires";
              list rd-rt {
                // NCS patched for predictable order
                ordered-by user;
                // NCS drop if-feature statement
                key "route-distinguisher";
                leaf route-distinguisher {
                  type rt-types:ncs_template_route-distinguisher;
                  description
                    "Route distinguisher";
                }
                uses rt-types:ncs_template_vpn-route-targets;
                description
                  "A list of route distinguishers and corresponding VPN route targets";
              }
            }
          }
          leaf arp-proxy {
            type string;
            // NCS drop default statement
            description
              "Enable (TRUE) or disable (FALSE) ARP proxy";
          }
          leaf arp-suppression {
            type string;
            // NCS drop default statement
            description
              "Enable (TRUE) or disable (FALSE) ARP suppression";
          }
          leaf nd-proxy {
            type string;
            // NCS drop default statement
            description
              "Enable (TRUE) or disable (FALSE) ND proxy";
          }
          leaf nd-suppression {
            type string;
            // NCS drop default statement
            description
              "Enable (TRUE) or disable (FALSE) ND suppression";
          }
          leaf underlay-multicast {
            type string;
            // NCS drop default statement
            description
              "Enable (TRUE) or disable (FALSE) underlay multicast";
          }
          leaf flood-unknown-unicast-supression {
            type string;
            // NCS drop default statement
            description
              "Enable (TRUE) or disable (FALSE) flood unknown unicast suppression";
          }
          leaf vpws-vlan-aware {
            type string;
            // NCS drop default statement
            description
              "Enable (TRUE) or disable (FALSE) VPWS VLAN aware";
          }
          // NCS drop config false container routes
          // NCS drop config false container statistics
        }
      }
    }
  }
  augment "/ncs:devices/ncs:template/ncs:ned-id/ncs:config/pw:pseudowires/pw:pseudowire/pw:pw-type" {
    description
      "Augment for an L2VPN instance to add EVPN VPWS pseudowire";
    case evpn-pw {
      container evpn-pw {
        description
          "EVPN pseudowire";
        leaf remote-id {
          type string;
          description
            "Remote pseudowire ID";
        }
        leaf local-id {
          type string;
          description
            "Local pseudowire ID";
        }
      }
    }
  }
  augment "/ncs:devices/ncs:device/ncs:live-status/pw:pseudowires/pw:pseudowire/pw:pw-type" {
    description
      "Augment for an L2VPN instance to add EVPN VPWS pseudowire";
    case evpn-pw {
      container evpn-pw {
        description
          "EVPN pseudowire";
        leaf remote-id {
          type uint32;
          description
            "Remote pseudowire ID";
        }
        leaf local-id {
          type uint32;
          description
            "Local pseudowire ID";
        }
      }
    }
  }
  augment "/ncs:devices/ncs:device/ncs:config/pw:pseudowires/pw:pseudowire/pw:pw-type" {
    description
      "Augment for an L2VPN instance to add EVPN VPWS pseudowire";
    case evpn-pw {
      container evpn-pw {
        description
          "EVPN pseudowire";
        leaf remote-id {
          type uint32;
          description
            "Remote pseudowire ID";
        }
        leaf local-id {
          type uint32;
          description
            "Local pseudowire ID";
        }
      }
    }
  }
  augment "/ncs:devices/ncs:template/ncs:ned-id/ncs:config/ni:network-instances/ni:network-instance/ni:ni-type/l2vpn:l2vpn" {
    description
      "Augment for an L2VPN instance and EVPN association";
    leaf evpn-instance {
      type ncs_template_evpn-instance-ref;
      description
        "Reference to an EVPN instance";
    }
  }
  augment "/ncs:devices/ncs:device/ncs:live-status/ni:network-instances/ni:network-instance/ni:ni-type/l2vpn:l2vpn" {
    description
      "Augment for an L2VPN instance and EVPN association";
    leaf evpn-instance {
      tailf:ncs-device-type "netconf";
      tailf:display-when "not(../../../../../../ncs:module) or ../../../../../../ncs:module[ncs:name='ietf-evpn'] or (../../../../../../ncs:live-status-protocol[not(ncs:capability)]) or (../../../../../../ncs:live-status-protocol/ncs:capability/ncs:module[.='ietf-evpn'])";
      type live_ncs_evpn-instance-ref;
      description
        "Reference to an EVPN instance";
    }
  }
  augment "/ncs:devices/ncs:device/ncs:config/ni:network-instances/ni:network-instance/ni:ni-type/l2vpn:l2vpn" {
    description
      "Augment for an L2VPN instance and EVPN association";
    leaf evpn-instance {
      tailf:ncs-device-type "netconf";
      tailf:display-when "not(../../../../../../ncs:module) or ../../../../../../ncs:module[ncs:name='ietf-evpn']";
      type evpn-instance-ref;
      description
        "Reference to an EVPN instance";
    }
  }
  augment "/ncs:devices/ncs:template/ncs:ned-id/ncs:config/ni:network-instances/ni:network-instance/ni:ni-type/l2vpn:l2vpn" {
    // NCS drop when statement
    description
      "Augment for VPLS instance";
    container vpls-contstraints {
      // NCS drop must statement
      description
        "VPLS constraints";
    }
  }
  augment "/ncs:devices/ncs:device/ncs:live-status/ni:network-instances/ni:network-instance/ni:ni-type/l2vpn:l2vpn" {
    // NCS drop when statement
    description
      "Augment for VPLS instance";
    container vpls-contstraints {
      tailf:ncs-device-type "netconf";
      tailf:display-when "not(../../../../../../ncs:module) or ../../../../../../ncs:module[ncs:name='ietf-evpn'] or (../../../../../../ncs:live-status-protocol[not(ncs:capability)]) or (../../../../../../ncs:live-status-protocol/ncs:capability/ncs:module[.='ietf-evpn'])";
      // NCS drop must statement
      description
        "VPLS constraints";
    }
  }
  augment "/ncs:devices/ncs:device/ncs:config/ni:network-instances/ni:network-instance/ni:ni-type/l2vpn:l2vpn" {
    when "l2vpn:type = 'l2vpn:vpls-instance-type'" {
      tailf:xpath-root 3;
      description
        "Constraints only for VPLS pseudowires";
    }
    description
      "Augment for VPLS instance";
    container vpls-contstraints {
      tailf:ncs-device-type "netconf";
      tailf:display-when "not(../../../../../../ncs:module) or ../../../../../../ncs:module[ncs:name='ietf-evpn']";
      must 'not(boolean(/pw:pseudowires/pw:pseudowire                [pw:name = current()/../l2vpn:endpoint            /l2vpn:pw/l2vpn:name]            /evpn-pw/remote-id)) and not(boolean(/pw:pseudowires/pw:pseudowire                [pw:name = current()/../l2vpn:endpoint            /l2vpn:pw/l2vpn:name]            /evpn-pw/local-id)) and not(boolean(/pw:pseudowires/pw:pseudowire                [pw:name = current()/../l2vpn:endpoint            /l2vpn:primary-pw/l2vpn:name]            /evpn-pw/remote-id)) and not(boolean(/pw:pseudowires/pw:pseudowire                [pw:name = current()/../l2vpn:endpoint            /l2vpn:primary-pw/l2vpn:name]            /evpn-pw/local-id)) and not(boolean(/pw:pseudowires/pw:pseudowire                [pw:name = current()/../l2vpn:endpoint            /l2vpn:backup-pw/l2vpn:name]            /evpn-pw/remote-id)) and not(boolean(/pw:pseudowires/pw:pseudowire                [pw:name = current()/../l2vpn:endpoint            /l2vpn:backup-pw/l2vpn:name]            /evpn-pw/local-id))' {
        tailf:xpath-root 3;
        description
          "A VPLS pseudowire must not be EVPN PW";
      }
      description
        "VPLS constraints";
    }
  }

  identity static-MAC-move-detected {
    base evpn-notification-state;
    description
      "Static MAC move is detected";
  }

  identity mass-withdraw-received {
    base evpn-notification-state;
    description
      "Mass withdraw received";
  }

  identity MAC-duplication-detected {
    base evpn-notification-state;
    description
      "MAC duplication is detected";
  }

  identity evpn-notification-state {
    description
      "The base identity on which EVPN notification states are based";
  }

  feature evpn-pbb-params {
    description
      "EVPN's PBB parameters";
  }

  feature evpn-bgp-params {
    description
      "EVPN's BGP parameters";
  }
}
