module bessevpn-nc {
  yang-version 1.1;
  namespace "http://tail-f.com/ns/ned-id/bessevpn-nc";
  prefix bessevpn-nc;

  import tailf-common {
    prefix tailf;
  }

  import tailf-ncs-ned {
    prefix ned;
  }

  identity bessevpn-nc {
    tailf:abstract;
    base ned:netconf-ned-id;
  }
}
